--
-- ELBER-DDM310Modem-MIB.my
-- MIB generated by MG-SOFT Visual MIB Builder Version 6.0  Build 88
-- Monday, January 09, 2006 at 09:07:59
--

ELBER-REBLE610-MIB DEFINITIONS ::= BEGIN

IMPORTS
	enterprises,
	mgmt
		FROM RFC1155-SMI
	OBJECT-TYPE
		FROM RFC-1212;


Alarm ::= INTEGER {
			ok(1),
			warning(2),
			alarm(3) }


trapLocalCommunicationInterfaceRemoteBerAlarm OBJECT-TYPE
	SYNTAX  TrapAlarm
	ACCESS  read-only
	STATUS  mandatory
	DESCRIPTION ""
	::= { trapLocalCommunicationInterface 2 }


Boolean ::= INTEGER {
			true(1),
			false(2) }


trapLocalCommunicationInterfaceTemperatureAlarm OBJECT-TYPE
	SYNTAX  TrapAlarm
	ACCESS  read-only
	STATUS  mandatory
	DESCRIPTION ""
	::= { trapLocalCommunicationInterface 3 }


Enable ::= INTEGER {
			enabled(1),
			disabled(2) }


trapLocalCommunicationInterfaceStepUpTemperatureAlarm OBJECT-TYPE
	SYNTAX  TrapAlarm
	ACCESS  read-only
	STATUS  mandatory
	DESCRIPTION ""
	::= { trapLocalCommunicationInterface 4 }


Error ::= INTEGER {
			ok(1),
			error(2) }


trapLocalCommunicationInterfacePreSwitchVoltageAlarm OBJECT-TYPE
	SYNTAX  TrapAlarm
	ACCESS  read-only
	STATUS  mandatory
	DESCRIPTION ""
	::= { trapLocalCommunicationInterface 5 }


EthPolaritySwap ::= INTEGER {
			notswapped(1),
			swapped(2) }


trapLocalCommunicationInterfacePostSwitchVoltageAlarm OBJECT-TYPE
	SYNTAX  TrapAlarm
	ACCESS  read-only
	STATUS  mandatory
	DESCRIPTION ""
	::= { trapLocalCommunicationInterface 6 }


Frequency ::= INTEGER


trapLocalCommunicationInterfaceCurrentAlarm OBJECT-TYPE
	SYNTAX  TrapAlarm
	ACCESS  read-only
	STATUS  mandatory
	DESCRIPTION ""
	::= { trapLocalCommunicationInterface 7 }


Power ::= INTEGER


trapLocalCommunicationInterfaceRSDecodeAlarm OBJECT-TYPE
	SYNTAX  TrapAlarm
	ACCESS  read-only
	STATUS  mandatory
	DESCRIPTION ""
	::= { trapLocalCommunicationInterface 8 }


Temperature ::= INTEGER (-40..100)


TrapAlarm ::= INTEGER {
			occurred(1),
			recovered(2) }


trapLocalCommunicationInterfaceDeframerLockAlarm OBJECT-TYPE
	SYNTAX  TrapAlarm
	ACCESS  read-only
	STATUS  mandatory
	DESCRIPTION ""
	::= { trapLocalCommunicationInterface 9 }


Voltage ::= INTEGER


trapLocalCommunicationInterfaceVCXOLockAlarm OBJECT-TYPE
	SYNTAX  TrapAlarm
	ACCESS  read-only
	STATUS  mandatory
	DESCRIPTION ""
	::= { trapLocalCommunicationInterface 10 }


--
-- Node definitions
--
--  Node definitions
-- 

elber OBJECT IDENTIFIER 	::= { enterprises 23548 }

trapLocalCommunicationInterfaceGtpPllLockAlarm OBJECT-TYPE
	SYNTAX  TrapAlarm
	ACCESS  read-only
	STATUS  mandatory
	DESCRIPTION ""
	::= { trapLocalCommunicationInterface 11 }


reble610 OBJECT IDENTIFIER 	::= { elber 610 }

system OBJECT IDENTIFIER 	::= { reble610 1 }

trapLocalCommunicationInterfaceSfpTxFaultAlarm OBJECT-TYPE
	SYNTAX  TrapAlarm
	ACCESS  read-only
	STATUS  mandatory
	DESCRIPTION ""
	::= { trapLocalCommunicationInterface 13 }


reble610ModulesInfo OBJECT-TYPE
	SYNTAX  SEQUENCE OF Reble610ModulesInfoEntry
	ACCESS  not-accessible
	STATUS  mandatory
	DESCRIPTION ""
	::= { system 1 }


trapLocalCommunicationInterfaceSfpLossAlarm OBJECT-TYPE
	SYNTAX  TrapAlarm
	ACCESS  read-only
	STATUS  mandatory
	DESCRIPTION ""
	::= { trapLocalCommunicationInterface 12 }


reble610ModulesInfoEntry OBJECT-TYPE
	SYNTAX  Reble610ModulesInfoEntry
	ACCESS  not-accessible
	STATUS  mandatory
	DESCRIPTION ""
	INDEX {
		reble610ModulesInfoIndex }
	::= { reble610ModulesInfo 1 }


Reble610ModulesInfoEntry ::= SEQUENCE {

	reble610ModulesInfoIndex   INTEGER,
	reble610ModulesInfoName    OCTET STRING,
	reble610ModulesInfoVersion OCTET STRING,
	reble610ModulesInfoNumber  OCTET STRING }


trapRemoteCommunicationInterfaceTemperatureAlarm OBJECT-TYPE
	SYNTAX  TrapAlarm
	ACCESS  read-only
	STATUS  mandatory
	DESCRIPTION ""
	::= { trapRemoteCommunicationInterface 1 }


trapRemoteCommunicationInterfaceVolt48Alarm OBJECT-TYPE
	SYNTAX  TrapAlarm
	ACCESS  read-only
	STATUS  mandatory
	DESCRIPTION ""
	::= { trapRemoteCommunicationInterface 2 }


reble610ModulesInfoIndex OBJECT-TYPE
	SYNTAX  INTEGER (1..5)
	ACCESS  read-only
	STATUS  mandatory
	DESCRIPTION ""
	::= { reble610ModulesInfoEntry 1 }


trapRemoteCommunicationInterfaceVolt12Alarm OBJECT-TYPE
	SYNTAX  TrapAlarm
	ACCESS  read-only
	STATUS  mandatory
	DESCRIPTION ""
	::= { trapRemoteCommunicationInterface 3 }


reble610ModulesInfoName OBJECT-TYPE
	SYNTAX  OCTET STRING
	ACCESS  read-only
	STATUS  mandatory
	DESCRIPTION ""
	::= { reble610ModulesInfoEntry 2 }


trapRemoteCommunicationInterfaceFPGAAlarm OBJECT-TYPE
	SYNTAX  TrapAlarm
	ACCESS  read-only
	STATUS  mandatory
	DESCRIPTION ""
	::= { trapRemoteCommunicationInterface 4 }


customer OBJECT IDENTIFIER 	::= { system 2 }

trapRemoteCommunicationInterfaceRSDecodeAlarm OBJECT-TYPE
	SYNTAX  TrapAlarm
	ACCESS  read-only
	STATUS  mandatory
	DESCRIPTION ""
	::= { trapRemoteCommunicationInterface 5 }


reble610CustomerName OBJECT-TYPE
	SYNTAX  OCTET STRING
	ACCESS  read-only
	STATUS  mandatory
	DESCRIPTION ""
	::= { customer 1 }


trapRemoteCommunicationInterfaceDeframerLockAlarm OBJECT-TYPE
	SYNTAX  TrapAlarm
	ACCESS  read-only
	STATUS  mandatory
	DESCRIPTION ""
	::= { trapRemoteCommunicationInterface 6 }


reble610CustomerLocation OBJECT-TYPE
	SYNTAX  OCTET STRING
	ACCESS  read-write
	STATUS  mandatory
	DESCRIPTION ""
	::= { customer 2 }


trapRemoteCommunicationInterfaceVCXOLockAlarm OBJECT-TYPE
	SYNTAX  TrapAlarm
	ACCESS  read-only
	STATUS  mandatory
	DESCRIPTION ""
	::= { trapRemoteCommunicationInterface 7 }


reble610SerialNumber OBJECT-TYPE
	SYNTAX  OCTET STRING
	ACCESS  read-only
	STATUS  mandatory
	DESCRIPTION ""
	::= { customer 3 }


trapRemoteCommunicationInterfaceGtpPllLockAlarm OBJECT-TYPE
	SYNTAX  TrapAlarm
	ACCESS  read-only
	STATUS  mandatory
	DESCRIPTION ""
	::= { trapRemoteCommunicationInterface 8 }


modules OBJECT IDENTIFIER 	::= { reble610 2 }

trapRemoteCommunicationInterfaceSfpLossAlarm OBJECT-TYPE
	SYNTAX  TrapAlarm
	ACCESS  read-only
	STATUS  mandatory
	DESCRIPTION ""
	::= { trapRemoteCommunicationInterface 9 }


modem OBJECT IDENTIFIER 	::= { modules 1 }

trapRemoteCommunicationInterfaceSfpTxFaultAlarm OBJECT-TYPE
	SYNTAX  TrapAlarm
	ACCESS  read-only
	STATUS  mandatory
	DESCRIPTION ""
	::= { trapRemoteCommunicationInterface 10 }


modemStatus OBJECT IDENTIFIER 	::= { modem 1 }

modemStatusTemperature OBJECT-TYPE
	SYNTAX  Temperature
	ACCESS  read-only
	STATUS  mandatory
	DESCRIPTION
		"Modem Board Temperature"
	::= { modemStatus 1 }


modemStatusPvg OBJECT IDENTIFIER 	::= { modemStatus 2 }

modemStatusTxProfile OBJECT-TYPE
	SYNTAX  OCTET STRING
	ACCESS  read-only
	STATUS  mandatory
	DESCRIPTION ""
	::= { modemStatusPvg 1 }


modemStatusXpicCPD OBJECT-TYPE
	SYNTAX  INTEGER
	ACCESS  read-only
	STATUS  mandatory
	DESCRIPTION
		"Cross Polarization Discrimination"
	::= { modemStatusXpicPvg 1 }


modemStatusXPicCalibrationStatus OBJECT-TYPE
	SYNTAX  INTEGER {
			success(1),
			mismatch(2),
			timeout(3) }
	ACCESS  read-only
	STATUS  mandatory
	DESCRIPTION ""
	::= { modemStatusXpicPvg 3 }


modemStatusTxSymbolRate OBJECT-TYPE
	SYNTAX  INTEGER
	ACCESS  read-only
	STATUS  mandatory
	DESCRIPTION
		"in MBaud"
	::= { modemStatusPvg 2 }


modemStatusNormalizedMSE OBJECT-TYPE
	SYNTAX  INTEGER
	ACCESS  read-only
	STATUS  mandatory
	DESCRIPTION ""
	::= { modemStatusPvg 4 }


modemStatusRXSymbolRate OBJECT-TYPE
	SYNTAX  INTEGER
	ACCESS  read-only
	STATUS  mandatory
	DESCRIPTION
		"in MBaud"
	::= { modemStatusPvg 5 }


modemStatusRXProfile OBJECT-TYPE
	SYNTAX  OCTET STRING
	ACCESS  read-only
	STATUS  mandatory
	DESCRIPTION
		"in MBaud"
	::= { modemStatusPvg 6 }


modemStatusCarrierOffset OBJECT-TYPE
	SYNTAX  INTEGER
	ACCESS  read-only
	STATUS  mandatory
	DESCRIPTION
		"in Hz"
	::= { modemStatusPvg 8 }


modemStatusInternalAGC OBJECT-TYPE
	SYNTAX  INTEGER
	ACCESS  read-only
	STATUS  mandatory
	DESCRIPTION
		"in tenth's of db"
	::= { modemStatusPvg 9 }


modemStatusXpicPvg OBJECT IDENTIFIER 	::= { modemStatus 3 }

modemStatusXPicCarrierOffset OBJECT-TYPE
	SYNTAX  INTEGER
	ACCESS  read-only
	STATUS  mandatory
	DESCRIPTION
		"in Hz"
	::= { modemStatusXpicPvg 2 }


modemStatusXPicInternalAGC OBJECT-TYPE
	SYNTAX  INTEGER
	ACCESS  read-only
	STATUS  mandatory
	DESCRIPTION
		"in tenth's of db"
	::= { modemStatusXpicPvg 4 }


modemStatusPvgAcquire OBJECT-TYPE
	SYNTAX  INTEGER {
			inprogress(1),
			locked(2),
			failed(3) }
	ACCESS  read-only
	STATUS  mandatory
	DESCRIPTION ""
	::= { modemStatusPvg 3 }


modemStatusLDPCStress OBJECT-TYPE
	SYNTAX  INTEGER
	ACCESS  read-only
	STATUS  mandatory
	DESCRIPTION
		"x 10E-8"
	::= { modemStatusPvg 7 }


modemAlarm OBJECT IDENTIFIER 	::= { modem 2 }

modemAlarmTemperature OBJECT-TYPE
	SYNTAX  Alarm
	ACCESS  read-only
	STATUS  mandatory
	DESCRIPTION ""
	::= { modemAlarm 1 }


modemAlarmMSE OBJECT-TYPE
	SYNTAX  Alarm
	ACCESS  read-only
	STATUS  mandatory
	DESCRIPTION ""
	::= { modemAlarm 2 }


modemAlarmTiming OBJECT-TYPE
	SYNTAX  Alarm
	ACCESS  read-only
	STATUS  mandatory
	DESCRIPTION ""
	::= { modemAlarm 3 }


modemAlarmLDPC OBJECT-TYPE
	SYNTAX  Alarm
	ACCESS  read-only
	STATUS  mandatory
	DESCRIPTION ""
	::= { modemAlarm 4 }


modemAlarmLock OBJECT-TYPE
	SYNTAX  Alarm
	ACCESS  read-only
	STATUS  mandatory
	DESCRIPTION ""
	::= { modemAlarm 5 }


modemAlarmMicroController OBJECT-TYPE
	SYNTAX  Alarm
	ACCESS  read-only
	STATUS  mandatory
	DESCRIPTION ""
	::= { modemAlarm 6 }


modemConfig OBJECT IDENTIFIER 	::= { modem 3 }

modemConfigOffline OBJECT IDENTIFIER 	::= { modemConfig 1 }

modemConfigOfflineTemperature OBJECT IDENTIFIER 	::= { modemConfigOffline 1 }

modemConfigOfflineTemperatureWarning OBJECT-TYPE
	SYNTAX  Temperature
	ACCESS  read-write
	STATUS  mandatory
	DESCRIPTION ""
	::= { modemConfigOfflineTemperature 1 }


modemConfigOfflineTemperatureAlarm OBJECT-TYPE
	SYNTAX  Temperature
	ACCESS  read-write
	STATUS  mandatory
	DESCRIPTION ""
	::= { modemConfigOfflineTemperature 2 }


modemConfigOfflineHwOption OBJECT-TYPE
	SYNTAX  INTEGER {
			rx(1),
			tx(2),
			bidi(3),
			modemOnly(4) }
	ACCESS  read-only
	STATUS  mandatory
	DESCRIPTION ""
	::= { modemConfigOffline 2 }


modemConfigOfflinePVGProfile OBJECT-TYPE
	SYNTAX  INTEGER (1..16)
	ACCESS  read-write
	STATUS  mandatory
	DESCRIPTION ""
	::= { modemConfigOffline 3 }


modemConfigOfflineTransmitterMode OBJECT-TYPE
	SYNTAX  INTEGER {
			normal(1),
			onetone(2),
			twotone(3),
			mute(4) }
	ACCESS  read-write
	STATUS  mandatory
	DESCRIPTION ""
	::= { modemConfigOffline 4 }


modemConfigOfflinePredistortion OBJECT-TYPE
	SYNTAX  Enable
	ACCESS  read-write
	STATUS  mandatory
	DESCRIPTION ""
	::= { modemConfigOffline 5 }


modemConfigOfflineXPIC OBJECT-TYPE
	SYNTAX  Enable
	ACCESS  read-write
	STATUS  mandatory
	DESCRIPTION ""
	::= { modemConfigOffline 6 }


modemConfigOfflineConfigurationInUse OBJECT-TYPE
	SYNTAX  INTEGER
	ACCESS  read-only
	STATUS  mandatory
	DESCRIPTION ""
	::= { modemConfigOffline 7 }


modemConfigRunning OBJECT IDENTIFIER 	::= { modemConfig 2 }

modemConfigRunningTemperature OBJECT IDENTIFIER 	::= { modemConfigRunning 1 }

modemConfigRunningTemperatureWarning OBJECT-TYPE
	SYNTAX  Temperature
	ACCESS  read-write
	STATUS  mandatory
	DESCRIPTION ""
	::= { modemConfigRunningTemperature 1 }


modemConfigRunningTemperatureAlarm OBJECT-TYPE
	SYNTAX  Temperature
	ACCESS  read-write
	STATUS  mandatory
	DESCRIPTION ""
	::= { modemConfigRunningTemperature 2 }


modemConfigRunningHwOption OBJECT-TYPE
	SYNTAX  INTEGER {
			rx(1),
			tx(2),
			bidi(3),
			modemOnly(4) }
	ACCESS  read-only
	STATUS  mandatory
	DESCRIPTION ""
	::= { modemConfigRunning 2 }


modemConfigRunningPVGProfile OBJECT-TYPE
	SYNTAX  INTEGER (1..16)
	ACCESS  read-write
	STATUS  mandatory
	DESCRIPTION ""
	::= { modemConfigRunning 3 }


modemConfigRunningTransmitterMode OBJECT-TYPE
	SYNTAX  INTEGER {
			normal(1),
			onetone(2),
			twotone(3),
			mute(4) }
	ACCESS  read-write
	STATUS  mandatory
	DESCRIPTION ""
	::= { modemConfigRunning 4 }


modemConfigRunningPredistortion OBJECT-TYPE
	SYNTAX  Enable
	ACCESS  read-write
	STATUS  mandatory
	DESCRIPTION ""
	::= { modemConfigRunning 5 }


modemConfigRunningXPIC OBJECT-TYPE
	SYNTAX  Enable
	ACCESS  read-write
	STATUS  mandatory
	DESCRIPTION ""
	::= { modemConfigRunning 6 }


modemConfigRunningConfigurationInUse OBJECT-TYPE
	SYNTAX  INTEGER
	ACCESS  read-only
	STATUS  mandatory
	DESCRIPTION ""
	::= { modemConfigRunning 7 }


interfaces OBJECT IDENTIFIER 	::= { modules 2 }

interfacesStatus OBJECT IDENTIFIER 	::= { interfaces 1 }

interfacesStatusAlarmASIE1 OBJECT-TYPE
	SYNTAX  SEQUENCE OF InterfacesStatusASIE1Entry
	ACCESS  not-accessible
	STATUS  mandatory
	DESCRIPTION ""
	::= { interfacesStatus 1 }


interfacesStatusASIE1Entry OBJECT-TYPE
	SYNTAX  InterfacesStatusASIE1Entry
	ACCESS  not-accessible
	STATUS  mandatory
	DESCRIPTION ""
	INDEX {
		interfacesStatusASIE1Index }
	::= { interfacesStatusAlarmASIE1 1 }


InterfacesStatusASIE1Entry ::= SEQUENCE {

	interfacesStatusASIE1Index          INTEGER,
	interfacesStatusASIE1BNC            OCTET STRING,
	interfacesStatusASIE1Direction      INTEGER,
	interfacesStatusASIE1Map            INTEGER,
	interfacesStatusASIE1PacketLenght   INTEGER,
	interfacesStatusASIE1SignalPresence Boolean,
	interfacesStatusASIE1Locked         Boolean,
	interfacesStatusASIE1TimingError    Error,
	interfacesStatusASIE1OverflowError  Error,
	interfacesStatusASIE1UnderflowError Error,
	interfacesStatusASIE1Bitrate        INTEGER }


interfacesStatusASIE1Index OBJECT-TYPE
	SYNTAX  INTEGER (1..10)
	ACCESS  read-only
	STATUS  mandatory
	DESCRIPTION ""
	::= { interfacesStatusASIE1Entry 1 }


interfacesStatusASIE1BNC OBJECT-TYPE
	SYNTAX  OCTET STRING
	ACCESS  read-only
	STATUS  mandatory
	DESCRIPTION ""
	::= { interfacesStatusASIE1Entry 2 }


interfacesStatusASIE1Direction OBJECT-TYPE
	SYNTAX  INTEGER {
			input(1),
			output(2),
			disabled(3) }
	ACCESS  read-only
	STATUS  mandatory
	DESCRIPTION ""
	::= { interfacesStatusASIE1Entry 3 }


interfacesStatusASIE1Map OBJECT-TYPE
	SYNTAX  INTEGER
	ACCESS  read-only
	STATUS  mandatory
	DESCRIPTION ""
	::= { interfacesStatusASIE1Entry 4 }


interfacesStatusASIE1PacketLenght OBJECT-TYPE
	SYNTAX  INTEGER {
			asi188(1),
			asi204(2),
			e1(3) }
	ACCESS  read-only
	STATUS  mandatory
	DESCRIPTION ""
	::= { interfacesStatusASIE1Entry 5 }


interfacesStatusASIE1SignalPresence OBJECT-TYPE
	SYNTAX  Boolean
	ACCESS  read-only
	STATUS  mandatory
	DESCRIPTION ""
	::= { interfacesStatusASIE1Entry 6 }


interfacesStatusASIE1Locked OBJECT-TYPE
	SYNTAX  Boolean
	ACCESS  read-only
	STATUS  mandatory
	DESCRIPTION ""
	::= { interfacesStatusASIE1Entry 7 }


interfacesStatusASIE1TimingError OBJECT-TYPE
	SYNTAX  Error
	ACCESS  read-only
	STATUS  mandatory
	DESCRIPTION ""
	::= { interfacesStatusASIE1Entry 8 }


interfacesStatusASIE1OverflowError OBJECT-TYPE
	SYNTAX  Error
	ACCESS  read-only
	STATUS  mandatory
	DESCRIPTION ""
	::= { interfacesStatusASIE1Entry 9 }


interfacesStatusASIE1UnderflowError OBJECT-TYPE
	SYNTAX  Error
	ACCESS  read-only
	STATUS  mandatory
	DESCRIPTION ""
	::= { interfacesStatusASIE1Entry 10 }


interfacesStatusASIE1Bitrate OBJECT-TYPE
	SYNTAX  INTEGER
	ACCESS  read-only
	STATUS  mandatory
	DESCRIPTION
		"Bitarate in Kbps"
	::= { interfacesStatusASIE1Entry 11 }


interfacesStatusEthernet OBJECT IDENTIFIER 	::= { interfacesStatus 2 }

interfaceStatusEthernetAutoNegotiation OBJECT-TYPE
	SYNTAX  INTEGER {
			inprogress(1),
			locked(2) }
	ACCESS  read-only
	STATUS  mandatory
	DESCRIPTION ""
	::= { interfacesStatusEthernet 1 }


interfaceStatusEthernetMDIMDXcrossover OBJECT-TYPE
	SYNTAX  INTEGER {
			notcrossed(1),
			crossed(2) }
	ACCESS  read-only
	STATUS  mandatory
	DESCRIPTION ""
	::= { interfacesStatusEthernet 2 }


interfaceStatusEthernetcdpair OBJECT-TYPE
	SYNTAX  EthPolaritySwap
	ACCESS  read-only
	STATUS  mandatory
	DESCRIPTION ""
	::= { interfacesStatusEthernet 3 }


interfaceStatusEthernetApair OBJECT-TYPE
	SYNTAX  EthPolaritySwap
	ACCESS  read-only
	STATUS  mandatory
	DESCRIPTION ""
	::= { interfacesStatusEthernet 4 }


interfaceStatusEthernetBpair OBJECT-TYPE
	SYNTAX  EthPolaritySwap
	ACCESS  read-only
	STATUS  mandatory
	DESCRIPTION ""
	::= { interfacesStatusEthernet 5 }


interfaceStatusEthernetCpair OBJECT-TYPE
	SYNTAX  EthPolaritySwap
	ACCESS  read-only
	STATUS  mandatory
	DESCRIPTION ""
	::= { interfacesStatusEthernet 6 }


interfaceStatusEthernetDpair OBJECT-TYPE
	SYNTAX  EthPolaritySwap
	ACCESS  read-only
	STATUS  mandatory
	DESCRIPTION ""
	::= { interfacesStatusEthernet 7 }


interfaceStatusEthernetDuplex OBJECT-TYPE
	SYNTAX  INTEGER {
			halfduplex(1),
			fullduplex(2) }
	ACCESS  read-only
	STATUS  mandatory
	DESCRIPTION ""
	::= { interfacesStatusEthernet 8 }


interfaceStatusEthernetSpeed OBJECT-TYPE
	SYNTAX  INTEGER {
			speed10baset(1),
			speed100basetx(2),
			speed1000baset(3) }
	ACCESS  read-only
	STATUS  mandatory
	DESCRIPTION ""
	::= { interfacesStatusEthernet 9 }


interfaceStatusEthernetInputDatarate OBJECT-TYPE
	SYNTAX  INTEGER
	ACCESS  read-only
	STATUS  mandatory
	DESCRIPTION ""
	::= { interfacesStatusEthernet 10 }


interfaceStatusEthernetOutputDatarate OBJECT-TYPE
	SYNTAX  INTEGER
	ACCESS  read-only
	STATUS  mandatory
	DESCRIPTION ""
	::= { interfacesStatusEthernet 11 }


interfaceStatusEthernetLock OBJECT-TYPE
	SYNTAX  INTEGER {
			locked(1),
			unlocked(2) }
	ACCESS  read-only
	STATUS  mandatory
	DESCRIPTION ""
	::= { interfacesStatusEthernet 12 }


interfacesAlarm OBJECT IDENTIFIER 	::= { interfaces 2 }

interfaceAlarmEthernetOverflow OBJECT-TYPE
	SYNTAX  Alarm
	ACCESS  read-only
	STATUS  mandatory
	DESCRIPTION ""
	::= { interfacesAlarm 1 }


interfaceAlarmEthernetPauseReceived OBJECT-TYPE
	SYNTAX  Alarm
	ACCESS  read-only
	STATUS  mandatory
	DESCRIPTION ""
	::= { interfacesAlarm 2 }


interfaceAlarmEthernetPauseTransmitted OBJECT-TYPE
	SYNTAX  Alarm
	ACCESS  read-only
	STATUS  mandatory
	DESCRIPTION ""
	::= { interfacesAlarm 3 }


interfaceAlarmFPGA OBJECT-TYPE
	SYNTAX  Alarm
	ACCESS  read-only
	STATUS  mandatory
	DESCRIPTION ""
	::= { interfacesAlarm 4 }


interfacesConfig OBJECT IDENTIFIER 	::= { interfaces 3 }

interfacesConfigOffline OBJECT IDENTIFIER 	::= { interfacesConfig 1 }

interfacesConfigOfflineASIE1 OBJECT-TYPE
	SYNTAX  SEQUENCE OF InterfacesConfigOfflineASIE1Entry
	ACCESS  not-accessible
	STATUS  mandatory
	DESCRIPTION ""
	::= { interfacesConfigOffline 1 }


interfacesConfigOfflineASIE1Entry OBJECT-TYPE
	SYNTAX  InterfacesConfigOfflineASIE1Entry
	ACCESS  not-accessible
	STATUS  mandatory
	DESCRIPTION ""
	INDEX {
		interfacesConfigOfflineASIE1Index }
	::= { interfacesConfigOfflineASIE1 1 }


InterfacesConfigOfflineASIE1Entry ::= SEQUENCE {

	interfacesConfigOfflineASIE1Index        INTEGER,
	interfacesConfigOfflineASIE1BNC          OCTET STRING,
	interfacesConfigOfflineASIE1Enable       Enable,
	interfacesConfigOfflineInOut             INTEGER,
	interfacesConfigOfflineASIE1InputMapper  INTEGER,
	interfacesConfigOfflineASIE1OutputMapper INTEGER }


interfacesConfigOfflineASIE1Index OBJECT-TYPE
	SYNTAX  INTEGER (1..10)
	ACCESS  read-only
	STATUS  mandatory
	DESCRIPTION ""
	::= { interfacesConfigOfflineASIE1Entry 1 }


interfacesConfigOfflineASIE1Enable OBJECT-TYPE
	SYNTAX  Enable
	ACCESS  read-write
	STATUS  mandatory
	DESCRIPTION ""
	::= { interfacesConfigOfflineASIE1Entry 3 }


interfacesConfigOfflineInOut OBJECT-TYPE
	SYNTAX  INTEGER {
			input(1),
			output(2) }
	ACCESS  read-write
	STATUS  mandatory
	DESCRIPTION ""
	::= { interfacesConfigOfflineASIE1Entry 4 }


interfacesConfigOfflineASIE1InputMapper OBJECT-TYPE
	SYNTAX  INTEGER (1..20)
	ACCESS  read-write
	STATUS  mandatory
	DESCRIPTION
		"1-10 input id
		20 disabled"
	::= { interfacesConfigOfflineASIE1Entry 5 }


interfacesConfigOfflineASIE1OutputMapper OBJECT-TYPE
	SYNTAX  INTEGER (1..20)
	ACCESS  read-write
	STATUS  mandatory
	DESCRIPTION
		"1-10 output mapper
		20 disabled"
	::= { interfacesConfigOfflineASIE1Entry 6 }


interfacesConfigOfflineE1 OBJECT-TYPE
	SYNTAX  Enable
	ACCESS  read-write
	STATUS  mandatory
	DESCRIPTION ""
	::= { interfacesConfigOffline 2 }


interfacesConfigRunning OBJECT IDENTIFIER 	::= { interfacesConfig 2 }

interfacesConfigRunningASIE1 OBJECT-TYPE
	SYNTAX  SEQUENCE OF InterfacesConfigRunningASIE1Entry
	ACCESS  not-accessible
	STATUS  mandatory
	DESCRIPTION ""
	::= { interfacesConfigRunning 1 }


interfacesConfigRunningASIE1Entry OBJECT-TYPE
	SYNTAX  InterfacesConfigRunningASIE1Entry
	ACCESS  not-accessible
	STATUS  mandatory
	DESCRIPTION ""
	INDEX {
		interfacesConfigRunningASIE1Index }
	::= { interfacesConfigRunningASIE1 1 }


InterfacesConfigRunningASIE1Entry ::= SEQUENCE {

	interfacesConfigRunningASIE1Index        INTEGER,
	interfacesConfigRunningASIE1BNC          OCTET STRING,
	interfacesConfigRunningASIE1Enable       Enable,
	interfacesConfigRunningASIE1InOut        INTEGER,
	interfacesConfigRunningASIE1InputMapper  INTEGER,
	interfacesConfigRunningASIE1OutputMapper INTEGER }


interfacesConfigRunningASIE1Index OBJECT-TYPE
	SYNTAX  INTEGER (1..10)
	ACCESS  read-only
	STATUS  mandatory
	DESCRIPTION ""
	::= { interfacesConfigRunningASIE1Entry 1 }


reble610ModulesInfoVersion OBJECT-TYPE
	SYNTAX  OCTET STRING
	ACCESS  read-only
	STATUS  mandatory
	DESCRIPTION ""
	::= { reble610ModulesInfoEntry 3 }


reble610ModulesInfoNumber OBJECT-TYPE
	SYNTAX  OCTET STRING
	ACCESS  read-only
	STATUS  mandatory
	DESCRIPTION
		"Part Number or Sw/Fw Revision"
	::= { reble610ModulesInfoEntry 4 }


interfacesConfigOfflineASIE1BNC OBJECT-TYPE
	SYNTAX  OCTET STRING
	ACCESS  read-only
	STATUS  mandatory
	DESCRIPTION ""
	::= { interfacesConfigOfflineASIE1Entry 2 }


interfacesConfigRunningASIE1BNC OBJECT-TYPE
	SYNTAX  OCTET STRING
	ACCESS  read-only
	STATUS  mandatory
	DESCRIPTION ""
	::= { interfacesConfigRunningASIE1Entry 2 }


interfacesConfigRunningASIE1Enable OBJECT-TYPE
	SYNTAX  Enable
	ACCESS  read-write
	STATUS  mandatory
	DESCRIPTION ""
	::= { interfacesConfigRunningASIE1Entry 3 }


interfacesConfigRunningASIE1InOut OBJECT-TYPE
	SYNTAX  INTEGER {
			input(1),
			output(2) }
	ACCESS  read-write
	STATUS  mandatory
	DESCRIPTION ""
	::= { interfacesConfigRunningASIE1Entry 4 }


interfacesConfigRunningASIE1InputMapper OBJECT-TYPE
	SYNTAX  INTEGER (1..20)
	ACCESS  read-write
	STATUS  mandatory
	DESCRIPTION
		"1-10 input id
		20 disabled"
	::= { interfacesConfigRunningASIE1Entry 5 }


interfacesConfigRunningASIE1OutputMapper OBJECT-TYPE
	SYNTAX  INTEGER (1..20)
	ACCESS  read-write
	STATUS  mandatory
	DESCRIPTION
		"1-10 output mapper
		20 disabled"
	::= { interfacesConfigRunningASIE1Entry 6 }


interfacesConfigRunningE1 OBJECT-TYPE
	SYNTAX  Enable
	ACCESS  read-write
	STATUS  mandatory
	DESCRIPTION ""
	::= { interfacesConfigRunning 2 }


rx OBJECT IDENTIFIER 	::= { modules 3 }

rxStatus OBJECT IDENTIFIER 	::= { rx 1 }

rxStatusTemperature OBJECT-TYPE
	SYNTAX  Temperature
	ACCESS  read-only
	STATUS  mandatory
	DESCRIPTION ""
	::= { rxStatus 1 }


rxStatusRSSI OBJECT-TYPE
	SYNTAX  INTEGER (-100..0)
	ACCESS  read-only
	STATUS  mandatory
	DESCRIPTION ""
	::= { rxStatus 2 }


rxAlarm OBJECT IDENTIFIER 	::= { rx 2 }

rxAlarmTemperature OBJECT-TYPE
	SYNTAX  Alarm
	ACCESS  read-only
	STATUS  mandatory
	DESCRIPTION ""
	::= { rxAlarm 1 }


rxAlarmPll1Lock OBJECT-TYPE
	SYNTAX  Alarm
	ACCESS  read-only
	STATUS  mandatory
	DESCRIPTION ""
	::= { rxAlarm 2 }


rxAlarmPll2Lock OBJECT-TYPE
	SYNTAX  Alarm
	ACCESS  read-only
	STATUS  mandatory
	DESCRIPTION ""
	::= { rxAlarm 3 }


rxAlarmField OBJECT-TYPE
	SYNTAX  INTEGER {
			noalarm(1),
			toohigh(2),
			toolow(3) }
	ACCESS  read-only
	STATUS  mandatory
	DESCRIPTION ""
	::= { rxAlarm 4 }


rxConfig OBJECT IDENTIFIER 	::= { rx 3 }

rxConfigOffline OBJECT IDENTIFIER 	::= { rxConfig 1 }

rxConfigOfflineTemperature OBJECT IDENTIFIER 	::= { rxConfigOffline 1 }

rxConfigOfflineTemperatureWarning OBJECT-TYPE
	SYNTAX  Temperature
	ACCESS  read-write
	STATUS  mandatory
	DESCRIPTION ""
	::= { rxConfigOfflineTemperature 1 }


rxConfigOfflineTemperatureAlarm OBJECT-TYPE
	SYNTAX  Temperature
	ACCESS  read-write
	STATUS  mandatory
	DESCRIPTION ""
	::= { rxConfigOfflineTemperature 2 }


rxConfigOfflineFrequency OBJECT-TYPE
	SYNTAX  INTEGER
	ACCESS  read-write
	STATUS  mandatory
	DESCRIPTION
		"in KHz"
	::= { rxConfigOffline 2 }


rxConfigOfflineFrequencyMin OBJECT-TYPE
	SYNTAX  INTEGER
	ACCESS  read-only
	STATUS  mandatory
	DESCRIPTION
		"in KHz"
	::= { rxConfigOffline 3 }


rxConfigRunning OBJECT IDENTIFIER 	::= { rxConfig 2 }

rxConfigRunningTemperature OBJECT IDENTIFIER 	::= { rxConfigRunning 1 }

rxConfigRunningTemperatureWarning OBJECT-TYPE
	SYNTAX  Temperature
	ACCESS  read-write
	STATUS  mandatory
	DESCRIPTION ""
	::= { rxConfigRunningTemperature 1 }


rxConfigRunningTemperatureAlarm OBJECT-TYPE
	SYNTAX  Temperature
	ACCESS  read-write
	STATUS  mandatory
	DESCRIPTION ""
	::= { rxConfigRunningTemperature 2 }


rxConfigRunningFrequency OBJECT-TYPE
	SYNTAX  INTEGER
	ACCESS  read-write
	STATUS  mandatory
	DESCRIPTION
		"in KHz"
	::= { rxConfigRunning 2 }


rxConfigRunningFrequencyMin OBJECT-TYPE
	SYNTAX  INTEGER
	ACCESS  read-only
	STATUS  mandatory
	DESCRIPTION
		"in KHz"
	::= { rxConfigRunning 3 }


rxConfigOfflineFrequencyMax OBJECT-TYPE
	SYNTAX  INTEGER
	ACCESS  read-only
	STATUS  mandatory
	DESCRIPTION
		"in KHz"
	::= { rxConfigOffline 4 }


rxConfigRunningFrequencyMax OBJECT-TYPE
	SYNTAX  INTEGER
	ACCESS  read-only
	STATUS  mandatory
	DESCRIPTION
		"in KHz"
	::= { rxConfigRunning 4 }


tx OBJECT IDENTIFIER 	::= { modules 4 }

txStatus OBJECT IDENTIFIER 	::= { tx 1 }

txStatusTemperature OBJECT-TYPE
	SYNTAX  Temperature
	ACCESS  read-only
	STATUS  mandatory
	DESCRIPTION ""
	::= { txStatus 1 }


txStatusPower OBJECT-TYPE
	SYNTAX  Power
	ACCESS  read-only
	STATUS  mandatory
	DESCRIPTION
		"in tenth's of dBm"
	::= { txStatus 2 }


txAlarm OBJECT IDENTIFIER 	::= { tx 2 }

txAlarmTemperature OBJECT-TYPE
	SYNTAX  Alarm
	ACCESS  read-only
	STATUS  mandatory
	DESCRIPTION ""
	::= { txAlarm 1 }


txAlarmPll1Lock OBJECT-TYPE
	SYNTAX  Alarm
	ACCESS  read-only
	STATUS  mandatory
	DESCRIPTION ""
	::= { txAlarm 2 }


txAlarmPll2Lock OBJECT-TYPE
	SYNTAX  Alarm
	ACCESS  read-only
	STATUS  mandatory
	DESCRIPTION ""
	::= { txAlarm 3 }


txAlarmLowPower OBJECT-TYPE
	SYNTAX  Alarm
	ACCESS  read-only
	STATUS  mandatory
	DESCRIPTION ""
	::= { txAlarm 4 }


txConfig OBJECT IDENTIFIER 	::= { tx 3 }

txConfigOffline OBJECT IDENTIFIER 	::= { txConfig 1 }

txConfigOfflineTemperature OBJECT IDENTIFIER 	::= { txConfigOffline 1 }

txConfigOfflineTemperatureWarning OBJECT-TYPE
	SYNTAX  Temperature
	ACCESS  read-write
	STATUS  mandatory
	DESCRIPTION ""
	::= { txConfigOfflineTemperature 1 }


txConfigOfflineTemperatureAlarm OBJECT-TYPE
	SYNTAX  Temperature
	ACCESS  read-write
	STATUS  mandatory
	DESCRIPTION ""
	::= { txConfigOfflineTemperature 2 }


txConfigOfflineFrequency OBJECT-TYPE
	SYNTAX  INTEGER
	ACCESS  read-write
	STATUS  mandatory
	DESCRIPTION
		"in KHz"
	::= { txConfigOffline 2 }


txConfigOfflineFrequencyMin OBJECT-TYPE
	SYNTAX  INTEGER
	ACCESS  read-only
	STATUS  mandatory
	DESCRIPTION
		"in KHz"
	::= { txConfigOffline 3 }


txConfigOfflineFrequencyMax OBJECT-TYPE
	SYNTAX  INTEGER
	ACCESS  read-only
	STATUS  mandatory
	DESCRIPTION
		"in KHz"
	::= { txConfigOffline 4 }


txConfigOfflineSquelch OBJECT-TYPE
	SYNTAX  Enable
	ACCESS  read-write
	STATUS  mandatory
	DESCRIPTION
		"in KHz"
	::= { txConfigOffline 5 }


txConfigOfflinePowerMngt OBJECT-TYPE
	SYNTAX  Power
	ACCESS  read-write
	STATUS  mandatory
	DESCRIPTION
		"in tenth's of dBm. Offset to be applied to calcultate
		              the requested output power.
		PWR=CALIBRATION_TARGET+MODULATION_OFFSET+txConfigOfflinePowerMngt"
	::= { txConfigOffline 6 }


txConfigRunning OBJECT IDENTIFIER 	::= { txConfig 2 }

txConfigRunningTemperature OBJECT IDENTIFIER 	::= { txConfigRunning 1 }

txConfigRunningTemperatureWarning OBJECT-TYPE
	SYNTAX  Temperature
	ACCESS  read-write
	STATUS  mandatory
	DESCRIPTION ""
	::= { txConfigRunningTemperature 1 }


txConfigRunningTemperatureAlarm OBJECT-TYPE
	SYNTAX  Temperature
	ACCESS  read-write
	STATUS  mandatory
	DESCRIPTION ""
	::= { txConfigRunningTemperature 2 }


txConfigRunningFrequency OBJECT-TYPE
	SYNTAX  INTEGER
	ACCESS  read-write
	STATUS  mandatory
	DESCRIPTION
		"in KHz"
	::= { txConfigRunning 2 }


txConfigRunningFrequencyMin OBJECT-TYPE
	SYNTAX  INTEGER
	ACCESS  read-only
	STATUS  mandatory
	DESCRIPTION
		"in KHz"
	::= { txConfigRunning 3 }


txConfigRunningFrequencyMax OBJECT-TYPE
	SYNTAX  INTEGER
	ACCESS  read-only
	STATUS  mandatory
	DESCRIPTION
		"in KHz"
	::= { txConfigRunning 4 }


txConfigRunningSquelch OBJECT-TYPE
	SYNTAX  Enable
	ACCESS  read-write
	STATUS  mandatory
	DESCRIPTION
		"in KHz"
	::= { txConfigRunning 5 }


txConfigRunningPowerMngt OBJECT-TYPE
	SYNTAX  Power
	ACCESS  read-write
	STATUS  mandatory
	DESCRIPTION
		"in tenth's of dBm. Offset to be applied to calcultate
		              the requested output power.
		PWR=CALIBRATION_TARGET+MODULATION_OFFSET+txConfigOfflinePowerMngt"
	::= { txConfigRunning 6 }


controller OBJECT IDENTIFIER 	::= { modules 5 }

controllerStatus OBJECT IDENTIFIER 	::= { controller 1 }

controllerStatusPSU OBJECT IDENTIFIER 	::= { controllerStatus 1 }

controllerStatusPSUSecondaryVoltage OBJECT-TYPE
	SYNTAX  Voltage
	ACCESS  read-only
	STATUS  mandatory
	DESCRIPTION
		"12 volt"
	::= { controllerStatusPSU 3 }


controllerStatusPSUPrimaryVoltage OBJECT-TYPE
	SYNTAX  Voltage
	ACCESS  read-only
	STATUS  mandatory
	DESCRIPTION
		"12 volt"
	::= { controllerStatusPSU 1 }


controllerStatusPSUPrimaryType OBJECT-TYPE
	SYNTAX  INTEGER {
			acdc(1),
			dcdc(2),
			notpresent(3) }
	ACCESS  read-only
	STATUS  mandatory
	DESCRIPTION ""
	::= { controllerStatusPSU 2 }


controllerStatusPSUSecondaryType OBJECT-TYPE
	SYNTAX  INTEGER {
			acdc(1),
			dcdc(2),
			notpresent(3) }
	ACCESS  read-only
	STATUS  mandatory
	DESCRIPTION ""
	::= { controllerStatusPSU 4 }


controllerStatusPSUVoltage3 OBJECT-TYPE
	SYNTAX  Voltage
	ACCESS  read-only
	STATUS  mandatory
	DESCRIPTION
		"6 Volt"
	::= { controllerStatusPSU 6 }


controllerStatusPSUVoltage2 OBJECT-TYPE
	SYNTAX  Voltage
	ACCESS  read-only
	STATUS  mandatory
	DESCRIPTION
		"5 Volt"
	::= { controllerStatusPSU 5 }


controllerStatusFans OBJECT IDENTIFIER 	::= { controllerStatus 2 }

controllerStatusFanRF OBJECT-TYPE
	SYNTAX  INTEGER
	ACCESS  read-only
	STATUS  mandatory
	DESCRIPTION ""
	::= { controllerStatusFans 1 }


controllerStatusFanModem OBJECT-TYPE
	SYNTAX  INTEGER
	ACCESS  read-only
	STATUS  mandatory
	DESCRIPTION ""
	::= { controllerStatusFans 2 }


controllerStatusFanPSU1 OBJECT-TYPE
	SYNTAX  INTEGER
	ACCESS  read-only
	STATUS  mandatory
	DESCRIPTION ""
	::= { controllerStatusFans 3 }


controllerStatusFanPSU2 OBJECT-TYPE
	SYNTAX  INTEGER
	ACCESS  read-only
	STATUS  mandatory
	DESCRIPTION ""
	::= { controllerStatusFans 4 }


controllerAlarm OBJECT IDENTIFIER 	::= { controller 2 }

controllerAlarmPrimaryVoltage OBJECT-TYPE
	SYNTAX  Alarm
	ACCESS  read-only
	STATUS  mandatory
	DESCRIPTION ""
	::= { controllerAlarm 1 }


controllerAlarmSecondaryVoltage OBJECT-TYPE
	SYNTAX  Alarm
	ACCESS  read-only
	STATUS  mandatory
	DESCRIPTION ""
	::= { controllerAlarm 2 }


controllerAlarmVoltage2 OBJECT-TYPE
	SYNTAX  Alarm
	ACCESS  read-only
	STATUS  mandatory
	DESCRIPTION ""
	::= { controllerAlarm 3 }


controllerAlarmVoltage3 OBJECT-TYPE
	SYNTAX  Alarm
	ACCESS  read-only
	STATUS  mandatory
	DESCRIPTION ""
	::= { controllerAlarm 4 }


controllerAlarmFanRF OBJECT-TYPE
	SYNTAX  Alarm
	ACCESS  read-only
	STATUS  mandatory
	DESCRIPTION ""
	::= { controllerAlarm 5 }


controllerAlarmFanModem OBJECT-TYPE
	SYNTAX  Alarm
	ACCESS  read-only
	STATUS  mandatory
	DESCRIPTION ""
	::= { controllerAlarm 6 }


controllerAlarmFanPSU1 OBJECT-TYPE
	SYNTAX  Alarm
	ACCESS  read-only
	STATUS  mandatory
	DESCRIPTION ""
	::= { controllerAlarm 7 }


controllerAlarmFanPSU2 OBJECT-TYPE
	SYNTAX  Alarm
	ACCESS  read-only
	STATUS  mandatory
	DESCRIPTION ""
	::= { controllerAlarm 8 }


controllerConfig OBJECT IDENTIFIER 	::= { controller 3 }

controllerConfigFan OBJECT IDENTIFIER 	::= { controllerConfig 1 }

controllerConfigRFFanManual OBJECT-TYPE
	SYNTAX  Enable
	ACCESS  read-write
	STATUS  mandatory
	DESCRIPTION ""
	::= { controllerConfigFan 1 }


controllerConfigRFFanSpeed OBJECT-TYPE
	SYNTAX  INTEGER
	ACCESS  read-write
	STATUS  mandatory
	DESCRIPTION ""
	::= { controllerConfigFan 2 }


controllerConfigRFFanTemperatureTarget OBJECT-TYPE
	SYNTAX  INTEGER
	ACCESS  read-write
	STATUS  mandatory
	DESCRIPTION ""
	::= { controllerConfigFan 3 }


controllerConfigModemFanManual OBJECT-TYPE
	SYNTAX  Enable
	ACCESS  read-write
	STATUS  mandatory
	DESCRIPTION ""
	::= { controllerConfigFan 4 }


controllerConfigModemFanSpeed OBJECT-TYPE
	SYNTAX  INTEGER
	ACCESS  read-write
	STATUS  mandatory
	DESCRIPTION ""
	::= { controllerConfigFan 5 }


controllerConfigModemFanTemperatureTarget OBJECT-TYPE
	SYNTAX  INTEGER
	ACCESS  read-write
	STATUS  mandatory
	DESCRIPTION ""
	::= { controllerConfigFan 6 }


controllerConfigNetwork OBJECT IDENTIFIER 	::= { controllerConfig 2 }

controllerConfigNetworkIpAddress OBJECT-TYPE
	SYNTAX  OCTET STRING
	ACCESS  read-write
	STATUS  mandatory
	DESCRIPTION ""
	::= { controllerConfigNetwork 1 }


controllerConfigNetworkNetMask OBJECT-TYPE
	SYNTAX  OCTET STRING
	ACCESS  read-write
	STATUS  mandatory
	DESCRIPTION ""
	::= { controllerConfigNetwork 2 }


controllerConfigNetworkGateway OBJECT-TYPE
	SYNTAX  OCTET STRING
	ACCESS  read-write
	STATUS  mandatory
	DESCRIPTION ""
	::= { controllerConfigNetwork 3 }


controllerConfigMAC OBJECT-TYPE
	SYNTAX  OCTET STRING
	ACCESS  read-only
	STATUS  mandatory
	DESCRIPTION ""
	::= { controllerConfigNetwork 4 }


controllerConfigDateTime OBJECT-TYPE
	SYNTAX  OCTET STRING
	ACCESS  read-write
	STATUS  mandatory
	DESCRIPTION ""
	::= { controllerConfig 3 }


controllerConfigResetSlot OBJECT-TYPE
	SYNTAX  Boolean
	ACCESS  read-write
	STATUS  mandatory
	DESCRIPTION ""
	::= { controllerConfig 4 }


controllerConfigResetController OBJECT-TYPE
	SYNTAX  Boolean
	ACCESS  read-write
	STATUS  mandatory
	DESCRIPTION ""
	::= { controllerConfig 5 }


controllerConfigResetSystem OBJECT-TYPE
	SYNTAX  Boolean
	ACCESS  read-write
	STATUS  mandatory
	DESCRIPTION ""
	::= { controllerConfig 6 }


controllerConfigNetworkApply OBJECT-TYPE
	SYNTAX  Boolean
	ACCESS  read-write
	STATUS  mandatory
	DESCRIPTION ""
	::= { controllerConfigNetwork 5 }


odu OBJECT IDENTIFIER 	::= { modules 6 }

localCommunicationInterface OBJECT IDENTIFIER 	::= { odu 1 }

localCommunicationInterfaceStatus OBJECT IDENTIFIER 	::= { localCommunicationInterface 1 }

localBer OBJECT-TYPE
	SYNTAX  INTEGER
	ACCESS  read-only
	STATUS  mandatory
	DESCRIPTION
		"10E-8"
	::= { localCommunicationInterfaceStatus 1 }


remoteBer OBJECT-TYPE
	SYNTAX  INTEGER
	ACCESS  read-only
	STATUS  mandatory
	DESCRIPTION
		"10E-8"
	::= { localCommunicationInterfaceStatus 2 }


localFpgaTemperature OBJECT-TYPE
	SYNTAX  Temperature
	ACCESS  read-only
	STATUS  mandatory
	DESCRIPTION
		""
	::= { localCommunicationInterfaceStatus 3 }


stepupTemperature OBJECT-TYPE
	SYNTAX  Temperature
	ACCESS  read-only
	STATUS  mandatory
	DESCRIPTION ""
	::= { localCommunicationInterfaceStatus 4 }


stepupVoltagePreSwitch OBJECT-TYPE
	SYNTAX  Voltage
	ACCESS  read-only
	STATUS  mandatory
	DESCRIPTION
		""
	::= { localCommunicationInterfaceStatus 5 }


stepupVoltagePostSwitch OBJECT-TYPE
	SYNTAX  Voltage
	ACCESS  read-only
	STATUS  mandatory
	DESCRIPTION ""
	::= { localCommunicationInterfaceStatus 6 }


stepUpCurrent OBJECT-TYPE
	SYNTAX  INTEGER
	ACCESS  read-only
	STATUS  mandatory
	DESCRIPTION
		""
	::= { localCommunicationInterfaceStatus 7 }


localCommunicationInterfaceAlarm OBJECT IDENTIFIER 	::= { localCommunicationInterface 2 }

localRSDecode OBJECT-TYPE
	SYNTAX  Alarm
	ACCESS  read-only
	STATUS  mandatory
	DESCRIPTION
		""
	::= { localCommunicationInterfaceAlarm 1 }


localDeframerLock OBJECT-TYPE
	SYNTAX  Alarm
	ACCESS  read-only
	STATUS  mandatory
	DESCRIPTION ""
	::= { localCommunicationInterfaceAlarm 2 }


localVCXOLock OBJECT-TYPE
	SYNTAX  Alarm
	ACCESS  read-only
	STATUS  mandatory
	DESCRIPTION ""
	::= { localCommunicationInterfaceAlarm 3 }


localGTPPllLock OBJECT-TYPE
	SYNTAX  Alarm
	ACCESS  read-only
	STATUS  mandatory
	DESCRIPTION
		""
	::= { localCommunicationInterfaceAlarm 4 }


localSFPLoss OBJECT-TYPE
	SYNTAX  Alarm
	ACCESS  read-only
	STATUS  mandatory
	DESCRIPTION
		""
	::= { localCommunicationInterfaceAlarm 5 }


localSFPTxFault OBJECT-TYPE
	SYNTAX  Alarm
	ACCESS  read-only
	STATUS  mandatory
	DESCRIPTION
		""
	::= { localCommunicationInterfaceAlarm 6 }


localCommunicationInterfaceConfig OBJECT IDENTIFIER 	::= { localCommunicationInterface 3 }

localCommunicationInterfaceFpgaTemperature OBJECT IDENTIFIER 	::= { localCommunicationInterfaceConfig 1 }

localCommunicationInterfaceStepUpTemperature OBJECT IDENTIFIER 	::= { localCommunicationInterfaceConfig 2 }

localCommunicationInterfaceConfigTurnOn OBJECT-TYPE
	SYNTAX  Boolean
	ACCESS  read-write
	STATUS  mandatory
	DESCRIPTION
		""
	::= { localCommunicationInterfaceConfig 3 }


remoteCommunicationInterface OBJECT IDENTIFIER 	::= { odu 2 }

remoteCommunicationInterfaceStatus OBJECT IDENTIFIER 	::= { remoteCommunicationInterface 1 }

remoteCommunicationInterfaceTemperature OBJECT-TYPE
	SYNTAX  Temperature
	ACCESS  read-only
	STATUS  mandatory
	DESCRIPTION
		""
	::= { remoteCommunicationInterfaceStatus 1 }


remoteCommunicationInterfaceVoltage1 OBJECT-TYPE
	SYNTAX  Temperature
	ACCESS  read-only
	STATUS  mandatory
	DESCRIPTION
		""
	::= { remoteCommunicationInterfaceStatus 2 }


remoteCommunicationInterfaceVoltage2 OBJECT-TYPE
	SYNTAX  Voltage
	ACCESS  read-only
	STATUS  mandatory
	DESCRIPTION
		""
	::= { remoteCommunicationInterfaceStatus 3 }


remoteCommunicationInterfaceAlarm OBJECT IDENTIFIER 	::= { remoteCommunicationInterface 2 }

remoteCommunicationInterfaceConfig OBJECT IDENTIFIER 	::= { remoteCommunicationInterface 3 }

trap OBJECT IDENTIFIER 	::= { reble610 3 }

trapPriority OBJECT-TYPE
	SYNTAX  INTEGER
	ACCESS  read-only
	STATUS  mandatory
	DESCRIPTION ""
	::= { trap 1 }


trapMessage OBJECT-TYPE
	SYNTAX  OCTET STRING
	ACCESS  read-only
	STATUS  mandatory
	DESCRIPTION ""
	::= { trap 2 }


trapCounter OBJECT-TYPE
	SYNTAX  INTEGER
	ACCESS  read-only
	STATUS  mandatory
	DESCRIPTION ""
	::= { trap 3 }


trapModemAlarm OBJECT IDENTIFIER 	::= { trap 4 }

trapControllerAlarm OBJECT IDENTIFIER 	::= { trap 14 }

trapModemAlarmTemperature OBJECT-TYPE
	SYNTAX  TrapAlarm
	ACCESS  read-only
	STATUS  mandatory
	DESCRIPTION ""
	::= { trapModemAlarm 1 }


trapModemAlarmMSE OBJECT-TYPE
	SYNTAX  TrapAlarm
	ACCESS  read-only
	STATUS  mandatory
	DESCRIPTION ""
	::= { trapModemAlarm 2 }


trapModemAlarmTiming OBJECT-TYPE
	SYNTAX  TrapAlarm
	ACCESS  read-only
	STATUS  mandatory
	DESCRIPTION ""
	::= { trapModemAlarm 3 }


trapModemAlarmLDPC OBJECT-TYPE
	SYNTAX  TrapAlarm
	ACCESS  read-only
	STATUS  mandatory
	DESCRIPTION ""
	::= { trapModemAlarm 4 }


trapModemAlarmLock OBJECT-TYPE
	SYNTAX  TrapAlarm
	ACCESS  read-only
	STATUS  mandatory
	DESCRIPTION ""
	::= { trapModemAlarm 5 }


trapModemAlarmMicroController OBJECT-TYPE
	SYNTAX  TrapAlarm
	ACCESS  read-only
	STATUS  mandatory
	DESCRIPTION ""
	::= { trapModemAlarm 6 }


trapInterfacesAlarm OBJECT IDENTIFIER 	::= { trap 5 }

trapInterfaceAlarmEthernetOverflow OBJECT-TYPE
	SYNTAX  TrapAlarm
	ACCESS  read-only
	STATUS  mandatory
	DESCRIPTION ""
	::= { trapInterfacesAlarm 2 }


trapInterfaceAlarmEthernetPauseReceived OBJECT-TYPE
	SYNTAX  TrapAlarm
	ACCESS  read-only
	STATUS  mandatory
	DESCRIPTION ""
	::= { trapInterfacesAlarm 3 }


trapInterfaceAlarmEthernetPauseTransmitted OBJECT-TYPE
	SYNTAX  TrapAlarm
	ACCESS  read-only
	STATUS  mandatory
	DESCRIPTION ""
	::= { trapInterfacesAlarm 4 }


trapInterfaceAlarmEthernetLock OBJECT-TYPE
	SYNTAX  TrapAlarm
	ACCESS  read-only
	STATUS  mandatory
	DESCRIPTION ""
	::= { trapInterfacesAlarm 1 }


trapInterfaceAlarmFPGA OBJECT-TYPE
	SYNTAX  TrapAlarm
	ACCESS  read-only
	STATUS  mandatory
	DESCRIPTION ""
	::= { trapInterfacesAlarm 5 }


trapInterfaceAlarmAsi OBJECT-TYPE
	SYNTAX  TrapAlarm
	ACCESS  read-only
	STATUS  mandatory
	DESCRIPTION
		"Generic ASI(E1 error, the error type id in the description trap field"
	::= { trapInterfacesAlarm 6 }


trapRxAlarm OBJECT IDENTIFIER 	::= { trap 6 }

trapRxAlarmTemperature OBJECT-TYPE
	SYNTAX  TrapAlarm
	ACCESS  read-only
	STATUS  mandatory
	DESCRIPTION ""
	::= { trapRxAlarm 1 }


trapRxAlarmPll1Lock OBJECT-TYPE
	SYNTAX  TrapAlarm
	ACCESS  read-only
	STATUS  mandatory
	DESCRIPTION ""
	::= { trapRxAlarm 2 }


trapRxAlarmPll2Lock OBJECT-TYPE
	SYNTAX  TrapAlarm
	ACCESS  read-only
	STATUS  mandatory
	DESCRIPTION ""
	::= { trapRxAlarm 3 }


trapRxAlarmField OBJECT-TYPE
	SYNTAX  TrapAlarm
	ACCESS  read-only
	STATUS  mandatory
	DESCRIPTION ""
	::= { trapRxAlarm 4 }


trapTxAlarm OBJECT IDENTIFIER 	::= { trap 7 }

trapTxAlarmTemperature OBJECT-TYPE
	SYNTAX  TrapAlarm
	ACCESS  read-only
	STATUS  mandatory
	DESCRIPTION ""
	::= { trapTxAlarm 1 }


trapTxAlarmPll1Lock OBJECT-TYPE
	SYNTAX  TrapAlarm
	ACCESS  read-only
	STATUS  mandatory
	DESCRIPTION ""
	::= { trapTxAlarm 2 }


trapTxAlarmPll2Lock OBJECT-TYPE
	SYNTAX  TrapAlarm
	ACCESS  read-only
	STATUS  mandatory
	DESCRIPTION ""
	::= { trapTxAlarm 3 }


trapTxAlarmLowPower OBJECT-TYPE
	SYNTAX  TrapAlarm
	ACCESS  read-only
	STATUS  mandatory
	DESCRIPTION ""
	::= { trapTxAlarm 4 }


trapListener OBJECT IDENTIFIER 	::= { trap 8 }

trapListener1 OBJECT-TYPE
	SYNTAX  OCTET STRING
	ACCESS  read-write
	STATUS  mandatory
	DESCRIPTION ""
	::= { trapListener 1 }


trapListener2 OBJECT-TYPE
	SYNTAX  OCTET STRING
	ACCESS  read-write
	STATUS  mandatory
	DESCRIPTION ""
	::= { trapListener 2 }


trapListener3 OBJECT-TYPE
	SYNTAX  OCTET STRING
	ACCESS  read-write
	STATUS  mandatory
	DESCRIPTION ""
	::= { trapListener 3 }


trapListener4 OBJECT-TYPE
	SYNTAX  OCTET STRING
	ACCESS  read-write
	STATUS  mandatory
	DESCRIPTION ""
	::= { trapListener 4 }


trapListener5 OBJECT-TYPE
	SYNTAX  OCTET STRING
	ACCESS  read-write
	STATUS  mandatory
	DESCRIPTION ""
	::= { trapListener 5 }


trapListener6 OBJECT-TYPE
	SYNTAX  OCTET STRING
	ACCESS  read-write
	STATUS  mandatory
	DESCRIPTION ""
	::= { trapListener 6 }


trapListener7 OBJECT-TYPE
	SYNTAX  OCTET STRING
	ACCESS  read-write
	STATUS  mandatory
	DESCRIPTION ""
	::= { trapListener 7 }


trapListener8 OBJECT-TYPE
	SYNTAX  OCTET STRING
	ACCESS  read-write
	STATUS  mandatory
	DESCRIPTION ""
	::= { trapListener 8 }


trapListener9 OBJECT-TYPE
	SYNTAX  OCTET STRING
	ACCESS  read-write
	STATUS  mandatory
	DESCRIPTION ""
	::= { trapListener 9 }


trapListener10 OBJECT-TYPE
	SYNTAX  OCTET STRING
	ACCESS  read-write
	STATUS  mandatory
	DESCRIPTION ""
	::= { trapListener 10 }


trapModemAlarmEnable OBJECT IDENTIFIER 	::= { trap 9 }

trapModemAlarmTemperatureEnable OBJECT-TYPE
	SYNTAX  Enable
	ACCESS  read-write
	STATUS  mandatory
	DESCRIPTION ""
	::= { trapModemAlarmEnable 1 }


trapModemAlarmMSEEnable OBJECT-TYPE
	SYNTAX  Enable
	ACCESS  read-write
	STATUS  mandatory
	DESCRIPTION ""
	::= { trapModemAlarmEnable 2 }


trapModemAlarmTimingEnable OBJECT-TYPE
	SYNTAX  Enable
	ACCESS  read-write
	STATUS  mandatory
	DESCRIPTION ""
	::= { trapModemAlarmEnable 3 }


trapModemAlarmLDPCEnable OBJECT-TYPE
	SYNTAX  Enable
	ACCESS  read-write
	STATUS  mandatory
	DESCRIPTION ""
	::= { trapModemAlarmEnable 4 }


trapModemAlarmLockEnable OBJECT-TYPE
	SYNTAX  Enable
	ACCESS  read-write
	STATUS  mandatory
	DESCRIPTION ""
	::= { trapModemAlarmEnable 5 }


trapModemAlarmMicroControllerEnable OBJECT-TYPE
	SYNTAX  Enable
	ACCESS  read-write
	STATUS  mandatory
	DESCRIPTION ""
	::= { trapModemAlarmEnable 6 }


trapInterfacesAlarmEnable OBJECT IDENTIFIER 	::= { trap 10 }

trapInterfaceAlarmEthernetPauseTransmittedEnable OBJECT-TYPE
	SYNTAX  Enable
	ACCESS  read-write
	STATUS  mandatory
	DESCRIPTION ""
	::= { trapInterfacesAlarmEnable 4 }


trapInterfaceAlarmEthernetLockEnable OBJECT-TYPE
	SYNTAX  Enable
	ACCESS  read-write
	STATUS  mandatory
	DESCRIPTION ""
	::= { trapInterfacesAlarmEnable 1 }


trapInterfaceAlarmEthernetOverflowEnable OBJECT-TYPE
	SYNTAX  Enable
	ACCESS  read-write
	STATUS  mandatory
	DESCRIPTION ""
	::= { trapInterfacesAlarmEnable 2 }


trapInterfaceAlarmEthernetPauseReceivedEnable OBJECT-TYPE
	SYNTAX  Enable
	ACCESS  read-write
	STATUS  mandatory
	DESCRIPTION ""
	::= { trapInterfacesAlarmEnable 3 }


trapInterfaceAlarmFPGAEnable OBJECT-TYPE
	SYNTAX  Enable
	ACCESS  read-write
	STATUS  mandatory
	DESCRIPTION ""
	::= { trapInterfacesAlarmEnable 5 }


trapInterfacesAlarmAsiEnable OBJECT-TYPE
	SYNTAX  SEQUENCE OF TrapInterfacesAlarmAsiEnableEntry
	ACCESS  not-accessible
	STATUS  mandatory
	DESCRIPTION ""
	::= { trapInterfacesAlarmEnable 6 }


trapInterfacesAlarmAsiEnableEntry OBJECT-TYPE
	SYNTAX  TrapInterfacesAlarmAsiEnableEntry
	ACCESS  not-accessible
	STATUS  mandatory
	DESCRIPTION ""
	INDEX {
		trapInterfacesAlarmAsiIndex }
	::= { trapInterfacesAlarmAsiEnable 1 }


TrapInterfacesAlarmAsiEnableEntry ::= SEQUENCE {

	trapInterfacesAlarmAsiIndex          INTEGER,
	trapInterfacesAlarmAsiSignalPresence Enable,
	trapInterfacesAlarmAsiLocked         Enable,
	trapInterfacesAlarmAsiTiming         Enable,
	trapInterfacesAlarmAsiOverflow       Enable,
	trapInterfacesAlarmAsiUnderflow      Enable }


trapInterfacesAlarmAsiIndex OBJECT-TYPE
	SYNTAX  INTEGER (1..10)
	ACCESS  read-only
	STATUS  mandatory
	DESCRIPTION ""
	::= { trapInterfacesAlarmAsiEnableEntry 1 }


trapInterfacesAlarmAsiSignalPresence OBJECT-TYPE
	SYNTAX  Enable
	ACCESS  read-write
	STATUS  mandatory
	DESCRIPTION ""
	::= { trapInterfacesAlarmAsiEnableEntry 2 }


trapInterfacesAlarmAsiLocked OBJECT-TYPE
	SYNTAX  Enable
	ACCESS  read-write
	STATUS  mandatory
	DESCRIPTION ""
	::= { trapInterfacesAlarmAsiEnableEntry 3 }


trapInterfacesAlarmAsiTiming OBJECT-TYPE
	SYNTAX  Enable
	ACCESS  read-write
	STATUS  mandatory
	DESCRIPTION ""
	::= { trapInterfacesAlarmAsiEnableEntry 4 }


trapInterfacesAlarmAsiOverflow OBJECT-TYPE
	SYNTAX  Enable
	ACCESS  read-write
	STATUS  mandatory
	DESCRIPTION ""
	::= { trapInterfacesAlarmAsiEnableEntry 5 }


trapInterfacesAlarmAsiUnderflow OBJECT-TYPE
	SYNTAX  Enable
	ACCESS  read-write
	STATUS  mandatory
	DESCRIPTION ""
	::= { trapInterfacesAlarmAsiEnableEntry 6 }


trapRxAlarmEnable OBJECT IDENTIFIER 	::= { trap 11 }

trapRxAlarmPll2LockEnable OBJECT-TYPE
	SYNTAX  Enable
	ACCESS  read-write
	STATUS  mandatory
	DESCRIPTION ""
	::= { trapRxAlarmEnable 3 }


trapRxAlarmPll1LockEnable OBJECT-TYPE
	SYNTAX  Enable
	ACCESS  read-write
	STATUS  mandatory
	DESCRIPTION ""
	::= { trapRxAlarmEnable 2 }


trapRxAlarmTemperatureEnable OBJECT-TYPE
	SYNTAX  Enable
	ACCESS  read-write
	STATUS  mandatory
	DESCRIPTION ""
	::= { trapRxAlarmEnable 1 }


trapRxAlarmFieldEnable OBJECT-TYPE
	SYNTAX  Enable
	ACCESS  read-write
	STATUS  mandatory
	DESCRIPTION ""
	::= { trapRxAlarmEnable 4 }


trapTxAlarmEnable OBJECT IDENTIFIER 	::= { trap 12 }

trapControllerAlarmEnable OBJECT IDENTIFIER 	::= { trap 13 }

trapTxAlarmTemperatureEnable OBJECT-TYPE
	SYNTAX  Enable
	ACCESS  read-write
	STATUS  mandatory
	DESCRIPTION ""
	::= { trapTxAlarmEnable 1 }


trapControllerAlarmFanModemEnable OBJECT-TYPE
	SYNTAX  Enable
	ACCESS  read-write
	STATUS  mandatory
	DESCRIPTION ""
	::= { trapControllerAlarmEnable 1 }


trapTxAlarmPll1LockEnable OBJECT-TYPE
	SYNTAX  Enable
	ACCESS  read-write
	STATUS  mandatory
	DESCRIPTION ""
	::= { trapTxAlarmEnable 2 }


trapControllerAlarmFanRFEnable OBJECT-TYPE
	SYNTAX  Enable
	ACCESS  read-write
	STATUS  mandatory
	DESCRIPTION ""
	::= { trapControllerAlarmEnable 2 }


trapTxAlarmPll2LockEnable OBJECT-TYPE
	SYNTAX  Enable
	ACCESS  read-write
	STATUS  mandatory
	DESCRIPTION ""
	::= { trapTxAlarmEnable 3 }


trapControllerAlarmFanPsu1Enable OBJECT-TYPE
	SYNTAX  Enable
	ACCESS  read-write
	STATUS  mandatory
	DESCRIPTION ""
	::= { trapControllerAlarmEnable 3 }


trapTxAlarmLowPowerEnable OBJECT-TYPE
	SYNTAX  Enable
	ACCESS  read-write
	STATUS  mandatory
	DESCRIPTION ""
	::= { trapTxAlarmEnable 4 }


trapControllerAlarmFanPsu2Enable OBJECT-TYPE
	SYNTAX  Enable
	ACCESS  read-write
	STATUS  mandatory
	DESCRIPTION ""
	::= { trapControllerAlarmEnable 4 }


trapControllerAlarm1V12Enable OBJECT-TYPE
	SYNTAX  Enable
	ACCESS  read-write
	STATUS  mandatory
	DESCRIPTION ""
	::= { trapControllerAlarmEnable 5 }


trapControllerAlarm2V12Enable OBJECT-TYPE
	SYNTAX  Enable
	ACCESS  read-write
	STATUS  mandatory
	DESCRIPTION ""
	::= { trapControllerAlarmEnable 6 }


trapControllerAlarmV5Enable OBJECT-TYPE
	SYNTAX  Enable
	ACCESS  read-write
	STATUS  mandatory
	DESCRIPTION ""
	::= { trapControllerAlarmEnable 7 }


trapControllerAlarmV6Enable OBJECT-TYPE
	SYNTAX  Enable
	ACCESS  read-write
	STATUS  mandatory
	DESCRIPTION ""
	::= { trapControllerAlarmEnable 8 }


trapControllerAlarmFanModem OBJECT-TYPE
	SYNTAX  TrapAlarm
	ACCESS  read-only
	STATUS  mandatory
	DESCRIPTION ""
	::= { trapControllerAlarm 1 }


trapControllerAlarmFanRF OBJECT-TYPE
	SYNTAX  TrapAlarm
	ACCESS  read-only
	STATUS  mandatory
	DESCRIPTION ""
	::= { trapControllerAlarm 2 }


trapControllerAlarmFanPsu1 OBJECT-TYPE
	SYNTAX  TrapAlarm
	ACCESS  read-only
	STATUS  mandatory
	DESCRIPTION ""
	::= { trapControllerAlarm 3 }


trapControllerAlarmFanPsu2 OBJECT-TYPE
	SYNTAX  TrapAlarm
	ACCESS  read-only
	STATUS  mandatory
	DESCRIPTION ""
	::= { trapControllerAlarm 4 }


trapControllerAlarm1V12 OBJECT-TYPE
	SYNTAX  TrapAlarm
	ACCESS  read-only
	STATUS  mandatory
	DESCRIPTION ""
	::= { trapControllerAlarm 5 }


trapControllerAlarm2V12 OBJECT-TYPE
	SYNTAX  TrapAlarm
	ACCESS  read-only
	STATUS  mandatory
	DESCRIPTION ""
	::= { trapControllerAlarm 6 }


trapControllerAlarmV5 OBJECT-TYPE
	SYNTAX  TrapAlarm
	ACCESS  read-only
	STATUS  mandatory
	DESCRIPTION ""
	::= { trapControllerAlarm 7 }


trapControllerAlarmV6 OBJECT-TYPE
	SYNTAX  TrapAlarm
	ACCESS  read-only
	STATUS  mandatory
	DESCRIPTION ""
	::= { trapControllerAlarm 8 }


localCommunicationInterfaceFpgaTemperatureWarning OBJECT-TYPE
	SYNTAX  Temperature
	ACCESS  read-write
	STATUS  mandatory
	DESCRIPTION ""
	::= { localCommunicationInterfaceFpgaTemperature 1 }


localCommunicationInterfaceFpgaTemperatureAlarm OBJECT-TYPE
	SYNTAX  Temperature
	ACCESS  read-write
	STATUS  mandatory
	DESCRIPTION ""
	::= { localCommunicationInterfaceFpgaTemperature 2 }


localCommunicationInterfaceStepUpTemperatureWarning OBJECT-TYPE
	SYNTAX  Temperature
	ACCESS  read-write
	STATUS  mandatory
	DESCRIPTION ""
	::= { localCommunicationInterfaceStepUpTemperature 1 }


localCommunicationInterfaceStepUpTemperatureAlarm OBJECT-TYPE
	SYNTAX  Temperature
	ACCESS  read-write
	STATUS  mandatory
	DESCRIPTION ""
	::= { localCommunicationInterfaceStepUpTemperature 2 }


remoteRSDecode OBJECT-TYPE
	SYNTAX  Alarm
	ACCESS  read-only
	STATUS  mandatory
	DESCRIPTION ""
	::= { remoteCommunicationInterfaceAlarm 1 }


remoteDeframerLock OBJECT-TYPE
	SYNTAX  Alarm
	ACCESS  read-only
	STATUS  mandatory
	DESCRIPTION ""
	::= { remoteCommunicationInterfaceAlarm 2 }


remoteVCXOLock OBJECT-TYPE
	SYNTAX  Alarm
	ACCESS  read-only
	STATUS  mandatory
	DESCRIPTION ""
	::= { remoteCommunicationInterfaceAlarm 3 }


remoteGTPPllLock OBJECT-TYPE
	SYNTAX  Alarm
	ACCESS  read-only
	STATUS  mandatory
	DESCRIPTION ""
	::= { remoteCommunicationInterfaceAlarm 4 }


remoteSFPLoss OBJECT-TYPE
	SYNTAX  Alarm
	ACCESS  read-only
	STATUS  mandatory
	DESCRIPTION ""
	::= { remoteCommunicationInterfaceAlarm 5 }


remoteSFPTxFault OBJECT-TYPE
	SYNTAX  Alarm
	ACCESS  read-only
	STATUS  mandatory
	DESCRIPTION ""
	::= { remoteCommunicationInterfaceAlarm 6 }


remoteCommunicationInterfaceTemperatureAlarm OBJECT-TYPE
	SYNTAX  Temperature
	ACCESS  read-write
	STATUS  mandatory
	DESCRIPTION ""
	::= { remoteCommunicationInterfaceConfig 2 }


remoteCommunicationInterfaceTemperatureWarning OBJECT-TYPE
	SYNTAX  Temperature
	ACCESS  read-write
	STATUS  mandatory
	DESCRIPTION ""
	::= { remoteCommunicationInterfaceConfig 1 }


trapLocalCommunicationInterface OBJECT IDENTIFIER 	::= { trap 15 }

trapLocalCommunicationInterfaceLocalBerAlarm OBJECT-TYPE
	SYNTAX  TrapAlarm
	ACCESS  read-only
	STATUS  mandatory
	DESCRIPTION
		""
	::= { trapLocalCommunicationInterface 1 }


trapRemoteCommunicationInterface OBJECT IDENTIFIER 	::= { trap 16 }

END
--
-- ELBER-DDM310Modem-MIB.my
--
