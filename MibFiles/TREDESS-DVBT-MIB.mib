TREDESS-DVBT-MIB DEFINITIONS ::= BEGIN

IMPORTS
	NOTIFICATION-TYPE, OBJECT-TYPE, MODULE-IDENTITY, 
	enterprises, Gauge32, Integer32, IpAddress
		FROM SNMPv2-SMI
	MODULE-COMPLIANCE, NOTIFICATION-GROUP, OBJECT-GROUP
		FROM SNMPv2-CONF
	TEXTUAL-CONVENTION, MacAddress, TruthValue, DisplayString
		FROM SNMPv2-TC;

dvbtBroadcastTredessMIB MODULE-IDENTITY
	LAST-UPDATED "201407111312Z"
	ORGANIZATION 
		"TREDESS 2010 S.L."
	CONTACT-INFO 
		"Volta do Castro, s/n
		15705 Santiago de Compostela - SPAIN
		aprieto@tredess.com"
	DESCRIPTION 
		"MIB of DVB-T Broadcast Gap Filler & Transmitter"
	
	REVISION "201407111312Z"
	DESCRIPTION 
		"Added:
			muxUnitType,
			muxReflectedPowerthreshold,
			muxExtendedDeecMode,
			muxInputLevel,
			muxSelectedASI,
			muxSeamlessStatus"

	REVISION "201407100959Z"
	DESCRIPTION 
		"IP/ASI changes:
		Obsoleted ASI rate constant/normal
		Added T2 Group 1/2"

	REVISION "201403190922Z"
	DESCRIPTION 
		"Included DVB-IP to ASI module"

	REVISION "201401211002Z"
	DESCRIPTION 
		"Added SFN error mute for DVB-T/T2 module"

	REVISION "201310291235Z"
	DESCRIPTION 
		"Included DVB-S/S2 to ASI module
		Regular NTP update option"

	REVISION "201307010910Z"
	DESCRIPTION 
		"Added T2 Lite compatibility. New oid in frame table for set/clear this mode
		New codeRate values 1/3 and 2/5
		T2 version according to ETSI EN 302 755"

	REVISION "201305050912Z"
	DESCRIPTION 
		"Add muteMux tables for UCA N+1 system.
		News MUX measurement OID: muxTimeOffset for MIP offset (T-transmitter) IA offset (T2-transmitter)
		New T2 meassurement in T2SystemTable: muxT2TTTx muxT2Latency
		New T2 alarm & trap: sfnError
		Reorder mpeg1x mpeg2x OIDs"
		
	REVISION "201301281044Z"
	DESCRIPTION 
		"Add T2 tables. 
		Add new OIDs:
		asi2ErrorAlarm, asi2EnableAlarm, asi2EnableTrap,
		mpeg1ErrorAlarm, mpeg1EnableAlarm, mpeg1EnableTrap,
		mpeg2ErrorAlarm, mpeg2EnableAlarm, mpeg2EnableTrap,
		tsErrorAlarm, tsEnableAlarm, tsEnableTrap,
		t2miErrorAlarm, t2miEnableAlarm, t2miEnableTrap"

	REVISION "201209251201Z"
	DESCRIPTION 
		"New splitter GPS table"

	REVISION "201202021031Z"
	DESCRIPTION 
		"New OIDs in gpsTable: 
		gpsState, gpsGMTdate, gpsHardware, gpsHoldoverDrift
		
		New OIDs in gpsAlarmTable:
		gpsSync, gpsSyncEnableAlarm, gpsSyncEnableTrap
		
		Renamed OIDs
		gpsReceiver[...] OIDs for gpsHoldover[...]"

	REVISION "201105261443Z"
	DESCRIPTION 
		"Add muxEchoCancelerOn in muxConfigurationTable.
		1: DAE/DEEC on
		2: DAE/DEEC off
		3: NotApply (Transmitter/Regenerative)"

	REVISION "201104201732Z"
	DESCRIPTION 
		"Delete muxDeecTemperature OID because
		this value is in muxTemperature.
		There are obsoleted values due new Compact Range.
		Hardware reset MUXs value hardwareResetMuxs(7) in dvbtBroadcastTredessMIB->adminDBTM->status OID"

	REVISION "201104200833Z"
	DESCRIPTION 
		"Included DEE Canceler. New OID for this:
		
		Mux Configuration Table:
		muxBW now available for DEEC also with 5MHz
		muxDeecWindow1Stat
		muxDeecWindow1Speed
		muxDeecWindow1Position
		muxDeecWindow2Speed
		muxDeecWindow2Position
		muxDeecWindow3Stat
		muxDeecWindow3Speed
		muxDeecWindow3Position
		
		Mux Measurement Table:
		muxDeecTemperature"

	REVISION "201104070807Z"
	DESCRIPTION 
		"snmpV2InformTimeout up to 1800 send.
		snmpV2InformRetries up to 10 retries."

	REVISION "201103210939Z"
	DESCRIPTION 
		"muxUserLocalDelay description/unit changed."

	REVISION "201008311333Z"
	DESCRIPTION 
		"muxCommunicationEnableTrap is writabled for Gap-Filler
		Two new columns in muxConfigurationTable:
		muxCellIdEnabled & muxCellIdValue (R/W)."

	REVISION "201006130934Z"
	DESCRIPTION 
		"NTP IP is correct although NTP client is disabled.
		Change OIDs traps for incommunication traps.
		New uca1Ready column for expecial commutations.
		uca1Mode description correction."

	REVISION "201005041045Z"
	DESCRIPTION 
		"New column in contactsInputTable (contactsInputSimulate)
		Writable ntpServerStatus (0 enabled, 1 disabled)
		New column in networkRoutingTable (networkRoutingInterfaz)
		Change web user change password system"

	REVISION "201004071925Z"
	DESCRIPTION 
		"Fan Traps
		Fan Service Time
		Mute configuration
		GPS Antenna position"

	REVISION "201003301154Z"
	DESCRIPTION 
		"New muxEnableAlarm Table.
		New newConfigurationFileTrap."

	REVISION "201003221756Z"
	DESCRIPTION 
		"New UCA 1+1 traps and organization,
		Integer Enums starts in 1 for snmpv1 compatibility"

	REVISION "201003111114Z"
	DESCRIPTION 
		"Errors in UCA 1+1 tables definition
		News OIDs for index (MUXs and UCA 1+1 tables)
		muxCtrlAddressMeassurement OID
		MIB descriptions errors
		v2Inform OIDs has changed"

	REVISION "201002041132Z"
	DESCRIPTION 
		"Revision, add new features:
		
		UCA 1+1
		NTP
		Routing Table
		WEBserver users (change passwords)
		FastTrapsSync
		v2 Inform"

	REVISION "200702231549Z"
	DESCRIPTION 
		"Initial version."
::= { tredessProducts 1 }


BitsStates ::= TEXTUAL-CONVENTION
	STATUS     deprecated
	DESCRIPTION 
		"Bit String providing a status summary for all
		alarms defined in this MIB module. A bit is set
		to one if the state of that alarm is 'fail'."
	SYNTAX  BITS {
		transmittedPowerMinor (0),
		transmittedPowerMajor (1),
		channelBERMinor (2),
		channelBERMajor (3),
		trtCurrentsOutRange (4),
		temperature (5),
		reflectedPower (6),
		unlockTS (7),
		noInputSignal (8),
		asiError (9),
		mipError (10),
		ppsError (11),
		iFDVBTSignal (12),
		gps10MHz (13),
		powerAmplifierCommunication (14),
		moduleCommunication (15),
		powerSupply1 (16),
		powerSupply2 (17),
		externalSupply (18),
		gpsHoldover (19),
		gpsAntenna (20)
	}


Mutes ::= TEXTUAL-CONVENTION
	STATUS     current
	DESCRIPTION 
		"Mutes status.
		
		Bit - Mutes
		1 - MPEG Error (lsb)
		2 - No MIP
		3 - GPS
		4 - ASI
		5 - MPEG overflow
		6 - SFN error
		"
	SYNTAX  BITS {
		null0 (0),
		null1 (1),
		sfnError (2),
		mpegOverflow (3),
		asi (4),
		gps (5),
		noMIP (6),
		mpegError (7)
	}


RateStatus ::= TEXTUAL-CONVENTION
	STATUS     current
	DESCRIPTION 
		"RateStatus is used in trap control 
		                            
		                            1: disabled 2: enabled 3: enabledPeriod"
	SYNTAX  INTEGER {
		disabled (1),
		enabled (2),
		enabledPeriod (3)
	}

televes              OBJECT IDENTIFIER ::= { enterprises 23180 }
televesGroup         OBJECT IDENTIFIER ::= { televes 2 }
tredess              OBJECT IDENTIFIER ::= { televesGroup 1 }
tredessProducts      OBJECT IDENTIFIER ::= { tredess 1 }

-- ###
-- ###  Description system
-- ###

systemDBTM           OBJECT IDENTIFIER ::= { dvbtBroadcastTredessMIB 1 }

-- ###
-- ###  General parameters
-- ###

adminDBTM            OBJECT IDENTIFIER ::= { dvbtBroadcastTredessMIB 2 }
networkAdmin         OBJECT IDENTIFIER ::= { adminDBTM 4 }
snmpAdmin            OBJECT IDENTIFIER ::= { adminDBTM 5 }
snmpTrapsConfiguration  OBJECT IDENTIFIER ::= { snmpAdmin 3 }
webserverAdmin       OBJECT IDENTIFIER ::= { adminDBTM 7 }

-- Configure server NTP (Network Time Protocol)

ntpServer            OBJECT IDENTIFIER ::= { adminDBTM 8 }

-- ###
-- ###  System elements
-- ###

dvbtBroadcastModules  OBJECT IDENTIFIER ::= { dvbtBroadcastTredessMIB 3 }

-- ###
-- ###  MULTIPLEX (Gap Filler OR Transmitter)
-- ###

mux                  OBJECT IDENTIFIER ::= { dvbtBroadcastModules 1 }

-- DVB-T2 Tables

dvbT2Tables          OBJECT IDENTIFIER ::= { mux 10 }

-- ###
-- ###  UCA
-- ###

uca                  OBJECT IDENTIFIER ::= { dvbtBroadcastModules 2 }

-- ###
-- ###  GPS
-- ###

gps                  OBJECT IDENTIFIER ::= { dvbtBroadcastModules 3 }

-- ###
-- ###  Dry contacts module (relays)
-- ###
-- 

contacts             OBJECT IDENTIFIER ::= { dvbtBroadcastModules 4 }
ucan                 OBJECT IDENTIFIER ::= { dvbtBroadcastModules 5 }
ucanStateConfiguration  OBJECT IDENTIFIER ::= { ucan 1 }

-- UCA n+1 State commutation

ucanStateCommutation  OBJECT IDENTIFIER ::= { ucan 2 }

-- UCA n+1 Alarms

ucanAlarm            OBJECT IDENTIFIER ::= { ucan 3 }

-- UCA N+1 for Compact Serie

ucanCompact          OBJECT IDENTIFIER ::= { ucan 4 }

-- ###
-- ###  UCA 1+1
-- ###

uca1                 OBJECT IDENTIFIER ::= { dvbtBroadcastModules 6 }
dvbs2Asi             OBJECT IDENTIFIER ::= { dvbtBroadcastModules 7 }

-- ###
-- ###  IP/ASI
-- ###

ip2Asi               OBJECT IDENTIFIER ::= { dvbtBroadcastModules 8 }

-- ###
-- ###  Alarm Section
-- ###

dvbtBroadcastAlarm   OBJECT IDENTIFIER ::= { dvbtBroadcastTredessMIB 4 }
transmittedPowerObjects  OBJECT IDENTIFIER ::= { dvbtBroadcastAlarm 1 }

-- Severity Major (2): transmitted forward power is 6 dB lower than nominal
-- Severity Minor (3):  transmitted power 3-6 dB lower than nominal 
-- Severity Cleared (5): transmitted prowe is the nominal 

transmittedPowerTrapsPrefix  OBJECT IDENTIFIER ::= { transmittedPowerObjects 0 }
trtCurrentsOutRangeObjects  OBJECT IDENTIFIER ::= { dvbtBroadcastAlarm 2 }

-- Severity Minor (3): Output stage transistors drain currents out of range (Power Amplifier)
-- Severity Cleared (5): Output stage transistors drain currents whithin the range (Power Amplifier)

trtCurrectsOutRangeTrapsPrefix  OBJECT IDENTIFIER ::= { trtCurrentsOutRangeObjects 0 }
reflectedPowerObjects  OBJECT IDENTIFIER ::= { dvbtBroadcastAlarm 3 }

-- Severity Minor (3): High reflected Power (> 40% of transmitted signal)
-- Severity Cleared (5): reflected Power is correct (< 40% of transmitted signal)

reflectedPowerTrapsPrefix  OBJECT IDENTIFIER ::= { reflectedPowerObjects 0 }
unlockTSObjects      OBJECT IDENTIFIER ::= { dvbtBroadcastAlarm 4 }
unlockTSTrapsPrefix  OBJECT IDENTIFIER ::= { unlockTSObjects 0 }
noInputSignalObjects  OBJECT IDENTIFIER ::= { dvbtBroadcastAlarm 5 }

-- Severity Minor (3): no input signal detected
-- Severity Cleared (5): input signal is detected

noInputSignalTrapsPrefix  OBJECT IDENTIFIER ::= { noInputSignalObjects 0 }
asi1ErrorObjects      OBJECT IDENTIFIER ::= { dvbtBroadcastAlarm 6 }

-- For Transmitter T (MOD description):
-- Severity Minor (3): no ASI signals available in any of the ASI inputs
-- Severity Cleared (5): ASI signals is available
-- 
-- For Transmitter T/T2 (MT2 description):
-- Severity Minor (3): no ASI 1 signal available
-- Severity Cleared (5): ASI 1 signal is available

asi1ErrorTrapsPrefix  OBJECT IDENTIFIER ::= { asi1ErrorObjects 0 }
mipErrorObjects      OBJECT IDENTIFIER ::= { dvbtBroadcastAlarm 7 }

-- Severity Minor (3): MIP Errors
-- Severity Cleared (5): MIP is correct

mipErrorTrapsPrefix  OBJECT IDENTIFIER ::= { mipErrorObjects 0 }
ppsObjects           OBJECT IDENTIFIER ::= { dvbtBroadcastAlarm 8 }

-- Severity Minor (3): 1pps signal error in modulator
-- Severity Cleared (5): 1pps signal in modulator is correct

ppsTrapsPrefix       OBJECT IDENTIFIER ::= { ppsObjects 0 }
iFDVBTSignalObjects  OBJECT IDENTIFIER ::= { dvbtBroadcastAlarm 9 }

-- Severity Minor (3): no DVB-T signal at IF stage (36.15MHz)
-- Severity Cleared (5): DVB-T signal at IF stage (36.15MHz) is correct

iFDVBTSignalTrapsPrefix  OBJECT IDENTIFIER ::= { iFDVBTSignalObjects 0 }
gps10MHzObjects      OBJECT IDENTIFIER ::= { dvbtBroadcastAlarm 10 }

-- Severity Minor (3): no 10 MHZ signal at the 10MHZ input of modulator
-- Severity Cleared (5): 10 MHZ signal at the 10MHZ input of modulator is correct

gps10MHzTrapsPrefix  OBJECT IDENTIFIER ::= { gps10MHzObjects 0 }
powerAmplifierCommunicatObjects  OBJECT IDENTIFIER ::= { dvbtBroadcastAlarm 11 }

-- Severity Minor (3): no power amplifier communication
-- Severity Cleared (5): power amplifier communication recovered

powerAmplifierCommunTrapsPrefix  OBJECT IDENTIFIER ::= { powerAmplifierCommunicatObjects 0 }
temperatureObjects   OBJECT IDENTIFIER ::= { dvbtBroadcastAlarm 12 }

-- Severity Minor (3): high temperature
-- Severity Cleared (5): normal temperature

temperatureTrapsPrefix  OBJECT IDENTIFIER ::= { temperatureObjects 0 }
moduleCommunicationObjects  OBJECT IDENTIFIER ::= { dvbtBroadcastAlarm 13 }

-- Severity Minor (3): no module communication
-- Severity Cleared (5): module communication recovered
-- 
-- Index could be:
-- 1..15: MUX
-- 1...4: UCA
-- 1,2: GPS
-- 1: CONTACTS

moduleCommunicationTrapsPrefix  OBJECT IDENTIFIER ::= { moduleCommunicationObjects 0 }
powerSupply1Objects  OBJECT IDENTIFIER ::= { dvbtBroadcastAlarm 14 }

-- Severity Minor (3): power supply 1 failure
-- Severity Cleared (5): power supply 1 recovered

powerSupply1TrapsPrefix  OBJECT IDENTIFIER ::= { powerSupply1Objects 0 }
powerSupply2Objects  OBJECT IDENTIFIER ::= { dvbtBroadcastAlarm 15 }

-- Severity Minor (3): power supply 2 failure
-- Severity Cleared (5): power supply 2 recovered

powerSupply2TrapsPrefix  OBJECT IDENTIFIER ::= { powerSupply2Objects 0 }
gpsHoldoverObjects   OBJECT IDENTIFIER ::= { dvbtBroadcastAlarm 16 }

-- Severity Minor (3): GPS receiver failure
-- Severity Cleared (5): GPS receiver recovered

gpsHoldoverTrapsPrefix  OBJECT IDENTIFIER ::= { gpsHoldoverObjects 0 }
gpsAntennaObjects    OBJECT IDENTIFIER ::= { dvbtBroadcastAlarm 17 }

-- Severity Minor (3): GPS antenna failure (disconnected or short-circuit)
-- Severity Cleared (5): GPS antenna connection is correct

gpsAntennaTrapsPrefix  OBJECT IDENTIFIER ::= { gpsAntennaObjects 0 }
relayObjects         OBJECT IDENTIFIER ::= { dvbtBroadcastAlarm 18 }

-- Severity Minor (3): external relay is close
-- Severity Cleared (5): external relay is open

relayTrapsPrefix     OBJECT IDENTIFIER ::= { relayObjects 0 }
channelBerObjects    OBJECT IDENTIFIER ::= { dvbtBroadcastAlarm 19 }

-- Severity Major (2): high Channel-BER (CBER > 2 x E-02)
-- Severity Minor (3): high Channel-BER (>1xE-04)
-- Severity Cleared (5): normal Channel-BER

channelBerTrapsPrefix  OBJECT IDENTIFIER ::= { channelBerObjects 0 }
minorObjects         OBJECT IDENTIFIER ::= { dvbtBroadcastAlarm 20 }
minorTrapsPrefix     OBJECT IDENTIFIER ::= { minorObjects 0 }
majorObjects         OBJECT IDENTIFIER ::= { dvbtBroadcastAlarm 21 }
majorTrapsPrefix     OBJECT IDENTIFIER ::= { majorObjects 0 }
generalObjects       OBJECT IDENTIFIER ::= { dvbtBroadcastAlarm 22 }

-- ###  Traps Prefix
-- This prefix is necessary to satisfy the requirement of RFC 2578
-- section 8.5 that 'the next to last sub-identifier in the name of
-- any newly-defined notification must have the value zero'.

generalTrapsPrefix   OBJECT IDENTIFIER ::= { generalObjects 0 }
inputsContactsObjects  OBJECT IDENTIFIER ::= { dvbtBroadcastAlarm 23 }
inputsContactsTrapsPrefix  OBJECT IDENTIFIER ::= { inputsContactsObjects 0 }
viterbiBerObjects    OBJECT IDENTIFIER ::= { dvbtBroadcastAlarm 24 }

-- Severity Major (2): high Channel-BER (CBER > 2 x E-02)
-- Severity Minor (3): high Channel-BER (>1xE-04)
-- Severity Cleared (5): normal Channel-BER

viterbiBerTrapsPrefix  OBJECT IDENTIFIER ::= { viterbiBerObjects 0 }
alternativeAsiObjects  OBJECT IDENTIFIER ::= { dvbtBroadcastAlarm 25 }

-- Severity Minor (3): alternative ASI OK
-- Severity Cleared (5): alternative ASI NOK

alternativeAsiTrapsPrefix  OBJECT IDENTIFIER ::= { alternativeAsiObjects 0 }
adaptativeEchoObjects  OBJECT IDENTIFIER ::= { dvbtBroadcastAlarm 26 }

-- Severity Minor (3): Adaptative Echo ON
-- Severity Cleared (5): Adaptative Echo OFF

adaptativeEchoTrapsPrefix  OBJECT IDENTIFIER ::= { adaptativeEchoObjects 0 }
n1ConmutationObjects  OBJECT IDENTIFIER ::= { dvbtBroadcastAlarm 27 }

-- Severity Minor (3): MUX n switched
-- Severity Cleared (5): MUX n no-switched

n1conmutationTrapsPrefix  OBJECT IDENTIFIER ::= { n1ConmutationObjects 0 }
ucaN1Objects         OBJECT IDENTIFIER ::= { dvbtBroadcastAlarm 28 }

-- Severity Minor (3): the alarm is ON
-- Severity Cleared (5): the alarm is OFF

ucaN1TrapsPrefix     OBJECT IDENTIFIER ::= { ucaN1Objects 0 }
uca1Objects          OBJECT IDENTIFIER ::= { dvbtBroadcastAlarm 29 }
uca101CompTrapsPrefix  OBJECT IDENTIFIER ::= { uca1Objects 0 }
uca101TrapsPrefix    OBJECT IDENTIFIER ::= { uca101CompTrapsPrefix 0 }
uca102CompTrapsPrefix  OBJECT IDENTIFIER ::= { uca1Objects 1 }
uca102TrapsPrefix    OBJECT IDENTIFIER ::= { uca102CompTrapsPrefix 0 }
uca103CompTrapsPrefix  OBJECT IDENTIFIER ::= { uca1Objects 2 }
uca103TrapsPrefix    OBJECT IDENTIFIER ::= { uca103CompTrapsPrefix 0 }
uca104CompTrapsPrefix  OBJECT IDENTIFIER ::= { uca1Objects 3 }
uca104TrapsPrefix    OBJECT IDENTIFIER ::= { uca104CompTrapsPrefix 0 }
uca105CompTrapsPrefix  OBJECT IDENTIFIER ::= { uca1Objects 4 }
uca105TrapsPrefix    OBJECT IDENTIFIER ::= { uca105CompTrapsPrefix 0 }
uca106CompTrapsPrefix  OBJECT IDENTIFIER ::= { uca1Objects 5 }
uca106TrapsPrefix    OBJECT IDENTIFIER ::= { uca106CompTrapsPrefix 0 }
uca107CompTrapsPrefix  OBJECT IDENTIFIER ::= { uca1Objects 6 }
uca107TrapsPrefix    OBJECT IDENTIFIER ::= { uca107CompTrapsPrefix 0 }
uca108CompTrapsPrefix  OBJECT IDENTIFIER ::= { uca1Objects 7 }
uca108TrapsPrefix    OBJECT IDENTIFIER ::= { uca108CompTrapsPrefix 0 }
uca109CompTrapsPrefix  OBJECT IDENTIFIER ::= { uca1Objects 8 }
uca109TrapsPrefix    OBJECT IDENTIFIER ::= { uca109CompTrapsPrefix 0 }
uca110CompTrapsPrefix  OBJECT IDENTIFIER ::= { uca1Objects 9 }
uca110TrapsPrefix    OBJECT IDENTIFIER ::= { uca110CompTrapsPrefix 0 }
uca111CompTrapsPrefix  OBJECT IDENTIFIER ::= { uca1Objects 10 }
uca111TrapsPrefix    OBJECT IDENTIFIER ::= { uca111CompTrapsPrefix 0 }
uca112CompTrapsPrefix  OBJECT IDENTIFIER ::= { uca1Objects 11 }
uca112TrapsPrefix    OBJECT IDENTIFIER ::= { uca112CompTrapsPrefix 0 }
uca113CompTrapsPrefix  OBJECT IDENTIFIER ::= { uca1Objects 12 }
uca113TrapsPrefix    OBJECT IDENTIFIER ::= { uca113CompTrapsPrefix 0 }
uca114CompTrapsPrefix  OBJECT IDENTIFIER ::= { uca1Objects 13 }
uca114TrapsPrefix    OBJECT IDENTIFIER ::= { uca114CompTrapsPrefix 0 }
uca115CompTrapsPrefix  OBJECT IDENTIFIER ::= { uca1Objects 14 }
uca115TrapsPrefix    OBJECT IDENTIFIER ::= { uca115CompTrapsPrefix 0 }
fanAlarmObjects      OBJECT IDENTIFIER ::= { dvbtBroadcastAlarm 31 }

-- Severity Major (2): transmitted forward power is 6 dB lower than nominal
-- Severity Minor (3):  transmitted power 3-6 dB lower than nominal 
-- Severity Cleared (5): transmitted prowe is the nominal 

fanAlarmTrapsPrefix  OBJECT IDENTIFIER ::= { fanAlarmObjects 0 }
gpsSyncObjects       OBJECT IDENTIFIER ::= { dvbtBroadcastAlarm 32 }

-- Severity Minor (3): GPS is synchronized
-- Severity Cleared (5): GPS is not synchronized

gpsSyncTrapsPrefix   OBJECT IDENTIFIER ::= { gpsSyncObjects 0 }
asi2ErrorObjects     OBJECT IDENTIFIER ::= { dvbtBroadcastAlarm 34 }

-- Only T/T2 Transmitter
-- Severity Minor (3): no ASI 2 signal available. 
-- Severity Cleared (5): ASI 2 signal is available.

asi2ErrorTrapsPrefix  OBJECT IDENTIFIER ::= { asi2ErrorObjects 0 }
mpeg1ErrorObjects     OBJECT IDENTIFIER ::= { dvbtBroadcastAlarm 37 }

-- Severity Minor (3): MPEG 1 error.
-- Severity Cleared (5): MPEG 1 signal OK.

mpeg1ErrorTrapsPrefix  OBJECT IDENTIFIER ::= { mpeg1ErrorObjects 0 }
mpeg2ErrorObjects     OBJECT IDENTIFIER ::= { dvbtBroadcastAlarm 38 }

-- Severity Minor (3): MPEG 2 error.
-- Severity Cleared (5): MPEG 2 signal OK.

mpeg2ErrorTrapsPrefix  OBJECT IDENTIFIER ::= { mpeg2ErrorObjects 0 }
sfnErrorObjects     OBJECT IDENTIFIER ::= { dvbtBroadcastAlarm 39 }

-- Only T/T2 Transmitter
-- Severity Minor (3): sfn error.
-- Severity Cleared (5): sfn available.

sfnErrorTrapsPrefix  OBJECT IDENTIFIER ::= { sfnErrorObjects 0 }
tsErrorObjects     OBJECT IDENTIFIER ::= { dvbtBroadcastAlarm 40 }

-- Only T/T2 Transmitter
-- Severity Minor (3): ts error.
-- Severity Cleared (5): ts available.

tsErrorTrapsPrefix  OBJECT IDENTIFIER ::= { tsErrorObjects 0 }
t2miErrorObjects     OBJECT IDENTIFIER ::= { dvbtBroadcastAlarm 41 }

-- Only T/T2 Transmitter
-- Severity Minor (3): t2mi error.
-- Severity Cleared (5): t2mi available.

t2miErrorTrapsPrefix  OBJECT IDENTIFIER ::= { t2miErrorObjects 0 }
dvbs2AsiObjects      OBJECT IDENTIFIER ::= { dvbtBroadcastAlarm 42 }
dvbs2AsiTrapComp     OBJECT IDENTIFIER ::= { dvbs2AsiObjects 0 }

ip2AsiObjects        OBJECT IDENTIFIER ::= { dvbtBroadcastAlarm 43 }
ip2AsiTrapComp       OBJECT IDENTIFIER ::= { ip2AsiObjects 0 }

conformance          OBJECT IDENTIFIER ::= { dvbtBroadcastTredessMIB 10 }
objectGroups         OBJECT IDENTIFIER ::= { conformance 1 }
groupCompilance      OBJECT IDENTIFIER ::= { conformance 2 }

sysDescrDBTM  OBJECT-TYPE
	SYNTAX     DisplayString
	MAX-ACCESS read-only
	STATUS     current
	DESCRIPTION 
		"A textual description of the entity."
	::= { systemDBTM 1 }

sysNameDBTM  OBJECT-TYPE
	SYNTAX     OCTET STRING (SIZE(12))
	MAX-ACCESS read-write
	STATUS     current
	DESCRIPTION 
		"Name of the station."
	::= { systemDBTM 2 }

sysManagementVersionDBTM  OBJECT-TYPE
	SYNTAX     DisplayString
	MAX-ACCESS read-only
	STATUS     current
	DESCRIPTION 
		"Management software version"
	::= { systemDBTM 3 }

sysKernelVersionDBTM  OBJECT-TYPE
	SYNTAX     DisplayString
	MAX-ACCESS read-only
	STATUS     current
	DESCRIPTION 
		"Kernel version."
	::= { systemDBTM 4 }

sysSnmpVersionDBTM  OBJECT-TYPE
	SYNTAX     DisplayString
	MAX-ACCESS read-only
	STATUS     current
	DESCRIPTION 
		"SNMP Version"
	::= { systemDBTM 5 }

sysCycleDBTM  OBJECT-TYPE
	SYNTAX     DisplayString
	MAX-ACCESS read-only
	STATUS     current
	DESCRIPTION 
		"Last time that has completed a cycle of polling
		
		DD/MM/YYYY hh:mm:ss (for example: 20/01/2007 12:14:09)"
	::= { systemDBTM 6 }

sysFileDateHourDBTM  OBJECT-TYPE
	SYNTAX     DisplayString
	MAX-ACCESS read-only
	STATUS     current
	DESCRIPTION 
		"Configuration File date/hour
		
		DD/MM/YYYY hh:mm:ss (for example: 08/03/2010 14:04:37)"
	::= { systemDBTM 7 }

sysRedundanceDBTM  OBJECT-TYPE
	SYNTAX     INTEGER {
		noRedundance (1),
		onePlusOneRedundance (2),
		nPlusOneRedundance (3),
		multichannel (4),
		compact (5)
	}
	MAX-ACCESS read-only
	STATUS     current
	DESCRIPTION 
		"Information redundancy.
		
		1: system is not redundant
		2: 1+1 system
		3: n+1 system
		4: multichannel Serie
		5: Compact Serie"
	::= { systemDBTM 8 }

date  OBJECT-TYPE
	SYNTAX     DisplayString
	MAX-ACCESS read-write
	STATUS     current
	DESCRIPTION 
		"System date DDMMYYYY (for example: 22012008 22/01/2007)"
	::= { adminDBTM 1 }

hour  OBJECT-TYPE
	SYNTAX     DisplayString
	MAX-ACCESS read-write
	STATUS     current
	DESCRIPTION 
		"System time HHMMSS (for example 180300 18:03:00)"
	::= { adminDBTM 2 }

status  OBJECT-TYPE
	SYNTAX     INTEGER {
		systemOK (1),
		systemReboot (2),
		systemSoftReset (3),
		systemHardReset (4),
		systemFindModules (5),
		systemReadConfigurations (6),
		hardwareResetMuxs (7)
	}
	MAX-ACCESS read-write
	STATUS     current
	DESCRIPTION 
		"If the manager writes in this variable:
		
		1 = it does not efect (telecontrol is ON and polling the modules)
		2 = telecontrol system will be reboot (telecontrol application)
		3 = telecontrol system will be soft reset (reboot with actual values)
		4 = telecontrol system will be hard reset (reboot with default values)
		5 = telecontrol system will find new modules connected to the control bus
		6 = telecontrol system will read module configurations - Obsolete in Compact Range
		7 = telecontrol system will resets MUXs
		"
	::= { adminDBTM 3 }

networkIpAddress  OBJECT-TYPE
	SYNTAX     IpAddress
	MAX-ACCESS read-write
	STATUS     current
	DESCRIPTION 
		"IP address"
	::= { networkAdmin 1 }

networkMaskAddress  OBJECT-TYPE
	SYNTAX     IpAddress
	MAX-ACCESS read-write
	STATUS     current
	DESCRIPTION 
		"Network mask IP address"
	::= { networkAdmin 2 }

networkGatewayAddress  OBJECT-TYPE
	SYNTAX     IpAddress
	MAX-ACCESS read-write
	STATUS     current
	DESCRIPTION 
		"Gateway Address"
	::= { networkAdmin 3 }

networkRoutingTable  OBJECT-TYPE
	SYNTAX SEQUENCE OF NetworkRoutingEntry
	MAX-ACCESS not-accessible
	STATUS     current
	DESCRIPTION 
		"Static Routing Table"
	::= { networkAdmin 4 }

networkRoutingEntry  OBJECT-TYPE
	SYNTAX 	NetworkRoutingEntry
	MAX-ACCESS not-accessible
	STATUS     current
	DESCRIPTION 
		"Each row is IP route"
	INDEX { networkRoutingIndex }
	::= { networkRoutingTable 1 }

NetworkRoutingEntry ::= SEQUENCE {
	networkRoutingIndex
		Integer32,
	networkRoutingDestination
		IpAddress,
	networkRoutingMask
		IpAddress,
	networkRoutingGateway
		IpAddress,
	networkRoutingInterfaz
		INTEGER,
	networkRoutingEnabled
		TruthValue
}

networkRoutingIndex  OBJECT-TYPE
	SYNTAX     Integer32 (1..4)
	MAX-ACCESS not-accessible
	STATUS     current
	DESCRIPTION 
		"Routing table index"
	::= { networkRoutingEntry 1 }

networkRoutingDestination  OBJECT-TYPE
	SYNTAX     IpAddress
	MAX-ACCESS read-write
	STATUS     current
	DESCRIPTION 
		"Destination Host/Network IP"
	::= { networkRoutingEntry 2 }

networkRoutingMask  OBJECT-TYPE
	SYNTAX     IpAddress
	MAX-ACCESS read-write
	STATUS     current
	DESCRIPTION 
		"Network Mask"
	::= { networkRoutingEntry 3 }

networkRoutingGateway  OBJECT-TYPE
	SYNTAX     IpAddress
	MAX-ACCESS read-write
	STATUS     current
	DESCRIPTION 
		"Routing gateway"
	::= { networkRoutingEntry 4 }

networkRoutingInterfaz  OBJECT-TYPE
	SYNTAX     INTEGER {
		networkRoutingEthernet (1),
		networkRoutingGprs (2),
		networkRoutingVpn (3)
	}
	MAX-ACCESS read-write
	STATUS     current
	DESCRIPTION 
		"Interfaz for this route.
		
		1: Ethernet
		2: GPRS
		3: VPN"
	::= { networkRoutingEntry 5 }

networkRoutingEnabled  OBJECT-TYPE
	SYNTAX     TruthValue
	MAX-ACCESS read-write
	STATUS     current
	DESCRIPTION 
		"Enable/disable this route"
	::= { networkRoutingEntry 6 }

snmpReadCommunity  OBJECT-TYPE
	SYNTAX     OCTET STRING (SIZE(1..32))
	MAX-ACCESS read-write
	STATUS     current
	DESCRIPTION 
		"The read-community parameter specifies the SNMP community 
		name for read access
		
		1..32 characters"
	::= { snmpAdmin 1 }

snmpWriteCommunity  OBJECT-TYPE
	SYNTAX     OCTET STRING (SIZE(1..32))
	MAX-ACCESS read-write
	STATUS     current
	DESCRIPTION 
		"The read-write-community parameter specifies SNMP community 
		name for read/write acces.
		
		1..32 characters"
	::= { snmpAdmin 2 }

snmpTrapsDestinationTable  OBJECT-TYPE
	SYNTAX SEQUENCE OF SnmpTrapsDestinationEntry
	MAX-ACCESS not-accessible
	STATUS     current
	DESCRIPTION 
		"This table contains the posibles trap destinations. 1..4"
	::= { snmpTrapsConfiguration 1 }

snmpTrapsDestinationEntry  OBJECT-TYPE
	SYNTAX 	SnmpTrapsDestinationEntry
	MAX-ACCESS not-accessible
	STATUS     current
	DESCRIPTION 
		"Each row is a traps destination IP"
	INDEX { snmpTrapsDestinationIndex }
	::= { snmpTrapsDestinationTable 1 }

SnmpTrapsDestinationEntry ::= SEQUENCE {
	snmpTrapsDestinationIndex
		Integer32,
	snmpTrapsDestionationEnable
		TruthValue,
	snmpTrapsDestinationIP
		IpAddress
}

snmpTrapsDestinationIndex  OBJECT-TYPE
	SYNTAX     Integer32 (1..3)
	MAX-ACCESS not-accessible
	STATUS     current
	DESCRIPTION 
		"Traps destinations indexs"
	::= { snmpTrapsDestinationEntry 1 }

snmpTrapsDestionationEnable  OBJECT-TYPE
	SYNTAX     TruthValue
	MAX-ACCESS read-write
	STATUS     current
	DESCRIPTION 
		"Enable/disable this IP trap destination.
		
		True : this IP destination is disables
		False: this IP destination is enabled"
	::= { snmpTrapsDestinationEntry 2 }

snmpTrapsDestinationIP  OBJECT-TYPE
	SYNTAX     IpAddress
	MAX-ACCESS read-write
	STATUS     current
	DESCRIPTION 
		"IP address for sending traps"
	::= { snmpTrapsDestinationEntry 3 }

snmpTrapControlRateStatus  OBJECT-TYPE
	SYNTAX     RateStatus
	MAX-ACCESS read-write
	STATUS     current
	DESCRIPTION 
		"This object is used for rate control of traps,
		preventing overload of the management network
		by transmission of an excessive number of traps.
		The value 'disabled' means that traps are never
		sent. The value 'enabled' means that a trap will
		be sent when triggered.
		                            
		When a trap is sent, the agent changes the value
		of this object to 'enabledPeriod'. In this
		state the agent will not send any more traps.
		The agent automatically changes the value back
		to 'enabled' when the time specified by
		alarmTrapControlPeriod
		expires. A management application may set the
		value to 'enabled' at any time, but must never
		set the value to 'enabledPeriod'.
		"
	::= { snmpTrapsConfiguration 2 }

snmpTrapControlPeriod  OBJECT-TYPE
	SYNTAX     Integer32
	UNITS 	"seconds"
	MAX-ACCESS read-write
	STATUS     current
	DESCRIPTION 
		"The agent will ensure that the interval between
		sending traps is no shorter than this time period
		(unless overridden by the manager)."
	::= { snmpTrapsConfiguration 3 }

snmpTrapsSync  OBJECT-TYPE
	SYNTAX     Integer32
	MAX-ACCESS read-write
	STATUS     current
	DESCRIPTION 
		"This value is the last sent trap number. It is used for synchronizing the traps.
		
		If the remote user writes this variable with a number lower than actual,
		the agent will send the traps since that number to the actual.
		"
	::= { snmpTrapsConfiguration 4 }

snmpTrapsAuthTrapEnable  OBJECT-TYPE
	SYNTAX     TruthValue
	MAX-ACCESS read-write
	STATUS     current
	DESCRIPTION 
		"Setting this variable to 1enables generation of authentication failure traps.
		
		True = authentication failure traps disable
		False  = authentication failure traps enable
		
		"
	::= { snmpTrapsConfiguration 5 }

snmpTrapsCommunity  OBJECT-TYPE
	SYNTAX     OCTET STRING (SIZE(1..32))
	MAX-ACCESS read-write
	STATUS     current
	DESCRIPTION 
		"This define the default comunity string to be used when sending traps.
		
		1..32 characters"
	::= { snmpTrapsConfiguration 6 }

snmpTrapsPeriodic  OBJECT-TYPE
	SYNTAX     Integer32
	UNITS 	"Seconds"
	MAX-ACCESS read-write
	STATUS     current
	DESCRIPTION 
		"The agent will send one trap if passed 
		this amount of seconds has not been sent no alarm
		
		0: the periodicTrap never will be sent"
	::= { snmpTrapsConfiguration 7 }

snmpFastTrapsSync  OBJECT-TYPE
	SYNTAX     TruthValue
	MAX-ACCESS read-write
	STATUS     current
	DESCRIPTION 
		"Fast Trap Syncronization sends to SNMP Managers 
		the traps which are actually activated alarms.
		
		false: is the default value. 
		true: starts fast trap syncronization process."
	::= { snmpTrapsConfiguration 8 }

snmpInformAck  OBJECT-TYPE
	SYNTAX     TruthValue
	MAX-ACCESS read-write
	STATUS     current
	DESCRIPTION 
		"Traps behavior.
		
		Indicates if the Manager has to send an ACK for each received trap or not.
		
		1: v2inform (ACK are necessary)
		2: v2trap (ACK are not necessary)
		
		"
	::= { snmpTrapsConfiguration 9 }

snmpInformTimeout  OBJECT-TYPE
	SYNTAX     Integer32 (1..1800)
	MAX-ACCESS read-write
	STATUS     current
	DESCRIPTION 
		"When this time out is completed if an ACK is not received and the attemps 
		number executed is lower than configurated value, the agent resends
		the trap."
	::= { snmpTrapsConfiguration 10 }

snmpInformRetries  OBJECT-TYPE
	SYNTAX     Integer32 (1..10)
	MAX-ACCESS read-write
	STATUS     current
	DESCRIPTION 
		"Number of retries for sending a trap."
	::= { snmpTrapsConfiguration 11 }

powerSupplyStatus  OBJECT-TYPE
	SYNTAX     INTEGER {
		powerSupplyAC (1),
		powerSupplyBattery (2),
		powerSupplyBatterySAE (3)
	}
	MAX-ACCESS read-only
	STATUS     current
	DESCRIPTION 
		"Indicates the power supply status.
		
		1: Management is powered by AC.
		2: Management is powered by battery.
		3: Management is powered by SAE (only if system has fuse box connected to realys module)"
	::= { adminDBTM 6 }

webserverAutoRefresh  OBJECT-TYPE
	SYNTAX     Integer32
	UNITS 	"seconds"
	MAX-ACCESS read-write
	STATUS     current
	DESCRIPTION 
		"Auto-refresh web is enabled if this value is not 0.
		Time in seconds"
	::= { webserverAdmin 1 }

webserverNewPass  OBJECT-TYPE
	SYNTAX     OCTET STRING (SIZE(1..10))
	MAX-ACCESS read-write
	STATUS     current
	DESCRIPTION 
		"New Password
		
		Only write!
		
		First set the new value. After that:
		- setting webserverUser1 with the same password for changing not privileged user ('user')
		- setting webserverUser1 with the same password for changing privileged user ('admin')"
	::= { webserverAdmin 2 }

webserverUser1  OBJECT-TYPE
	SYNTAX     OCTET STRING (SIZE(1..10))
	MAX-ACCESS read-write
	STATUS     current
	DESCRIPTION 
		"New Password User1
		
		Only write!
		
		After setting webserverNewPass, setting this value with the same password for changing not privileged user ('user')
		"
	::= { webserverAdmin 3 }

webserverUser2  OBJECT-TYPE
	SYNTAX     OCTET STRING (SIZE(1..10))
	MAX-ACCESS read-write
	STATUS     current
	DESCRIPTION 
		"New Password User2
		
		Only write!
		
		After setting webserverNewPass, setting this value with the same password for changing privileged user ('admin')"
	::= { webserverAdmin 4 }

-- NTP status
-- 
-- 1: Disabled
-- 2: Updated
-- 3: Updating
-- 4: Error

ntpServerStatus  OBJECT-TYPE
	SYNTAX     INTEGER {
		ntpServerEnabled (0),
		ntpServerDisabled (1),
		ntpServerUpdated (2),
		ntpServerUpdating (3),
		ntpServerError (4)
	}
	MAX-ACCESS read-write
	STATUS     current
	DESCRIPTION 
		"Indicates the NTP server status
		
		0: enabled
		1: disabled
		2: udpated
		3: udpating
		4: error during updating process
		
		It is possible only write values 0 (enabled) and 1(disabled)"
	::= { ntpServer 1 }

ntpServerIp  OBJECT-TYPE
	SYNTAX     IpAddress
	MAX-ACCESS read-write
	STATUS     current
	DESCRIPTION 
		"NTP IP server"
	::= { ntpServer 2 }

ntpServerVersion  OBJECT-TYPE
	SYNTAX     Integer32 (1..3)
	MAX-ACCESS read-write
	STATUS     deprecated
	DESCRIPTION 
		"NTP version 1,2,3"
	::= { ntpServer 3 }

ntpServerOffset  OBJECT-TYPE
	SYNTAX     Integer32 (-12..14)
	MAX-ACCESS read-write
	STATUS     current
	DESCRIPTION 
		"GMT offset
		-12 ... +14"
	::= { ntpServer 4 }

ntpServerUpdate  OBJECT-TYPE
	SYNTAX     INTEGER {
		auto (1),
		periodical (2)
	}
	MAX-ACCESS read-write
	STATUS     current
	DESCRIPTION 
		"Update on startup or periodically"
	::= { ntpServer 5 }

ntpServerDays  OBJECT-TYPE
	SYNTAX     Integer32 (0..5)
	MAX-ACCESS read-write
	STATUS     current
	DESCRIPTION 
		"Days update"
	::= { ntpServer 6 }

ntpServerHours  OBJECT-TYPE
	SYNTAX     Integer32 (0..23)
	MAX-ACCESS read-write
	STATUS     current
	DESCRIPTION 
		"Hours update"
	::= { ntpServer 7 }

ntpServerMinutes  OBJECT-TYPE
	SYNTAX     Integer32 (0..59)
	MAX-ACCESS read-write
	STATUS     current
	DESCRIPTION 
		"Minutes update"
	::= { ntpServer 8 }

muxConfigurationTable  OBJECT-TYPE
	SYNTAX SEQUENCE OF MuxConfigurationEntry
	MAX-ACCESS not-accessible
	STATUS     current
	DESCRIPTION 
		"This table contains the basic information of multiplex connected to the system."
	::= { mux 1 }

muxConfigurationEntry  OBJECT-TYPE
	SYNTAX 	MuxConfigurationEntry
	MAX-ACCESS not-accessible
	STATUS     current
	DESCRIPTION 
		"Multiplex slot. Multiplex could be Gap Filler or Transmitter system."
	INDEX { muxConfigurationIndex }
	::= { muxConfigurationTable 1 }

MuxConfigurationEntry ::= SEQUENCE {
	muxConfigurationIndex
		Integer32,
	muxConfigurationDescription
		DisplayString,
	muxCtrlAddress
		Integer32,
	muxChannelIn
		Integer32,
	muxChannelOut
		Integer32,
	muxFreqIn
		Integer32,
	muxFreqOut
		Integer32,
	muxTNetworkMode
		INTEGER,
	muxAutoMIP
		INTEGER,
	muxFFTSize
		INTEGER,
	muxGuardInterval
		INTEGER,
	muxBW
		INTEGER,
	muxConstellation
		INTEGER,
	muxFEC
		INTEGER,
	muxUserLocalDelay
		Integer32,
	muxMutes
		Mutes,
	muxVcorr1
		Integer32,
	muxVcorr2
		Integer32,
	muxHysteresis
		Integer32,
	muxCBERwarningLevel
		OCTET STRING,
	muxCBERcriticalLevel
		OCTET STRING,
	muxTrapsConfiguration
		BitsStates,
	muxVBERwarningLevel
		OCTET STRING,
	muxVBERcriticalLevel
		OCTET STRING,
	muxEchoAdaptation
		INTEGER,
	muxAsiInput
		INTEGER,
	muxUmbralTemp
		Integer32,
	muxConfigurationRowIndex
		Integer32,
	muxRfMute
		TruthValue,
	muxTCellIdEnable
		TruthValue,
	muxTCellIdValue
		Integer32,
	muxDeecWindow1Stat
		TruthValue,
	muxDeecWindow1Speed
		INTEGER,
	muxDeecWindow1Position
		Integer32,
	muxDeecWindow2Speed
		INTEGER,
	muxDeecWindow2Position
		Integer32,
	muxDeecWindow3Stat
		TruthValue,
	muxDeecWindow3Speed
		INTEGER,
	muxDeecWindow3Position
		Integer32,
	muxEchoCancelerOn
		INTEGER,
	muxConfigurationType
		INTEGER,
	muxUmbralTempFPGA
		Integer32,
	muxTcfgPPSedge
		INTEGER,
	muxTtxId
		INTEGER,
	muxUnitType
		DisplayString,
	muxReflectedPowerthreshold
		Integer32,
	muxExtendedDeecMode
		INTEGER
}

muxConfigurationIndex  OBJECT-TYPE
	SYNTAX     Integer32 (1..30)
	MAX-ACCESS not-accessible
	STATUS     current
	DESCRIPTION 
		"MUX index"
	::= { muxConfigurationEntry 1 }

muxConfigurationDescription  OBJECT-TYPE
	SYNTAX     DisplayString
	MAX-ACCESS read-only
	STATUS     current
	DESCRIPTION 
		"MUX description. The module could be 
		
		REM: GapFiller DAE
		DEEC: GapFiller DEEC
		MOD: Transmitter.
		REG: retransmitter
		MT2: Modualtor T/T2"
	::= { muxConfigurationEntry 2 }

muxCtrlAddress  OBJECT-TYPE
	SYNTAX     Integer32 (1..15|101..115)
	MAX-ACCESS read-only
	STATUS     current
	DESCRIPTION 
		"Control address"
	::= { muxConfigurationEntry 3 }

muxChannelIn  OBJECT-TYPE
	SYNTAX     Integer32
	MAX-ACCESS read-only
	STATUS     current
	DESCRIPTION 
		"Input Channel
		0: N/A (The multiplex is a Transmitter)"
	::= { muxConfigurationEntry 4 }

muxChannelOut  OBJECT-TYPE
	SYNTAX     Integer32 (21..69)
	MAX-ACCESS read-only
	STATUS     current
	DESCRIPTION 
		"Output Channel"
	::= { muxConfigurationEntry 5 }

muxFreqIn  OBJECT-TYPE
	SYNTAX     Integer32
	MAX-ACCESS read-write
	STATUS     current
	DESCRIPTION 
		"Input frequency
		0: N/A (The multiplex is a Transmitter)"
	::= { muxConfigurationEntry 6 }

muxFreqOut  OBJECT-TYPE
	SYNTAX     Integer32
	MAX-ACCESS read-write
	STATUS     current
	DESCRIPTION 
		"Output frequency"
	::= { muxConfigurationEntry 7 }

muxTNetworkMode  OBJECT-TYPE
	SYNTAX     INTEGER {
		sfn (1),
		mfn (2),
		unknown (3)
	}
	MAX-ACCESS read-write
	STATUS     current
	DESCRIPTION 
		"Network Mode (SFN/MFN) for DVB-T transmitter (or DVB-T2 module working on T mode)
		
		1: SFN
		2: MFN
		3: unkown (Gap-Filler / Retransmitter / DVB-T2)
		"
	::= { muxConfigurationEntry 8 }

muxAutoMIP  OBJECT-TYPE
	SYNTAX     INTEGER {
		autoMIPon (1),
		autoMIPoff (2),
		notApply (3)
	}
	MAX-ACCESS read-write
	STATUS     current
	DESCRIPTION 
		"Auto MIP On/Off
		For Retransmitter Module is Auto-Configuration (web tag)
		
		1: On
		2: Off
		3: N/A (The multiplex is a GapFiller)
		
		
		"
	::= { muxConfigurationEntry 9 }

muxFFTSize  OBJECT-TYPE
	SYNTAX     INTEGER {
		notApply (1),
		muxFFTSize2K (2),
		muxFFTSize8K (3)
	}
	MAX-ACCESS read-write
	STATUS     current
	DESCRIPTION 
		"OFDM transmission mode (2K, 8K) 
		
		1: N/A (The multiplex is a GapFiller)
		2: 2K-OFDM
		3: 8K-OFDM"
	::= { muxConfigurationEntry 10 }

muxGuardInterval  OBJECT-TYPE
	SYNTAX     INTEGER {
		notApply (1),
		guardIntervalDIV32 (2),
		guardIntervalDIV16 (3),
		guardIntervalDIV8 (4),
		guardIntervalDIV4 (5)
	}
	MAX-ACCESS read-write
	STATUS     current
	DESCRIPTION 
		"Guard Interval: 
		1: N/A (The multiplex is a GapFiller)
		2: 1/32 
		3: 1/16 
		4: 1/8 
		5: 1/4"
	::= { muxConfigurationEntry 11 }

muxBW  OBJECT-TYPE
	SYNTAX     INTEGER {
		notApply (1),
		muxBW8MHz (2),
		muxBW7MHz (3),
		muxBW6MHz (4),
		muxBW5MHz (5)
	}
	MAX-ACCESS read-write
	STATUS     current
	DESCRIPTION 
		"OFDM Bandwith (6-7-8 MHz)
		
		1: N/A (The multiplex is a GapFiller and has not an DEEC)
		2: 8 MHz
		3: 7 MHz
		4: 6 MHz
		5: 5 MHz (Only for DEE Canceler)"
	::= { muxConfigurationEntry 12 }

muxConstellation  OBJECT-TYPE
	SYNTAX     INTEGER {
		notApply (1),
		constellationQPSK (2),
		constellation16QAM (3),
		constellation64QAM (4)
	}
	MAX-ACCESS read-write
	STATUS     current
	DESCRIPTION 
		"QAM Constellation
		
		1: N/A (The multiplex is a GapFiller)
		2: QPSK 
		3: 16-QAM 
		4: 64-QAM"
	::= { muxConfigurationEntry 13 }

muxFEC  OBJECT-TYPE
	SYNTAX     INTEGER {
		notApply (1),
		fec1div2 (2),
		fec2div3 (3),
		fec3div4 (4),
		fec5div6 (5),
		fec7div8 (6)
	}
	MAX-ACCESS read-write
	STATUS     current
	DESCRIPTION 
		"FEC (Code Rate) 
		
		1: N/A (The multiplex is a GapFiller)
		2: 1/2 
		3: 2/3 
		4: 3/4
		5: 5/6 
		6: 7/8"
	::= { muxConfigurationEntry 14 }

muxUserLocalDelay  OBJECT-TYPE
	SYNTAX     Integer32 (-20000..20000)
	UNITS 	"usec/10"
	MAX-ACCESS read-write
	STATUS     current
	DESCRIPTION 
		"User Delay in 0.1 microseconds steps"
	::= { muxConfigurationEntry 15 }

muxMutes  OBJECT-TYPE
	SYNTAX     Mutes
	MAX-ACCESS read-write
	STATUS     current
	DESCRIPTION 
		"This bits arrays indicates that 
		
		Each bit indicates that cause mute the transmitter output.
		
		bit - mute if
		1 - there are errors in the MIP
		2 - there aren't MIP
		3 - there aren't GPS reference
		4 - there aren't ASI input
		5 - there are MPEG overflow
		6 - there are SFN error
		"
	::= { muxConfigurationEntry 16 }

muxVcorr1  OBJECT-TYPE
	SYNTAX     Integer32
	MAX-ACCESS read-write
	STATUS     current
	DESCRIPTION 
		"Precorrector 1 Voltage "
	::= { muxConfigurationEntry 17 }

muxVcorr2  OBJECT-TYPE
	SYNTAX     Integer32
	MAX-ACCESS read-write
	STATUS     deprecated
	DESCRIPTION 
		"Precorrector 2 Voltage "
	::= { muxConfigurationEntry 18 }

muxHysteresis  OBJECT-TYPE
	SYNTAX     Integer32
	UNITS 	"dsec"
	MAX-ACCESS read-write
	STATUS     deprecated
	DESCRIPTION 
		"Time to validate the alarm status."
	::= { muxConfigurationEntry 19 }

muxCBERwarningLevel  OBJECT-TYPE
	SYNTAX     OCTET STRING (SIZE(9))
	MAX-ACCESS read-write
	STATUS     current
	DESCRIPTION 
		"CBER level for warning alarm"
	::= { muxConfigurationEntry 20 }

muxCBERcriticalLevel  OBJECT-TYPE
	SYNTAX     OCTET STRING (SIZE(9))
	MAX-ACCESS read-write
	STATUS     current
	DESCRIPTION 
		"CBER level for critical alarm"
	::= { muxConfigurationEntry 21 }

muxTrapsConfiguration  OBJECT-TYPE
	SYNTAX     BitsStates
	MAX-ACCESS read-write
	STATUS     deprecated
	DESCRIPTION 
		"Bits array for enable/disable the traps from this module
		
		For each bit:
		     False: disable
		     true: enable
		
		The bits are represented in BitsStates convection"
	::= { muxConfigurationEntry 22 }

muxVBERwarningLevel  OBJECT-TYPE
	SYNTAX     OCTET STRING (SIZE(9))
	MAX-ACCESS read-write
	STATUS     current
	DESCRIPTION 
		"CBER level for warning alarm"
	::= { muxConfigurationEntry 23 }

muxVBERcriticalLevel  OBJECT-TYPE
	SYNTAX     OCTET STRING (SIZE(9))
	MAX-ACCESS read-write
	STATUS     current
	DESCRIPTION 
		"CBER level for critical alarm"
	::= { muxConfigurationEntry 24 }

muxEchoAdaptation  OBJECT-TYPE
	SYNTAX     INTEGER {
		on (1),
		off (2),
		notApply (3)
	}
	MAX-ACCESS read-write
	STATUS     deprecated
	DESCRIPTION 
		"Switch on/off echo adaptations. Reduce the transmited power if the echo is high.
		
		1: On
		2: Off
		3: N/A this mux is a transmisor or the version is not compatible
		"
	::= { muxConfigurationEntry 25 }

muxAsiInput  OBJECT-TYPE
	SYNTAX     INTEGER {
		manualAsi1 (1),
		manualAsi2 (2),
		auto (3),
		autoPriority1 (4),
		notApply (5)
	}
	MAX-ACCESS read-write
	STATUS     current
	DESCRIPTION 
		"ASI selection:
		
		1: Manual ASI 1
		2: Manual ASI 2
		3: Automatic without priority
		4: Automatic  with priority 1
		5: N/A this mux is a gap-filler or the version is not comptible"
	::= { muxConfigurationEntry 26 }

muxUmbralTemp  OBJECT-TYPE
	SYNTAX     Integer32 (0..99)
	MAX-ACCESS read-write
	STATUS     current
	DESCRIPTION 
		"Alarm temperature threshold"
	::= { muxConfigurationEntry 27 }

muxConfigurationRowIndex  OBJECT-TYPE
	SYNTAX     Integer32 (1..30)
	MAX-ACCESS read-only
	STATUS     current
	DESCRIPTION 
		"MUX index (readable)"
	::= { muxConfigurationEntry 28 }

muxRfMute  OBJECT-TYPE
	SYNTAX     TruthValue
	MAX-ACCESS read-write
	STATUS     current
	DESCRIPTION 
		"The RF output can be muted with this variable."
	::= { muxConfigurationEntry 29 }

muxTCellIdEnable  OBJECT-TYPE
	SYNTAX     TruthValue
	MAX-ACCESS read-write
	STATUS     current
	DESCRIPTION 
		"Enable/Disable Cell ID"
	::= { muxConfigurationEntry 30 }

muxTCellIdValue  OBJECT-TYPE
	SYNTAX     Integer32 (0..65535)
	MAX-ACCESS read-write
	STATUS     current
	DESCRIPTION 
		"Cell ID value (if Cell ID is enabled)"
	::= { muxConfigurationEntry 31 }

muxDeecWindow1Stat  OBJECT-TYPE
	SYNTAX     TruthValue
	MAX-ACCESS read-write
	STATUS     current
	DESCRIPTION 
		"On/Off Cancellation window 1 on DEE Canceler
		
		If the MUX has not an DEEC, do not apply"
	::= { muxConfigurationEntry 32 }

muxDeecWindow1Speed  OBJECT-TYPE
	SYNTAX     INTEGER {
		speed0 (0),
		speed1 (1),
		speed2 (2),
		speed3 (3),
		speed4 (4),
		speed5 (5),
		speed6 (6),
		speed7 (7)
	}
	MAX-ACCESS read-write
	STATUS     current
	DESCRIPTION 
		"Speed  Cancellation window 1 on DEE Canceler
		
		If the MUX has not an DEEC, do not apply"
	::= { muxConfigurationEntry 33 }

-- This is an time aproximation from 0 up to 255 values.
-- So you can set an value (0,5 .... 32,1) and EEC willl use an aproximate value.

muxDeecWindow1Position  OBJECT-TYPE
	SYNTAX     Integer32
	UNITS 	"usec/10"
	MAX-ACCESS read-write
	STATUS     current
	DESCRIPTION 
		"Cancellation window 1 Position for DEE Canceler
		
		Position in 0.1 microseconds steps
		
		From 5 (0.5 usec) up to 316 (31.6 usec)
		
		If the MUX has not an DEEC, do not apply"
	::= { muxConfigurationEntry 34 }

muxDeecWindow2Speed  OBJECT-TYPE
	SYNTAX     INTEGER {
		speed0 (0),
		speed1 (1),
		speed2 (2),
		speed3 (3),
		speed4 (4),
		speed5 (5),
		speed6 (6),
		speed7 (7)
	}
	MAX-ACCESS read-write
	STATUS     current
	DESCRIPTION 
		"Speed  Cancellation window 2 on DEE Canceler
		
		If the MUX has not an DEEC, do not apply"
	::= { muxConfigurationEntry 35 }

-- This is an time aproximation from 0 up to 255 values.
-- So you can set an value (0,5 .... 32,1) and EEC willl use an aproximate value.

muxDeecWindow2Position  OBJECT-TYPE
	SYNTAX     Integer32
	UNITS 	"usec/10"
	MAX-ACCESS read-write
	STATUS     current
	DESCRIPTION 
		"Cancellation window 2 Position for DEE Canceler
		
		Position in 0.1 microseconds steps
		
		From 50 (5 usec) up to 361 (36.1 usec)
		
		If the MUX has not an DEEC, do not apply"
	::= { muxConfigurationEntry 36 }

muxDeecWindow3Stat  OBJECT-TYPE
	SYNTAX     TruthValue
	MAX-ACCESS read-write
	STATUS     current
	DESCRIPTION 
		"On/Off Cancellation window 3 on DEE Canceler
		
		If the MUX has not an DEEC, do not apply"
	::= { muxConfigurationEntry 37 }

muxDeecWindow3Speed  OBJECT-TYPE
	SYNTAX     INTEGER {
		speed0 (0),
		speed1 (1),
		speed2 (2),
		speed3 (3),
		speed4 (4),
		speed5 (5),
		speed6 (6),
		speed7 (7)
	}
	MAX-ACCESS read-write
	STATUS     current
	DESCRIPTION 
		"Speed  Cancellation window 1 on DEE Canceler
		
		If the MUX has not an DEEC, do not apply"
	::= { muxConfigurationEntry 38 }

-- This is an time aproximation from 0 up to 255 values.
-- So you can set an value (0,5 .... 32,1) and EEC willl use an aproximate value.

muxDeecWindow3Position  OBJECT-TYPE
	SYNTAX     Integer32
	UNITS 	"usec/10"
	MAX-ACCESS read-write
	STATUS     current
	DESCRIPTION 
		"Cancellation window 3 Position for DEE Canceler
		
		Position in 0.1 microseconds steps
		
		From 5 (0.5 usec) up to 316 (31.6 usec)
		
		If the MUX has not an DEEC, do not apply"
	::= { muxConfigurationEntry 39 }

muxEchoCancelerOn  OBJECT-TYPE
	SYNTAX     INTEGER {
		muxEchoCancelerOn (1),
		muxEchoCancelerOff (2),
		notApply (3)
	}
	MAX-ACCESS read-write
	STATUS     current
	DESCRIPTION 
		"Echo Canceler On/Off
		
		MUX trasnsmitter will be notApply(3).
		
		1: Echo Canceler is On
		2: Echo Canceler is Off
		3: NotApply"
	::= { muxConfigurationEntry 40 }

muxConfigurationType  OBJECT-TYPE
	SYNTAX     INTEGER {
		dvbt (1),
		dvbt2 (2),
		unknown (3),
		notApply (4)
	}
	MAX-ACCESS read-write
	STATUS     current
	DESCRIPTION 
		"DVB-T / DVB-T2 selector
		
		1: DVB-T
		2: DVB-T2
		3: Unknown (Gap-Filler)
		4: Not Apply (dummy)"
	::= { muxConfigurationEntry 43 }

muxUmbralTempFPGA  OBJECT-TYPE
	SYNTAX     Integer32 (-1|0..99)
	UNITS 	"Celsius"
	MAX-ACCESS read-write
	STATUS     current
	DESCRIPTION 
		"Alarm temperature (FPGA) threshold
		
		Only available for T/T2 Transmitter.
		
		-1: N/A this mux is a dummy or not T/T2 Transmitter"
	DEFVAL  { 65 }
	::= { muxConfigurationEntry 44 }

muxTcfgPPSedge  OBJECT-TYPE
	SYNTAX     INTEGER {
		rising (1),
		falling (2),
		notApply (3)
	}
	MAX-ACCESS read-write
	STATUS     current
	DESCRIPTION 
		"PPS edge:
		
		1: rising
		2: falling
		3: notApply
		"
	::= { muxConfigurationEntry 45 }

muxTtxId  OBJECT-TYPE
	SYNTAX     Integer32 (-1|0..65535)
	MAX-ACCESS read-write
	STATUS     current
	DESCRIPTION 
		"DVB-T trasmitter ID"
	::= { muxConfigurationEntry 46 }

muxUnitType  OBJECT-TYPE
	SYNTAX     DisplayString
	MAX-ACCESS read-only
	STATUS     current
	DESCRIPTION 
		"Amplifier type"
	::= { muxConfigurationEntry 47 }

muxReflectedPowerthreshold  OBJECT-TYPE
	SYNTAX     Integer32 (-6..-2)
	MAX-ACCESS read-write
	STATUS     current
	DESCRIPTION 
		"Reflected Powerthreshold"
	::= { muxConfigurationEntry 48 }

muxExtendedDeecMode OBJECT-TYPE
	SYNTAX     INTEGER{
		extendedOn(1),
		extendedOff(2),
		notApply(3)
	}	
	MAX-ACCESS read-write
	STATUS     current
	DESCRIPTION 
		"DEEC Extended mode"
	::= { muxConfigurationEntry 49 }

muxMeasurementTable  OBJECT-TYPE
	SYNTAX SEQUENCE OF MuxMeasurementEntry
	MAX-ACCESS not-accessible
	STATUS     current
	DESCRIPTION 
		"This table contains the status information of multiplex connected to the system."
	::= { mux 2 }

muxMeasurementEntry  OBJECT-TYPE
	SYNTAX 	MuxMeasurementEntry
	MAX-ACCESS not-accessible
	STATUS     current
	DESCRIPTION 
		"Each row is the Multiplex information. 1 multiplex 
		could be Gap Filler or Transmitter system."
	INDEX { muxMeasurementIndex }
	::= { muxMeasurementTable 1 }

MuxMeasurementEntry ::= SEQUENCE {
	muxMeasurementIndex
		Integer32,
	muxMeasurementDescription
		DisplayString,
	muxChannel
		Integer32,
	muxChannelBER
		DisplayString,
	muxTransmittedPower
		DisplayString,
	muxReflectedPower
		DisplayString,
	muxTemperature
		DisplayString,
	muxIdT1
		DisplayString,
	muxIdT2
		DisplayString,
	muxNetworkMaxDelay
		DisplayString,
	muxLocalMarginDelay
		DisplayString,
	muxAlarmStatus
		BitsStates,
	muxViterbiBER
		DisplayString,
	echoMG
		DisplayString,
	echoAdaptationFactor
		DisplayString,
	asi1Status
		INTEGER,
	asi2Status
		INTEGER,
	muxCtrlAddressMeasurerement
		Integer32,
	muxMeasurementRowIndex
		Integer32,
	muxFan1ServiceTime
		Integer32,
	muxFan2ServiceTime
		Integer32,
	muxFan3ServiceTime
		Integer32,
	muxMeasurementType
		INTEGER,
	muxTemperatureFpga
		DisplayString,
	muxTimeOffset
		DisplayString,
	muxInputLevel
		DisplayString,
	muxSelectedAsi
		INTEGER,
	muxSeamlessStatus
		INTEGER
}

muxMeasurementIndex  OBJECT-TYPE
	SYNTAX     Integer32 (1..30)
	MAX-ACCESS not-accessible
	STATUS     current
	DESCRIPTION 
		"MUX index"
	::= { muxMeasurementEntry 1 }

muxMeasurementDescription  OBJECT-TYPE
	SYNTAX     DisplayString
	MAX-ACCESS read-only
	STATUS     current
	DESCRIPTION 
		"MUX description. The module could be 
		
		REM: GapFiller DAE
		DEEC: GapFiller DEEC
		MOD: Transmitter.
		REG: retransmitter"
	::= { muxMeasurementEntry 2 }

muxChannel  OBJECT-TYPE
	SYNTAX     Integer32 (21..69)
	MAX-ACCESS read-only
	STATUS     current
	DESCRIPTION 
		"Output Channel"
	::= { muxMeasurementEntry 3 }

muxChannelBER  OBJECT-TYPE
	SYNTAX     DisplayString
	MAX-ACCESS read-only
	STATUS     current
	DESCRIPTION 
		"Channel BER"
	::= { muxMeasurementEntry 4 }

muxTransmittedPower  OBJECT-TYPE
	SYNTAX     DisplayString
	UNITS 	"W"
	MAX-ACCESS read-only
	STATUS     current
	DESCRIPTION 
		"Transmitted Power (W)"
	::= { muxMeasurementEntry 5 }

muxReflectedPower  OBJECT-TYPE
	SYNTAX     DisplayString
	UNITS 	"W"
	MAX-ACCESS read-only
	STATUS     current
	DESCRIPTION 
		"Reflected Power (W)"
	::= { muxMeasurementEntry 6 }

muxTemperature  OBJECT-TYPE
	SYNTAX     DisplayString
	UNITS 	"C"
	MAX-ACCESS read-only
	STATUS     current
	DESCRIPTION 
		"Temperature"
	::= { muxMeasurementEntry 7 }

muxIdT1  OBJECT-TYPE
	SYNTAX     DisplayString
	UNITS 	"mA"
	MAX-ACCESS read-only
	STATUS     current
	DESCRIPTION 
		"Output Stage Transistor 1 Drain Current"
	::= { muxMeasurementEntry 8 }

muxIdT2  OBJECT-TYPE
	SYNTAX     DisplayString
	UNITS 	"mA"
	MAX-ACCESS read-only
	STATUS     current
	DESCRIPTION 
		"Output Stage Transistor 2 Drain Current"
	::= { muxMeasurementEntry 9 }

muxNetworkMaxDelay  OBJECT-TYPE
	SYNTAX     DisplayString
	UNITS 	"usec"
	MAX-ACCESS read-only
	STATUS     current
	DESCRIPTION 
		"Maximum Network Delay (microseconds)"
	::= { muxMeasurementEntry 10 }

muxLocalMarginDelay  OBJECT-TYPE
	SYNTAX     DisplayString
	UNITS 	"usec"
	MAX-ACCESS read-only
	STATUS     current
	DESCRIPTION 
		"Margin delay necessary for synchronization. Steps of 100ns."
	::= { muxMeasurementEntry 11 }

muxAlarmStatus  OBJECT-TYPE
	SYNTAX     BitsStates
	MAX-ACCESS read-only
	STATUS     deprecated
	DESCRIPTION 
		"Alarm bits states for this module."
	::= { muxMeasurementEntry 12 }

muxViterbiBER  OBJECT-TYPE
	SYNTAX     DisplayString
	MAX-ACCESS read-only
	STATUS     current
	DESCRIPTION 
		"Channel BER"
	::= { muxMeasurementEntry 13 }

echoMG  OBJECT-TYPE
	SYNTAX     DisplayString
	MAX-ACCESS read-only
	STATUS     current
	DESCRIPTION 
		"Echo Gain Margin"
	::= { muxMeasurementEntry 14 }

echoAdaptationFactor  OBJECT-TYPE
	SYNTAX     DisplayString
	MAX-ACCESS read-only
	STATUS     current
	DESCRIPTION 
		"Echo Adaptation Factor is the power reduction factor."
	::= { muxMeasurementEntry 15 }

asi1Status  OBJECT-TYPE
	SYNTAX     INTEGER {
		asiOk (1),
		asiError (2),
		noMIP (3),
		noMPEG (4),
		noCRC (5),
		notApply (6)
	}
	MAX-ACCESS read-only
	STATUS     current
	DESCRIPTION 
		"ASI 1 status:
		
		1: ASI OK
		2: asiError
		3: No MIP
		4: No MPEG
		5: No CRC
		6: N/A. This mux is a gap-filler or version is not compatible"
	::= { muxMeasurementEntry 16 }

asi2Status  OBJECT-TYPE
	SYNTAX     INTEGER {
		asiOk (1),
		asiError (2),
		noMIP (3),
		noMPEG (4),
		noCRC (5),
		notApply (6)
	}
	MAX-ACCESS read-only
	STATUS     current
	DESCRIPTION 
		"ASI 2 status:
		
		1: ASI OK
		2: asiError
		3: No MIP
		4: No MPEG
		5: No CRC
		6: N/A. This mux is a gap-filler or version is not compatible"
	::= { muxMeasurementEntry 17 }

muxCtrlAddressMeasurerement  OBJECT-TYPE
	SYNTAX     Integer32 (1..15|101..115)
	MAX-ACCESS read-only
	STATUS     current
	DESCRIPTION 
		"Control address"
	::= { muxMeasurementEntry 18 }

muxMeasurementRowIndex  OBJECT-TYPE
	SYNTAX     Integer32 (1..30)
	MAX-ACCESS read-only
	STATUS     current
	DESCRIPTION 
		"MUX index (readable)"
	::= { muxMeasurementEntry 19 }

muxFan1ServiceTime  OBJECT-TYPE
	SYNTAX     Integer32
	MAX-ACCESS read-only
	STATUS     current
	DESCRIPTION 
		"Fan 1 services time (hours).
		If this value is -1, this time is not available
		This value is only available in Compact Range and 50W broadcast"
	::= { muxMeasurementEntry 20 }

muxFan2ServiceTime  OBJECT-TYPE
	SYNTAX     Integer32
	MAX-ACCESS read-only
	STATUS     obsolete
	DESCRIPTION 
		"Fan 2 services time (hours).
		This value is useful for 50W power amplifier."
	::= { muxMeasurementEntry 21 }

muxFan3ServiceTime  OBJECT-TYPE
	SYNTAX     Integer32
	MAX-ACCESS read-only
	STATUS     obsolete
	DESCRIPTION 
		"Fan 3 services time (hours).
		This value is useful for 50W power amplifier."
	::= { muxMeasurementEntry 22 }

muxMeasurementType  OBJECT-TYPE
	SYNTAX     INTEGER {
		dvbt (1),
		dvbt2 (2),
		unknown (3),
		notApply (4)
	}
	MAX-ACCESS read-only
	STATUS     current
	DESCRIPTION 
		"DVB-T / DVB-T2 selector
		
		1: DVB-T
		2: DVB-T2
		3: Unknown (Gap-Filler)
		4: Not Apply (dummy)"
	::= { muxMeasurementEntry 23 }

muxTemperatureFpga  OBJECT-TYPE
	SYNTAX     DisplayString
	MAX-ACCESS read-only
	STATUS     current
	DESCRIPTION 
		"FPGA Temperature
		
		NULL: N/A"
	::= { muxMeasurementEntry 24 }

muxTimeOffset  OBJECT-TYPE
	SYNTAX     DisplayString
	MAX-ACCESS read-only
	STATUS     current
	DESCRIPTION 
		"Time Offset for transmitter. 
		
		DVB-T: MIP Offset
		DVB-T2: Individual Addressing Offset
		NULL: N/A (The multiplex is a Dummy)"
	::= { muxMeasurementEntry 25 }

muxInputLevel  OBJECT-TYPE
	SYNTAX     DisplayString
	MAX-ACCESS read-only
	STATUS     current
	DESCRIPTION 
		"Signal input level for Gap-filler"
	::= { muxMeasurementEntry 26 }

muxSelectedAsi  OBJECT-TYPE
	SYNTAX     INTEGER{
		selectedAsi1(1),
		selectedAsi2(2),
		unselectedAsis(3)
	}	
	MAX-ACCESS read-only
	STATUS     current
	DESCRIPTION 
		"Selected ASI input for Transmitter"
	::= { muxMeasurementEntry 27 }

muxSeamlessStatus  OBJECT-TYPE
	SYNTAX     INTEGER{
		seamlesOk(1),
		seamlesNok(2),
		notApply(3)
	}	
	MAX-ACCESS read-only
	STATUS     current
	DESCRIPTION 
		"Seamless status for Transmitter"
	::= { muxMeasurementEntry 28 }

muxVersionTable  OBJECT-TYPE
	SYNTAX SEQUENCE OF MuxVersionEntry
	MAX-ACCESS not-accessible
	STATUS     current
	DESCRIPTION 
		"This table contains the status information of multiplex connected to the system."
	::= { mux 3 }

muxVersionEntry  OBJECT-TYPE
	SYNTAX 	MuxVersionEntry
	MAX-ACCESS not-accessible
	STATUS     current
	DESCRIPTION 
		"Each row is the Multiplex information. 1 multiplex 
		could be Gap Filler or Transmitter system."
	INDEX { muxVersionIndex }
	::= { muxVersionTable 1 }

MuxVersionEntry ::= SEQUENCE {
	muxVersionIndex
		Integer32,
	muxCtrlAddressVersion
		Integer32,
	muxRFoutVersion
		Integer32,
	muxMicrocontrollerVersion
		DisplayString,
	muxMicrocontrollerAmpVersion
		DisplayString,
	muxFPGAVersion
		DisplayString,
	muxVersionRowIndex
		Integer32,
	muxVersionType
		INTEGER
}

muxVersionIndex  OBJECT-TYPE
	SYNTAX     Integer32 (1..30)
	MAX-ACCESS not-accessible
	STATUS     current
	DESCRIPTION 
		"MUX index"
	::= { muxVersionEntry 1 }

muxCtrlAddressVersion  OBJECT-TYPE
	SYNTAX     Integer32 (1..15|101..115)
	MAX-ACCESS read-only
	STATUS     current
	DESCRIPTION 
		"Control address for this module"
	::= { muxVersionEntry 2 }

muxRFoutVersion  OBJECT-TYPE
	SYNTAX     Integer32
	MAX-ACCESS read-only
	STATUS     current
	DESCRIPTION 
		"RF out channel for this multiplex"
	::= { muxVersionEntry 3 }

muxMicrocontrollerVersion  OBJECT-TYPE
	SYNTAX     DisplayString
	MAX-ACCESS read-only
	STATUS     current
	DESCRIPTION 
		"Multiplex firmware version"
	::= { muxVersionEntry 4 }

muxMicrocontrollerAmpVersion  OBJECT-TYPE
	SYNTAX     DisplayString
	MAX-ACCESS read-only
	STATUS     current
	DESCRIPTION 
		"Power amplifier firmware version"
	::= { muxVersionEntry 5 }

muxFPGAVersion  OBJECT-TYPE
	SYNTAX     DisplayString
	MAX-ACCESS read-only
	STATUS     current
	DESCRIPTION 
		"FPGA version"
	::= { muxVersionEntry 6 }

muxVersionRowIndex  OBJECT-TYPE
	SYNTAX     Integer32 (1..30)
	MAX-ACCESS read-only
	STATUS     current
	DESCRIPTION 
		"MUX index (readable)"
	::= { muxVersionEntry 7 }

muxVersionType  OBJECT-TYPE
	SYNTAX     INTEGER {
		dvbt (1),
		dvbt2 (2),
		unknown (3),
		notApply (4)
	}
	MAX-ACCESS read-only
	STATUS     current
	DESCRIPTION 
		"DVB-T / DVB-T2 selector
		
		1: DVB-T
		2: DVB-T2
		3: Unknown (Gap-Filler)
		4: Not Apply (dummy)"
	::= { muxVersionEntry 8 }

muxAlarmsTable  OBJECT-TYPE
	SYNTAX SEQUENCE OF MuxAlarmsEntry
	MAX-ACCESS not-accessible
	STATUS     current
	DESCRIPTION 
		"This table contains the alarm status of each mux."
	::= { mux 4 }

muxAlarmsEntry  OBJECT-TYPE
	SYNTAX 	MuxAlarmsEntry
	MAX-ACCESS not-accessible
	STATUS     current
	DESCRIPTION 
		"Each row is the Multiplex information. 1 multiplex 
		could be Gap Filler or Transmitter system."
	INDEX { muxAlarmsIndex }
	::= { muxAlarmsTable 1 }

MuxAlarmsEntry ::= SEQUENCE {
	muxAlarmsIndex
		Integer32,
	muxCtrlAddressAlarm
		Integer32,
	muxRFoutAlarm
		Integer32,
	muxMajorAlarm
		TruthValue,
	muxMinorAlarm
		TruthValue,
	transmittedPower6dBAlarm
		TruthValue,
	transmittedPower3dBAlarm
		TruthValue,
	trtCurrentsOutRangeAlarm
		TruthValue,
	reflectedPowerAlarm
		TruthValue,
	unLockTSAlarm
		TruthValue,
	noInputSignalAlarm
		TruthValue,
	asi1ErrorAlarm
		TruthValue,
	mipErrorAlarm
		TruthValue,
	ppsAlarm
		TruthValue,
	iFDVBTSignalAlarm
		TruthValue,
	gps10MHzAlarm
		TruthValue,
	powerAmplifierCommunicatAlarm
		TruthValue,
	temperatureAlarm
		TruthValue,
	moduleCommunitacionAlarm
		TruthValue,
	onOffAlarm
		TruthValue,
	cBerAlarm
		TruthValue,
	vBerAlarm
		TruthValue,
	muxAlarmsRowIndex
		Integer32,
	fanAlarm
		TruthValue,
	asi2ErrorAlarm
		TruthValue,
	tsErrorAlarm
		TruthValue,
	t2miErrorAlarm
		TruthValue,
	sfnErrorAlarm
		TruthValue,
	mpeg1ErrorAlarm
		TruthValue,
	mpeg2ErrorAlarm
		TruthValue
}

muxAlarmsIndex  OBJECT-TYPE
	SYNTAX     Integer32 (1..15)
	MAX-ACCESS not-accessible
	STATUS     current
	DESCRIPTION 
		"MUX index"
	::= { muxAlarmsEntry 1 }

muxCtrlAddressAlarm  OBJECT-TYPE
	SYNTAX     Integer32 (1..15|101..115)
	MAX-ACCESS read-only
	STATUS     current
	DESCRIPTION 
		"Control address for this module"
	::= { muxAlarmsEntry 2 }

muxRFoutAlarm  OBJECT-TYPE
	SYNTAX     Integer32
	MAX-ACCESS read-only
	STATUS     current
	DESCRIPTION 
		"RF out channel for this multiplex
		
		Applies to:
		
		Gap Filler DEEC/DAE
		
		Regenerative
		
		Transmitter"
	::= { muxAlarmsEntry 3 }

muxMajorAlarm  OBJECT-TYPE
	SYNTAX     TruthValue
	MAX-ACCESS read-only
	STATUS     current
	DESCRIPTION 
		"Major MUX status
		Applies to:
		
		Gap Filler DEEC/DAE
		
		Regenerative
		
		Transmitter"
	::= { muxAlarmsEntry 4 }

muxMinorAlarm  OBJECT-TYPE
	SYNTAX     TruthValue
	MAX-ACCESS read-only
	STATUS     current
	DESCRIPTION 
		"Minor MUX status
		Applies to:
		
		Gap Filler DEEC/DAE
		
		Regenerative
		
		Transmitter"
	::= { muxAlarmsEntry 5 }

transmittedPower6dBAlarm  OBJECT-TYPE
	SYNTAX     TruthValue
	MAX-ACCESS read-only
	STATUS     current
	DESCRIPTION 
		"Transmitted Power 6dB lower than nominal
		Applies to:
		
		Gap Filler DEEC/DAE
		
		Regenerative
		
		Transmitter"
	::= { muxAlarmsEntry 6 }

transmittedPower3dBAlarm  OBJECT-TYPE
	SYNTAX     TruthValue
	MAX-ACCESS read-only
	STATUS     current
	DESCRIPTION 
		"Transmitted Power 3dB lower than nominal
		Applies to:
		
		Gap Filler DEEC/DAE
		
		Regenerative
		
		Transmitter"
	::= { muxAlarmsEntry 7 }

trtCurrentsOutRangeAlarm  OBJECT-TYPE
	SYNTAX     TruthValue
	MAX-ACCESS read-only
	STATUS     current
	DESCRIPTION 
		"Power amplifier firmware version
		Applies to:
		
		Gap Filler DEEC/DAE
		
		Regenerative
		
		Transmitter"
	::= { muxAlarmsEntry 8 }

reflectedPowerAlarm  OBJECT-TYPE
	SYNTAX     TruthValue
	MAX-ACCESS read-only
	STATUS     current
	DESCRIPTION 
		"Reflected power alarm status
		Applies to:
		
		Gap Filler DEEC/DAE
		
		Regenerative
		
		Transmitter"
	::= { muxAlarmsEntry 9 }

unLockTSAlarm  OBJECT-TYPE
	SYNTAX     TruthValue
	MAX-ACCESS read-only
	STATUS     current
	DESCRIPTION 
		"Unlock Transport Stream alarm
		Applies to:
		
		Gap Filler DEEC/DAE
		
		Regenerative
		
		Transmitter
		
		
		If DVB-T Receiver is installed on Management Module"
	::= { muxAlarmsEntry 10 }

noInputSignalAlarm  OBJECT-TYPE
	SYNTAX     TruthValue
	MAX-ACCESS read-only
	STATUS     current
	DESCRIPTION 
		"No input signal alarm
		Applies to:
		
		Gap Filler DEEC/DAE
		
		Regenerative: Means MPEG ERROR"
	::= { muxAlarmsEntry 11 }

asi1ErrorAlarm  OBJECT-TYPE
	SYNTAX     TruthValue
	MAX-ACCESS read-only
	STATUS     current
	DESCRIPTION 
		"ASI error alarm. 
		General for only T transmitter.
		ASI 1 for T/T2 transmitter"
	::= { muxAlarmsEntry 12 }

mipErrorAlarm  OBJECT-TYPE
	SYNTAX     TruthValue
	MAX-ACCESS read-only
	STATUS     current
	DESCRIPTION 
		"MIP error alarm
		Applies to:
		
		Transmitter"
	::= { muxAlarmsEntry 13 }

ppsAlarm  OBJECT-TYPE
	SYNTAX     TruthValue
	MAX-ACCESS read-only
	STATUS     current
	DESCRIPTION 
		"1 pps alarm status
		Applies to:
		
		Transmitter"
	::= { muxAlarmsEntry 14 }

iFDVBTSignalAlarm  OBJECT-TYPE
	SYNTAX     TruthValue
	MAX-ACCESS read-only
	STATUS     current
	DESCRIPTION 
		"No DVBT IF signal alarm
		Applies to:
		
		Gap Filler DEEC/DAE
		
		Regenerative
		
		Transmitter"
	::= { muxAlarmsEntry 15 }

gps10MHzAlarm  OBJECT-TYPE
	SYNTAX     TruthValue
	MAX-ACCESS read-only
	STATUS     current
	DESCRIPTION 
		"10 MHz alarm
		Applies to:
		
		Transmitter"
	::= { muxAlarmsEntry 16 }

powerAmplifierCommunicatAlarm  OBJECT-TYPE
	SYNTAX     TruthValue
	MAX-ACCESS read-only
	STATUS     obsolete
	DESCRIPTION 
		"Power Amplifier communication"
	::= { muxAlarmsEntry 17 }

temperatureAlarm  OBJECT-TYPE
	SYNTAX     TruthValue
	MAX-ACCESS read-only
	STATUS     current
	DESCRIPTION 
		"Temperature alarm
		Applies to:
		
		Gap Filler DEEC/DAE
		
		Regenerative
		
		Transmitter"
	::= { muxAlarmsEntry 18 }

moduleCommunitacionAlarm  OBJECT-TYPE
	SYNTAX     TruthValue
	MAX-ACCESS read-only
	STATUS     current
	DESCRIPTION 
		"Communication alarm
		Applies to:
		
		Gap Filler DEEC/DAE
		
		Regenerative
		
		Transmitter"
	::= { muxAlarmsEntry 19 }

onOffAlarm  OBJECT-TYPE
	SYNTAX     TruthValue
	MAX-ACCESS read-only
	STATUS     deprecated
	DESCRIPTION 
		"MUX status"
	::= { muxAlarmsEntry 20 }

cBerAlarm  OBJECT-TYPE
	SYNTAX     TruthValue
	MAX-ACCESS read-only
	STATUS     current
	DESCRIPTION 
		"Channel BER (pre-Viterbi) alarm status
		Applies to:
		
		Gap Filler DEEC/DAE
		
		Regenerative
		
		Transmitter
		
		
		If DVB-T Receiver is installed on Management Module"
	::= { muxAlarmsEntry 21 }

vBerAlarm  OBJECT-TYPE
	SYNTAX     TruthValue
	MAX-ACCESS read-only
	STATUS     current
	DESCRIPTION 
		"VBER (post-Viterbi) alarm status
		Applies to:
		
		Gap Filler DEEC/DAE
		
		Regenerative
		
		Transmitter
		
		
		If DVB-T Receiver is installed on Management Module"
	::= { muxAlarmsEntry 22 }

muxAlarmsRowIndex  OBJECT-TYPE
	SYNTAX     Integer32 (1..30)
	MAX-ACCESS read-only
	STATUS     current
	DESCRIPTION 
		"MUX index (readable)"
	::= { muxAlarmsEntry 23 }

fanAlarm  OBJECT-TYPE
	SYNTAX     TruthValue
	MAX-ACCESS read-only
	STATUS     obsolete
	DESCRIPTION 
		"Fan alarm.
		This value is useful for 50W power amplifier."
	::= { muxAlarmsEntry 24 }

asi2ErrorAlarm  OBJECT-TYPE
	SYNTAX     TruthValue
	MAX-ACCESS read-only
	STATUS     current
	DESCRIPTION 
		"ASI 2 error alarm."
	::= { muxAlarmsEntry 25 }

tsErrorAlarm  OBJECT-TYPE
	SYNTAX     TruthValue
	MAX-ACCESS read-only
	STATUS     current
	DESCRIPTION 
		"TS error alarm. Only available for T/T2 transmitter."
	::= { muxAlarmsEntry 26 }

t2miErrorAlarm  OBJECT-TYPE
	SYNTAX     TruthValue
	MAX-ACCESS read-only
	STATUS     current
	DESCRIPTION 
		"T2MI error alarm. Only available for T/T2 transmitter."
	::= { muxAlarmsEntry 27 }

sfnErrorAlarm  OBJECT-TYPE
	SYNTAX     TruthValue
	MAX-ACCESS read-only
	STATUS     current
	DESCRIPTION 
		"SFN error alarm. Only available for T/T2 transmitter."
	::= { muxAlarmsEntry 28 }

mpeg1ErrorAlarm  OBJECT-TYPE
	SYNTAX     TruthValue
	MAX-ACCESS read-only
	STATUS     current
	DESCRIPTION 
		"MPEG 1 error alarm."
	::= { muxAlarmsEntry 29 }

mpeg2ErrorAlarm  OBJECT-TYPE
	SYNTAX     TruthValue
	MAX-ACCESS read-only
	STATUS     current
	DESCRIPTION 
		"MPEG 2 error alarm."
	::= { muxAlarmsEntry 30 }

muxEnableAlarmTable  OBJECT-TYPE
	SYNTAX SEQUENCE OF MuxEnableAlarmEntry
	MAX-ACCESS not-accessible
	STATUS     current
	DESCRIPTION 
		"This table contains the enable alarm status for each MUX."
	::= { mux 5 }

muxEnableAlarmEntry  OBJECT-TYPE
	SYNTAX 	MuxEnableAlarmEntry
	MAX-ACCESS not-accessible
	STATUS     current
	DESCRIPTION 
		"Each row is the Multiplex information. 1 multiplex  could be Gap Filler or Transmitter system."
	INDEX { muxEnableAlarmIndex }
	::= { muxEnableAlarmTable 1 }

MuxEnableAlarmEntry ::= SEQUENCE {
	muxEnableAlarmIndex
		Integer32,
	muxCtrlAddressEnableAlarm
		Integer32,
	muxRFoutEnableAlarm
		Integer32,
	transmittedPower6dBEnableAlarm
		TruthValue,
	transmittedPower3dBEnableAlarm
		TruthValue,
	trtCurrentsOutRangeEnableAlarm
		TruthValue,
	reflectedPowerEnableAlarm
		TruthValue,
	unLockTSEnableAlarm
		TruthValue,
	noInputSignalEnableAlarm
		TruthValue,
	asi1ErrorEnableAlarm
		TruthValue,
	mipErrorEnableAlarm
		TruthValue,
	ppsEnableAlarm
		TruthValue,
	iFDVBTSignalEnableAlarm
		TruthValue,
	gps10MHzEnableAlarm
		TruthValue,
	powerAmplifierCommunicatEnAlarm
		TruthValue,
	muxCBerEnableAlarm
		TruthValue,
	temperatureEnableAlarm
		TruthValue,
	muxVBerEnableAlarm
		TruthValue,
	muxEnableTrapRowAlarm
		Integer32,
	fanEnableAlarm
		TruthValue,
	communicationEnableAlarm
		TruthValue,
	asi2EnableAlarm
		TruthValue,
	tsEnableAlarm
		TruthValue,
	t2miEnableAlarm
		TruthValue,
	sfnErrorEnableAlarm
		TruthValue,
	mpeg1EnableAlarm
		TruthValue,
	mpeg2EnableAlarm
		TruthValue
}

muxEnableAlarmIndex  OBJECT-TYPE
	SYNTAX     Integer32 (1..15)
	MAX-ACCESS not-accessible
	STATUS     current
	DESCRIPTION 
		"MUX index"
	::= { muxEnableAlarmEntry 1 }

muxCtrlAddressEnableAlarm  OBJECT-TYPE
	SYNTAX     Integer32 (1..15|101..115)
	MAX-ACCESS read-only
	STATUS     current
	DESCRIPTION 
		"Control address for this module"
	::= { muxEnableAlarmEntry 2 }

muxRFoutEnableAlarm  OBJECT-TYPE
	SYNTAX     Integer32
	MAX-ACCESS read-only
	STATUS     current
	DESCRIPTION 
		"RF out channel for this multiplex
		Applies to:
		
		Gap Filler DEEC/DAE
		
		Regenerative
		
		Transmitter"
	::= { muxEnableAlarmEntry 3 }

transmittedPower6dBEnableAlarm  OBJECT-TYPE
	SYNTAX     TruthValue
	MAX-ACCESS read-write
	STATUS     current
	DESCRIPTION 
		"Enable/Disable alarm: Transmitted Power 6dB lower than nominal
		Applies to:
		
		Gap Filler DEEC/DAE
		
		Regenerative
		
		Transmitter"
	::= { muxEnableAlarmEntry 4 }

transmittedPower3dBEnableAlarm  OBJECT-TYPE
	SYNTAX     TruthValue
	MAX-ACCESS read-write
	STATUS     current
	DESCRIPTION 
		"Enable/Disable alarm: Transmitted Power 3dB lower than nominal
		Applies to:
		
		Gap Filler DEEC/DAE
		Regenerative
		
		Transmitter"
	::= { muxEnableAlarmEntry 5 }

trtCurrentsOutRangeEnableAlarm  OBJECT-TYPE
	SYNTAX     TruthValue
	MAX-ACCESS read-write
	STATUS     current
	DESCRIPTION 
		"Enable/Disable alarm: Power amplifier firmware version
		Applies to:
		
		Gap Filler DEEC/DAE
		
		Regenerative
		
		Transmitter"
	::= { muxEnableAlarmEntry 6 }

reflectedPowerEnableAlarm  OBJECT-TYPE
	SYNTAX     TruthValue
	MAX-ACCESS read-write
	STATUS     current
	DESCRIPTION 
		"Enable/Disable alarm: Reflected power alarm status
		Applies to:
		
		Gap Filler DEEC/DAE
		
		Regenerative
		
		Transmitter"
	::= { muxEnableAlarmEntry 7 }

unLockTSEnableAlarm  OBJECT-TYPE
	SYNTAX     TruthValue
	MAX-ACCESS read-write
	STATUS     current
	DESCRIPTION 
		"Enable/Disable alarm: Unlock Transport Stream alarm
		Applies to:
		
		Gap Filler DEEC/DAE
		
		Regenerative
		
		Transmitter"
	::= { muxEnableAlarmEntry 8 }

noInputSignalEnableAlarm  OBJECT-TYPE
	SYNTAX     TruthValue
	MAX-ACCESS read-write
	STATUS     current
	DESCRIPTION 
		"Enable/Disable alarm: No input signal alarm
		
		Applies to:
		
		Gap Filler DEEC/DAE
		
		Regenerative: Means MPEG ERROR"
	::= { muxEnableAlarmEntry 9 }

asi1ErrorEnableAlarm  OBJECT-TYPE
	SYNTAX     TruthValue
	MAX-ACCESS read-write
	STATUS     current
	DESCRIPTION 
		"Enable/Disable alarm: ASI error alarm
		Applies to:
		
		Transmitter"
	::= { muxEnableAlarmEntry 10 }

mipErrorEnableAlarm  OBJECT-TYPE
	SYNTAX     TruthValue
	MAX-ACCESS read-write
	STATUS     current
	DESCRIPTION 
		"Enable/Disable alarm: MIP error alarm
		Applies to:
		
		Transmitter"
	::= { muxEnableAlarmEntry 11 }

ppsEnableAlarm  OBJECT-TYPE
	SYNTAX     TruthValue
	MAX-ACCESS read-write
	STATUS     current
	DESCRIPTION 
		"Enable/Disable alarm: 1 pps alarm status
		Applies to:
		
		Transmitter"
	::= { muxEnableAlarmEntry 12 }

iFDVBTSignalEnableAlarm  OBJECT-TYPE
	SYNTAX     TruthValue
	MAX-ACCESS read-write
	STATUS     current
	DESCRIPTION 
		"Enable/Disable alarm: No DVBT IF signal alarm
		Applies to:
		
		Gap Filler DEEC/DAE
		
		Regenerative
		
		Transmitter"
	::= { muxEnableAlarmEntry 13 }

gps10MHzEnableAlarm  OBJECT-TYPE
	SYNTAX     TruthValue
	MAX-ACCESS read-write
	STATUS     current
	DESCRIPTION 
		"Enable/Disable alarm: 10 MHz alarm
		Applies to:
		
		Transmitter"
	::= { muxEnableAlarmEntry 14 }

powerAmplifierCommunicatEnAlarm  OBJECT-TYPE
	SYNTAX     TruthValue
	MAX-ACCESS read-write
	STATUS     obsolete
	DESCRIPTION 
		"Enable/Disable alarm: Power Amplifier communication"
	::= { muxEnableAlarmEntry 15 }

muxCBerEnableAlarm  OBJECT-TYPE
	SYNTAX     TruthValue
	MAX-ACCESS read-write
	STATUS     current
	DESCRIPTION 
		"Enable/Disable alarm: Cber trap
		Applies to:
		
		Gap Filler DEEC/DAE
		
		Regenerative
		
		Transmitter
		
		
		If DVB-T Receiver is installed on Management Module"
	::= { muxEnableAlarmEntry 16 }

temperatureEnableAlarm  OBJECT-TYPE
	SYNTAX     TruthValue
	MAX-ACCESS read-write
	STATUS     current
	DESCRIPTION 
		"Enable/Disable alarm: Temperature alarm
		Applies to:
		
		Gap Filler DEEC/DAE
		
		Regenerative
		
		Transmitter"
	::= { muxEnableAlarmEntry 17 }

muxVBerEnableAlarm  OBJECT-TYPE
	SYNTAX     TruthValue
	MAX-ACCESS read-write
	STATUS     current
	DESCRIPTION 
		"Enable/Disable alarm: Cber trap
		Applies to:
		
		Gap Filler DEEC/DAE
		
		Regenerative
		
		Transmitter
		
		
		If DVB-T Receiver is installed on Management Module"
	::= { muxEnableAlarmEntry 18 }

muxEnableTrapRowAlarm  OBJECT-TYPE
	SYNTAX     Integer32 (1..30)
	MAX-ACCESS read-only
	STATUS     current
	DESCRIPTION 
		"MUX index (readable)"
	::= { muxEnableAlarmEntry 19 }

fanEnableAlarm  OBJECT-TYPE
	SYNTAX     TruthValue
	MAX-ACCESS read-write
	STATUS     obsolete
	DESCRIPTION 
		"Enable/Disable Alarm: Fan(s)
		This value is useful for 50W power amplifier."
	::= { muxEnableAlarmEntry 20 }

communicationEnableAlarm  OBJECT-TYPE
	SYNTAX     TruthValue
	MAX-ACCESS read-write
	STATUS     deprecated
	DESCRIPTION 
		"Enable/Disable communication alarm."
	::= { muxEnableAlarmEntry 21 }
	
asi2EnableAlarm  OBJECT-TYPE
	SYNTAX     TruthValue
	MAX-ACCESS read-write
	STATUS     current
	DESCRIPTION 
		"Enable/Disable alarm: ASI 2 error alarm."
	::= { muxEnableAlarmEntry 22 }

tsEnableAlarm  OBJECT-TYPE
	SYNTAX     TruthValue
	MAX-ACCESS read-write
	STATUS     current
	DESCRIPTION 
		"Enable/Disable alarma: TS error alarm. Only available for T/T2 transmitter."
	::= { muxEnableAlarmEntry 23 }

t2miEnableAlarm  OBJECT-TYPE
	SYNTAX     TruthValue
	MAX-ACCESS read-write
	STATUS     current
	DESCRIPTION 
		"Enable/Disable alarma: T2MI error alarm. Only available for T/T2 transmitter."
	::= { muxEnableAlarmEntry 24 }

sfnErrorEnableAlarm  OBJECT-TYPE
	SYNTAX     TruthValue
	MAX-ACCESS read-write
	STATUS     current
	DESCRIPTION 
		"Enable/Disable alarma: SFN error alarm. Only available for T/T2 transmitter."
	::= { muxEnableAlarmEntry 27 }

mpeg1EnableAlarm  OBJECT-TYPE
	SYNTAX     TruthValue
	MAX-ACCESS read-write
	STATUS     current
	DESCRIPTION 
		"Enable/Disable alarm: MPEG 1 error alarm."
	::= { muxEnableAlarmEntry 28 }

mpeg2EnableAlarm  OBJECT-TYPE
	SYNTAX     TruthValue
	MAX-ACCESS read-write
	STATUS     current
	DESCRIPTION 
		"Enable/Disable alarm: MPEG 2 error alarm."
	::= { muxEnableAlarmEntry 29 }
	
muxEnableTrapTable  OBJECT-TYPE
	SYNTAX SEQUENCE OF MuxEnableTrapEntry
	MAX-ACCESS not-accessible
	STATUS     current
	DESCRIPTION 
		"This table contains the enable trap status"
	::= { mux 6 }

muxEnableTrapEntry  OBJECT-TYPE
	SYNTAX 	MuxEnableTrapEntry
	MAX-ACCESS not-accessible
	STATUS     current
	DESCRIPTION 
		"Each row is the Multiplex information. 1 multiplex 
		could be Gap Filler or Transmitter system."
	INDEX { muxEnableTrapIndex }
	::= { muxEnableTrapTable 1 }

MuxEnableTrapEntry ::= SEQUENCE {
	muxEnableTrapIndex
		Integer32,
	muxCtrlAddressEnableTrap
		Integer32,
	muxRFoutEnableTrap
		Integer32,
	muxEnableTrapRowIndex
		Integer32,
	transmittedPower6dBEnableTrap
		TruthValue,
	transmittedPower3dBEnableTrap
		TruthValue,
	trtCurrentsOutRangeEnableTrap
		TruthValue,
	reflectedPowerEnableTrap
		TruthValue,
	unLockTSEnableTrap
		TruthValue,
	noInputSignalEnableTrap
		TruthValue,
	asi1ErrorEnableTrap
		TruthValue,
	mipErrorEnableTrap
		TruthValue,
	ppsEnableTrap
		TruthValue,
	iFDVBTSignalEnableTrap
		TruthValue,
	gps10MHzEnableTrap
		TruthValue,
	powerAmplifierCommunicatEnTrap
		TruthValue,
	muxCBerEnableTrap
		TruthValue,
	temperatureEnableTrap
		TruthValue,
	muxVBerEnableTrap
		TruthValue,
	muxCommunicationEnableTrap
		TruthValue,
	fanEnableTrap
		TruthValue,
	asi2EnableTrap
		TruthValue,
	tsEnableTrap
		TruthValue,
	t2miEnableTrap
		TruthValue,
	sfnErrorEnableTrap
		TruthValue,
	mpeg1EnableTrap
		TruthValue,
	mpeg2EnableTrap
		TruthValue
}

muxEnableTrapIndex  OBJECT-TYPE
	SYNTAX     Integer32 (1..15)
	MAX-ACCESS not-accessible
	STATUS     current
	DESCRIPTION 
		"MUX index"
	::= { muxEnableTrapEntry 1 }

muxCtrlAddressEnableTrap  OBJECT-TYPE
	SYNTAX     Integer32 (1..15|101..115)
	MAX-ACCESS read-only
	STATUS     current
	DESCRIPTION 
		"Control address for this module"
	::= { muxEnableTrapEntry 2 }

muxRFoutEnableTrap  OBJECT-TYPE
	SYNTAX     Integer32
	MAX-ACCESS read-only
	STATUS     current
	DESCRIPTION 
		"RF out channel for this multiplex"
	::= { muxEnableTrapEntry 3 }

muxEnableTrapRowIndex  OBJECT-TYPE
	SYNTAX     Integer32 (1..30)
	MAX-ACCESS read-only
	STATUS     current
	DESCRIPTION 
		"MUX index (readable)"
	::= { muxEnableTrapEntry 4 }

transmittedPower6dBEnableTrap  OBJECT-TYPE
	SYNTAX     TruthValue
	MAX-ACCESS read-write
	STATUS     current
	DESCRIPTION 
		"Enable/Disable trap: Transmitted Power 6dB lower than nominal
		Applies to:
		
		Gap Filler DEEC/DAE
		
		Regenerative
		
		Transmitter"
	::= { muxEnableTrapEntry 5 }

transmittedPower3dBEnableTrap  OBJECT-TYPE
	SYNTAX     TruthValue
	MAX-ACCESS read-write
	STATUS     current
	DESCRIPTION 
		"Enable/Disable trap: Transmitted Power 3dB lower than nominal
		Applies to:
		
		Gap Filler DEEC/DAE
		
		Regenerative
		
		Transmitter"
	::= { muxEnableTrapEntry 6 }

trtCurrentsOutRangeEnableTrap  OBJECT-TYPE
	SYNTAX     TruthValue
	MAX-ACCESS read-write
	STATUS     current
	DESCRIPTION 
		"Enable/Disable trap: Power amplifier firmware version
		Applies to:
		
		Gap Filler DEEC/DAE
		
		Regenerative
		
		Transmitter"
	::= { muxEnableTrapEntry 7 }

reflectedPowerEnableTrap  OBJECT-TYPE
	SYNTAX     TruthValue
	MAX-ACCESS read-write
	STATUS     current
	DESCRIPTION 
		"Enable/Disable trap: Reflected power alarm status
		Applies to:
		
		Gap Filler DEEC/DAE
		
		Regenerative
		
		Transmitter"
	::= { muxEnableTrapEntry 8 }

unLockTSEnableTrap  OBJECT-TYPE
	SYNTAX     TruthValue
	MAX-ACCESS read-write
	STATUS     current
	DESCRIPTION 
		"Enable/Disable trap: Unlock Transport Stream alarm
		Applies to:
		
		Gap Filler DEEC/DAE
		
		Regenerative
		
		Transmitter"
	::= { muxEnableTrapEntry 9 }

noInputSignalEnableTrap  OBJECT-TYPE
	SYNTAX     TruthValue
	MAX-ACCESS read-write
	STATUS     current
	DESCRIPTION 
		"Enable/Disable trap: No input signal alarm
		Applies to:
		
		Gap Filler DEEC/DAE
		
		Regenerative: Means MPEG ERROR"
	::= { muxEnableTrapEntry 10 }

asi1ErrorEnableTrap  OBJECT-TYPE
	SYNTAX     TruthValue
	MAX-ACCESS read-write
	STATUS     current
	DESCRIPTION 
		"Enable/Disable trap: ASI error alarm
		Applies to:
		
		Transmitter"
	::= { muxEnableTrapEntry 11 }

mipErrorEnableTrap  OBJECT-TYPE
	SYNTAX     TruthValue
	MAX-ACCESS read-write
	STATUS     current
	DESCRIPTION 
		"Enable/Disable trap: MIP error alarm
		Applies to:
		
		Transmitter"
	::= { muxEnableTrapEntry 12 }

ppsEnableTrap  OBJECT-TYPE
	SYNTAX     TruthValue
	MAX-ACCESS read-write
	STATUS     current
	DESCRIPTION 
		"Enable/Disable trap: 1 pps alarm status
		Applies to:
		
		Transmitter"
	::= { muxEnableTrapEntry 13 }

iFDVBTSignalEnableTrap  OBJECT-TYPE
	SYNTAX     TruthValue
	MAX-ACCESS read-write
	STATUS     current
	DESCRIPTION 
		"Enable/Disable trap: No DVBT IF signal alarm
		Applies to:
		
		Gap Filler DEEC/DAE
		
		Regenerative
		
		Transmitter"
	::= { muxEnableTrapEntry 14 }

gps10MHzEnableTrap  OBJECT-TYPE
	SYNTAX     TruthValue
	MAX-ACCESS read-write
	STATUS     current
	DESCRIPTION 
		"Enable/Disable trap: 10 MHz alarm
		Applies to:
		
		Transmitter"
	::= { muxEnableTrapEntry 15 }

powerAmplifierCommunicatEnTrap  OBJECT-TYPE
	SYNTAX     TruthValue
	MAX-ACCESS read-write
	STATUS     obsolete
	DESCRIPTION 
		"Enable/Disable trap: Power Amplifier communication"
	::= { muxEnableTrapEntry 16 }

muxCBerEnableTrap  OBJECT-TYPE
	SYNTAX     TruthValue
	MAX-ACCESS read-write
	STATUS     current
	DESCRIPTION 
		"Enable/Disable trap: Cber trap
		Applies to:
		
		Gap Filler DEEC/DAE
		
		Regenerative
		
		Transmitter
		
		
		If DVB-T Receiver is installed on Management Module"
	::= { muxEnableTrapEntry 17 }

temperatureEnableTrap  OBJECT-TYPE
	SYNTAX     TruthValue
	MAX-ACCESS read-write
	STATUS     current
	DESCRIPTION 
		"Enable/Disable trap: Temperature alarm
		Applies to:
		
		Gap Filler DEEC/DAE
		
		Regenerative
		
		Transmitter"
	::= { muxEnableTrapEntry 18 }

muxVBerEnableTrap  OBJECT-TYPE
	SYNTAX     TruthValue
	MAX-ACCESS read-write
	STATUS     current
	DESCRIPTION 
		"Enable/Disable trap: Cber trap
		Applies to:
		
		Gap Filler DEEC/DAE
		
		Regenerative
		
		Transmitter
		
		
		If DVB-T Receiver is installed on Management Module"
	::= { muxEnableTrapEntry 19 }

muxCommunicationEnableTrap  OBJECT-TYPE
	SYNTAX     TruthValue
	MAX-ACCESS read-write
	STATUS     current
	DESCRIPTION 
		"Enable/Disable trap: communication fail trap"
	::= { muxEnableTrapEntry 20 }

fanEnableTrap  OBJECT-TYPE
	SYNTAX     TruthValue
	MAX-ACCESS read-write
	STATUS     obsolete
	DESCRIPTION 
		"Enable/Disable trap: fan(s)
		This value is useful for 50W power amplifier."
	::= { muxEnableTrapEntry 21 }

asi2EnableTrap  OBJECT-TYPE
	SYNTAX     TruthValue
	MAX-ACCESS read-write
	STATUS     current
	DESCRIPTION 
		"Enable/Disable trap: ASI 2 error alarm."
	::= { muxEnableTrapEntry 22 }

tsEnableTrap  OBJECT-TYPE
	SYNTAX     TruthValue
	MAX-ACCESS read-write
	STATUS     current
	DESCRIPTION 
		"Enable/Disable trap: TS error alarm. Only available for T/T2 transmitter."
	::= { muxEnableTrapEntry 23 }

t2miEnableTrap  OBJECT-TYPE
	SYNTAX     TruthValue
	MAX-ACCESS read-write
	STATUS     current
	DESCRIPTION 
		"Enable/Disable trap: T2MI error alarm. Only available for T/T2 transmitter."
	::= { muxEnableTrapEntry 24 }

sfnErrorEnableTrap  OBJECT-TYPE
	SYNTAX     TruthValue
	MAX-ACCESS read-write
	STATUS     current
	DESCRIPTION 
		"Enable/Disable trap: SFN error alarm. Only available for T/T2 transmitter."
	::= { muxEnableTrapEntry 27 }
	
mpeg1EnableTrap  OBJECT-TYPE
	SYNTAX     TruthValue
	MAX-ACCESS read-write
	STATUS     current
	DESCRIPTION 
		"Enable/Disable trap: MPEG 1 error alarm."
	::= { muxEnableTrapEntry 28 }

mpeg2EnableTrap  OBJECT-TYPE
	SYNTAX     TruthValue
	MAX-ACCESS read-write
	STATUS     current
	DESCRIPTION 
		"Enable/Disable trap: MPEG 2 error alarm."
	::= { muxEnableTrapEntry 29 }

muxT2SystemTable  OBJECT-TYPE
	SYNTAX SEQUENCE OF MuxT2SystemEntry
	MAX-ACCESS not-accessible
	STATUS     current
	DESCRIPTION 
		"This table contains the basic information of multiplex connected to the system."
	::= { dvbT2Tables 1 }

muxT2SystemEntry  OBJECT-TYPE
	SYNTAX 	MuxT2SystemEntry
	MAX-ACCESS not-accessible
	STATUS     current
	DESCRIPTION 
		"Each row is the Multiplex information. 1 multiplex 
		could be Gap Filler or Transmitter system."
	INDEX { muxT2SystemIndex }
	::= { muxT2SystemTable 1 }

MuxT2SystemEntry ::= SEQUENCE {
	muxT2SystemIndex
		Integer32,
	muxT2SystemDescription
		DisplayString,
	muxT2SystemCtrlAddress
		Integer32,
	muxT2SystenRowIndex
		Integer32,
	muxT2SystemChannelOut
		Integer32,
	muxT2SystemType
		INTEGER,
	muxT2cfgSource
		INTEGER,
	muxT2cfgNetworkMode
		INTEGER,
	muxT2cfgPPSedge
		INTEGER,
	muxT2cfgBW
		INTEGER,
	muxT2cfgVersion
		INTEGER,
	muxT2frequency
		Integer32,
	muxT2idTxID
		Integer32,
	muxT2idCellID
		Integer32,
	muxT2idNetworkID
		Integer32,
	muxT2idT2SystemID
		Integer32,
	muxT2UserLocalDelay
		Integer32,
	muxT2Pid
		Integer32,
	muxT2TTTx
		DisplayString,
	muxT2Latency
		DisplayString
}

muxT2SystemIndex  OBJECT-TYPE
	SYNTAX     Integer32 (1..36)
	MAX-ACCESS not-accessible
	STATUS     current
	DESCRIPTION 
		"MUX index"
	::= { muxT2SystemEntry 1 }

muxT2SystemDescription  OBJECT-TYPE
	SYNTAX     DisplayString
	MAX-ACCESS read-only
	STATUS     current
	DESCRIPTION 
		"MUX description. The module could be:
		
		GapFiller (REM)
		Transmitter (MOD)
		Profesional GapFiller (PRO)
		Modualtor T/T2 (MT2)"
	::= { muxT2SystemEntry 2 }

muxT2SystemCtrlAddress  OBJECT-TYPE
	SYNTAX     Integer32 (-1|1..18|101..118)
	MAX-ACCESS read-only
	STATUS     current
	DESCRIPTION 
		"Control address:
		
		-1: N/A (The multiplex is a dummy)"
	::= { muxT2SystemEntry 3 }

muxT2SystenRowIndex  OBJECT-TYPE
	SYNTAX     Integer32 (1..36)
	MAX-ACCESS read-only
	STATUS     current
	DESCRIPTION 
		"MUX index (readable)
		
		Usable for row reference"
	::= { muxT2SystemEntry 4 }

muxT2SystemChannelOut  OBJECT-TYPE
	SYNTAX     Integer32 (-1|21..69)
	MAX-ACCESS read-only
	STATUS     current
	DESCRIPTION 
		"Output Channel:
		
		-1: N/A (The multiplex is a Dummy)"
	::= { muxT2SystemEntry 5 }

muxT2SystemType  OBJECT-TYPE
	SYNTAX     INTEGER {
		dvbt (1),
		dvbt2 (2),
		unknown (3),
		notApply (4)
	}
	MAX-ACCESS read-only
	STATUS     current
	DESCRIPTION 
		"DVB-T / DVB-T2 selector
		
		1: DVB-T
		2: DVB-T2
		3: Unknown (Gap-Filler)
		4: Not Apply (dummy)"
	::= { muxT2SystemEntry 6 }

muxT2cfgSource  OBJECT-TYPE
	SYNTAX     INTEGER {
		t2mi (1),
		ts (2),
		unknown (3),
		notApply (4)
	}
	UNITS 	"Hertzios"
	MAX-ACCESS read-write
	STATUS     current
	DESCRIPTION 
		"Source Mode:
		
		1: T2MI
		2: TS
		3: unknown (Gap-Filler)
		4: notApply (Dummy)
		"
	::= { muxT2SystemEntry 7 }

muxT2cfgNetworkMode  OBJECT-TYPE
	SYNTAX     INTEGER {
		sfn (1),
		mfn (2),
		unknown (3),
		notApply (4)
	}
	UNITS 	"Hertzios"
	MAX-ACCESS read-write
	STATUS     current
	DESCRIPTION 
		"Network Mode:
		
		1: SFN
		2: MFN
		3: unknown (Gap-Filler)
		4: notApply (Dummy)
		"
	::= { muxT2SystemEntry 8 }

muxT2cfgPPSedge  OBJECT-TYPE
	SYNTAX     INTEGER {
		rising (1),
		falling (2),
		notApply (3)
	}
	MAX-ACCESS read-write
	STATUS     current
	DESCRIPTION 
		"PPS edge:
		
		1: rising
		2: falling
		3: notApply
		"
	::= { muxT2SystemEntry 9 }

muxT2cfgBW  OBJECT-TYPE
	SYNTAX     INTEGER {
		notApply (1),
		bw10MHz (2),
		bw8MHz (3),
		bw7MHz (4),
		bw6MHz (5),
		bw5MHz (6),
		bw1M7Hz (7)
	}
	MAX-ACCESS read-write
	STATUS     current
	DESCRIPTION 
		"OFDM Bandwith:
		
		1: N/A (The multiplex is a GapFiller/Dummy)
		2: 10 MHz
		3: 8 MHz
		4: 7 MHz
		5: 6 MHz
		6: 5 MHz
		7: 1.7 MHz
		
		"
	::= { muxT2SystemEntry 10 }

muxT2cfgVersion  OBJECT-TYPE
	SYNTAX     INTEGER {
		notApply (1),
		v111 (2),
		v121 (3),
		v131 (4)
	}
	MAX-ACCESS read-write
	STATUS     current
	DESCRIPTION 
		"T2 Version
		
		1: Not Apply
		2: Version 1_1_1
		3: Version 1_2_1
		4: Version 1_3_1
		"
	::= { muxT2SystemEntry 11 }

muxT2frequency  OBJECT-TYPE
	SYNTAX     Integer32 (-1|470000000..862000000)
	UNITS 	"Hertzios"
	MAX-ACCESS read-only
	STATUS     current
	DESCRIPTION 
		"T2 Frequency
		
		-1: N/A (The multiplex is a Dummy)"
	::= { muxT2SystemEntry 12 }

muxT2idTxID  OBJECT-TYPE
	SYNTAX     Integer32 (-1|0..65535)
	MAX-ACCESS read-write
	STATUS     current
	DESCRIPTION 
		"Tx ID
		
		-1: N/A (The multiplex is a Dummy)"
	::= { muxT2SystemEntry 13 }

muxT2idCellID  OBJECT-TYPE
	SYNTAX     Integer32 (-1|0..65535)
	MAX-ACCESS read-write
	STATUS     current
	DESCRIPTION 
		"Cell ID
		
		-1: N/A (The multiplex is a Dummy)"
	::= { muxT2SystemEntry 14 }

muxT2idNetworkID  OBJECT-TYPE
	SYNTAX     Integer32 (-1|0..65535)
	MAX-ACCESS read-write
	STATUS     current
	DESCRIPTION 
		"Network ID
		
		-1: N/A (The multiplex is a Dummy)"
	::= { muxT2SystemEntry 15 }

muxT2idT2SystemID  OBJECT-TYPE
	SYNTAX     Integer32 (-1|0..65535)
	MAX-ACCESS read-write
	STATUS     current
	DESCRIPTION 
		"T2 System ID
		
		-1: N/A (The multiplex is a Dummy)"
	::= { muxT2SystemEntry 16 }

muxT2UserLocalDelay  OBJECT-TYPE
	SYNTAX     Integer32 (-20000..20000)
	UNITS 	"usec/10"
	MAX-ACCESS read-write
	STATUS     current
	DESCRIPTION 
		"User Delay in 0.1 microseconds steps
		
		
		-1: N/A (The multiplex is a GapFiller/Dummy)"
	::= { muxT2SystemEntry 17 }

muxT2Pid  OBJECT-TYPE
	SYNTAX     Integer32 (32..8191)
	UNITS 	"usec/10"
	MAX-ACCESS read-write
	STATUS     current
	DESCRIPTION 
		"Modulation Interface: Packet IDentifier
		
		32...8191"
	::= { muxT2SystemEntry 18 }

muxT2TTTx  OBJECT-TYPE
	SYNTAX     DisplayString
	UNITS 	"usec"
	MAX-ACCESS read-only
	STATUS     current
	DESCRIPTION 
		"Time to Transmit the next superframe"
	::= { muxT2SystemEntry 19 }

muxT2Latency  OBJECT-TYPE
	SYNTAX     DisplayString
	UNITS 	"usec"
	MAX-ACCESS read-only
	STATUS     current
	DESCRIPTION 
		"Time that superframe is inside of transmitter before being transmitted."
	::= { muxT2SystemEntry 20 }

muxT2FrameTable  OBJECT-TYPE
	SYNTAX SEQUENCE OF MuxT2FrameEntry
	MAX-ACCESS not-accessible
	STATUS     current
	DESCRIPTION 
		"Layer 1 configuration"
	::= { dvbT2Tables 2 }

muxT2FrameEntry  OBJECT-TYPE
	SYNTAX 	MuxT2FrameEntry
	MAX-ACCESS not-accessible
	STATUS     current
	DESCRIPTION 
		"Each row is the Multiplex information. 1 multiplex 
		could be Gap Filler or Transmitter system."
	INDEX { muxT2FrameIndex }
	::= { muxT2FrameTable 1 }

MuxT2FrameEntry ::= SEQUENCE {
	muxT2FrameIndex
		Integer32,
	muxT2FrameDescription
		DisplayString,
	muxT2FrameCtrlAddress
		Integer32,
	muxT2FrameRowIndex
		Integer32,
	muxT2FrameChannelOut
		Integer32,
	muxT2FrameType
		INTEGER,
	muxT2FrameL1Mode
		INTEGER,
	muxT2FramePreamb
		INTEGER,
	muxT2FrameExtCarr
		INTEGER,
	muxT2FrameFFT
		INTEGER,
	muxT2FrameGuardInterval
		INTEGER,
	muxT2FramePAPR
		INTEGER,
	muxT2FramePilotPattern
		INTEGER,
	muxT2FrameT2Frames
		Integer32,
	muxT2FrameDataSymbol
		Integer32,
	muxT2Perfil
		Integer32,
	muxT2Group
		INTEGER,
	muxT2UserGroup
		INTEGER
}

muxT2FrameIndex  OBJECT-TYPE
	SYNTAX     Integer32 (1..36)
	MAX-ACCESS not-accessible
	STATUS     current
	DESCRIPTION 
		"MUX index"
	::= { muxT2FrameEntry 1 }

muxT2FrameDescription  OBJECT-TYPE
	SYNTAX     DisplayString
	MAX-ACCESS read-only
	STATUS     current
	DESCRIPTION 
		"MUX description. The module could be:
		
		GapFiller (REM)
		Transmitter (MOD)
		Profesional GapFiller (PRO)
		Modualtor T/T2 (MT2)
		"
	::= { muxT2FrameEntry 2 }

muxT2FrameCtrlAddress  OBJECT-TYPE
	SYNTAX     Integer32 (-1|1..18|101..118)
	MAX-ACCESS read-only
	STATUS     current
	DESCRIPTION 
		"Control address:
		
		-1: N/A (The multiplex is a dummy)"
	::= { muxT2FrameEntry 3 }

muxT2FrameRowIndex  OBJECT-TYPE
	SYNTAX     Integer32 (1..36)
	MAX-ACCESS read-only
	STATUS     current
	DESCRIPTION 
		"Input Channel:
		
		-1: N/A (The multiplex is a Transmitter/Dummy)"
	::= { muxT2FrameEntry 4 }

muxT2FrameChannelOut  OBJECT-TYPE
	SYNTAX     Integer32 (-1|21..69)
	MAX-ACCESS read-only
	STATUS     current
	DESCRIPTION 
		"Output Channel:
		
		-1: N/A (The multiplex is a Transmitter/Dummy)"
	::= { muxT2FrameEntry 5 }

muxT2FrameType  OBJECT-TYPE
	SYNTAX     INTEGER {
		dvbt (1),
		dvbt2 (2),
		unknown (3),
		notApply (4)
	}
	MAX-ACCESS read-only
	STATUS     current
	DESCRIPTION 
		"DVB-T / DVB-T2 selector
		
		1: DVB-T
		2: DVB-T2
		3: Unknown (Gap-Filler)
		4: Not Apply (dummy)"
	::= { muxT2FrameEntry 6 }

muxT2FrameL1Mode  OBJECT-TYPE
	SYNTAX     INTEGER {
		notApply (1),
		modeBPSK (2),
		modeQPSK (3),
		mode16QAM (4),
		mode64QAM (5)
	}
	MAX-ACCESS read-write
	STATUS     current
	DESCRIPTION 
		"L1 Mode:
		
		1: not Apply
		2: BPSK
		3: QPSK
		4: 16QAM
		5: 64QAM"
	::= { muxT2FrameEntry 7 }

muxT2FramePreamb  OBJECT-TYPE
	SYNTAX     INTEGER {
		notApply (1),
		preamMISO (2),
		preamSISO (3)
	}
	MAX-ACCESS read-write
	STATUS     current
	DESCRIPTION 
		"Format SISO/MISO
		
		1: not Apply
		2: MISO
		3: SISO"
	::= { muxT2FrameEntry 8 }

muxT2FrameExtCarr  OBJECT-TYPE
	SYNTAX     INTEGER {
		notApply (1),
		extCarrON (2),
		extCarrOFF (3)
	}
	MAX-ACCESS read-write
	STATUS     current
	DESCRIPTION 
		"Extended Carriers
		
		1: not Apply
		2: On
		3: Off
		"
	::= { muxT2FrameEntry 9 }

muxT2FrameFFT  OBJECT-TYPE
	SYNTAX     INTEGER {
		notApply (1),
		fft32K (2),
		fft16K (3),
		fft8K (4),
		fft4K (5),
		fft2K (6),
		fft1K (7)
	}
	MAX-ACCESS read-write
	STATUS     current
	DESCRIPTION 
		"FFT size
		
		1: not Apply
		2: 32K
		3: 16K
		4: 8K
		5: 4K
		6: 2K
		7: 1K
		"
	::= { muxT2FrameEntry 10 }

muxT2FrameGuardInterval  OBJECT-TYPE
	SYNTAX     INTEGER {
		notApply (1),
		guard1div32 (2),
		guard1div16 (3),
		guard1div8 (4),
		guard1div4 (5),
		guard1div128 (6),
		guard19div128 (7),
		guard19div256 (8)
	}
	MAX-ACCESS read-write
	STATUS     current
	DESCRIPTION 
		"Guard Interval:
		
		1: not Apply
		2: 1/32
		3: 1/16
		4: 1/8
		5: 1/4
		6: 1/128
		7: 19/128
		8: 19/256
		"
	::= { muxT2FrameEntry 11 }

muxT2FramePAPR  OBJECT-TYPE
	SYNTAX     INTEGER {
		notApply (1),
		paprNullTRP2 (2),
		paprACE (3),
		paprTR (4),
		paprACETR (5)
	}
	MAX-ACCESS read-write
	STATUS     current
	DESCRIPTION 
		"Reduction PAPR
		
		Possible combinations:
		v1_1_1 => - / ACE / TR / ACE-TR
		v1_2_1 => TR-P2 / ACE / TR / ACE-TR
		
		1: not apply
		2: -/TR-P2 (version dependent)
		3: ACE
		4: TR
		5: ACE-TR
		"
	::= { muxT2FrameEntry 12 }

muxT2FramePilotPattern  OBJECT-TYPE
	SYNTAX     INTEGER {
		notApply (1),
		pilotPattern8 (2),
		pilotPattern7 (3),
		pilotPattern6 (4),
		pilotPattern5 (5),
		pilotPattern4 (6),
		pilotPattern3 (7),
		pilotPattern2 (8),
		pilotPattern1 (9)
	}
	MAX-ACCESS read-write
	STATUS     current
	DESCRIPTION 
		"Pilot Pattern:
		
		1: not Apply
		2: 8
		3: 7
		4: 6
		5: 5
		6: 4
		7: 3
		8: 2
		9: 1
		"
	::= { muxT2FrameEntry 13 }

muxT2FrameT2Frames  OBJECT-TYPE
	SYNTAX     Integer32 (-1|0..255)
	MAX-ACCESS read-write
	STATUS     current
	DESCRIPTION 
		"Number of T2 frames for each super-frame
		
		-1: N/A (The multiplex is a Dummy)"
	::= { muxT2FrameEntry 14 }

muxT2FrameDataSymbol  OBJECT-TYPE
	SYNTAX     Integer32 (-1|0..4095)
	MAX-ACCESS read-write
	STATUS     current
	DESCRIPTION 
		"Number of symbols for frame
		
		-1: N/A (The multiplex is a Dummy)"
	::= { muxT2FrameEntry 15 }

muxT2Perfil  OBJECT-TYPE
	SYNTAX     INTEGER {
		notApply (1),
		base (2),
		lite (3)
	}
	MAX-ACCESS read-write
	STATUS     current
	DESCRIPTION 
		"T2 Perfil
		
		1: not Apply
		2: T2 Base
		3: T2 Lite
		-1: N/A (The multiplex is a Dummy)"
	::= { muxT2FrameEntry 16 }

muxT2Group  OBJECT-TYPE
	SYNTAX     INTEGER {
		group1 (1),
		group2 (2),
		notApply (3)
	}
	MAX-ACCESS read-only
	STATUS     current
	DESCRIPTION 
		"T2 Group
		
		1: Group 1
		2: Group 2
		3: not Apply
		-1: N/A (The multiplex is a Dummy)"
	::= { muxT2FrameEntry 17 }

muxT2UserGroup  OBJECT-TYPE
	SYNTAX     INTEGER {
		group1 (1),
		group2 (2),
		notApply (3)
	}
	MAX-ACCESS read-write
	STATUS     current
	DESCRIPTION 
		"T2 User Group
		
		1: Group1
		2: Group2
		3: not Apply
		-1: N/A (The multiplex is a Dummy)"
	::= { muxT2FrameEntry 18 }

muxT2plpTable  OBJECT-TYPE
	SYNTAX SEQUENCE OF MuxT2plpEntry
	MAX-ACCESS not-accessible
	STATUS     current
	DESCRIPTION 
		"Physical Layer Pipe 1 configuration"
	::= { dvbT2Tables 4 }

muxT2plpEntry  OBJECT-TYPE
	SYNTAX 	MuxT2plpEntry
	MAX-ACCESS not-accessible
	STATUS     current
	DESCRIPTION 
		"Each row is the Multiplex information. 1 multiplex 
		could be Gap Filler or Transmitter system."
	INDEX { muxT2plpMuxIndex,
		muxT2plpIndex}
	::= { muxT2plpTable 1 }

MuxT2plpEntry ::= SEQUENCE {
	muxT2plpMuxIndex
		Integer32,
	muxT2plpDescription
		DisplayString,
	muxT2plpCtrlAddress
		Integer32,
	muxT2plpRowIndex
		Integer32,
	muxT2plpChannelOut
		Integer32,
	muxT2plpType
		INTEGER,
	muxT2plpMode
		INTEGER,
	muxT2plpGroupID
		Integer32,
	muxT2plpConstellation
		INTEGER,
	muxT2plpRotCon
		TruthValue,
	muxT2plpFECtype
		INTEGER,
	muxT2plpCodeRate
		INTEGER,
	muxT2plpnBlocks
		Integer32,
	muxT2plpTiType
		INTEGER,
	muxT2plpTiLength
		Integer32,
	muxT2plpIndex
		Integer32,
	muxT2plpIbSignal
		INTEGER,
	muxT2plpId
		Integer32,
	muxT2plpTypePlp
		INTEGER,
	muxT2plpOk
		INTEGER
}

muxT2plpMuxIndex  OBJECT-TYPE
	SYNTAX     Integer32 (1..36)
	MAX-ACCESS not-accessible
	STATUS     current
	DESCRIPTION 
		"MUX index"
	::= { muxT2plpEntry 1 }

muxT2plpDescription  OBJECT-TYPE
	SYNTAX     DisplayString
	MAX-ACCESS read-only
	STATUS     current
	DESCRIPTION 
		"MUX description. The module could be:
		
		GapFiller (REM)
		Transmitter (MOD)
		Profesional GapFiller (PRO)
		Modualtor T/T2 (MT2)"
	::= { muxT2plpEntry 2 }

muxT2plpCtrlAddress  OBJECT-TYPE
	SYNTAX     Integer32 (-1|1..18|101..118)
	MAX-ACCESS read-only
	STATUS     current
	DESCRIPTION 
		"Control address:
		
		-1: N/A (The multiplex is a dummy)"
	::= { muxT2plpEntry 3 }

muxT2plpRowIndex  OBJECT-TYPE
	SYNTAX     Integer32 (1..36)
	MAX-ACCESS read-only
	STATUS     current
	DESCRIPTION 
		"Input Channel:
		
		-1: N/A (The multiplex is a Transmitter/Dummy)"
	::= { muxT2plpEntry 4 }

muxT2plpChannelOut  OBJECT-TYPE
	SYNTAX     Integer32 (-1|21..69)
	MAX-ACCESS read-only
	STATUS     current
	DESCRIPTION 
		"Output Channel:
		
		-1: N/A (The multiplex is a Transmitter/Dummy)"
	::= { muxT2plpEntry 5 }

muxT2plpType  OBJECT-TYPE
	SYNTAX     INTEGER {
		dvbt (1),
		dvbt2 (2),
		unknown (3),
		notApply (4)
	}
	MAX-ACCESS read-only
	STATUS     current
	DESCRIPTION 
		"DVB-T / DVB-T2 selector
		
		1: DVB-T
		2: DVB-T2
		3: Unknown (Gap-Filler)
		4: Not Apply (dummy)"
	::= { muxT2plpEntry 6 }

muxT2plpMode  OBJECT-TYPE
	SYNTAX     INTEGER {
		notApply (1),
		hem (2),
		nm (3)
	}
	MAX-ACCESS read-write
	STATUS     current
	DESCRIPTION 
		"PLP Mode:
		
		1: not Apply
		2: HEM (High Efificent Mode)
		3: NM (Normal Mode)"
	::= { muxT2plpEntry 7 }

muxT2plpGroupID  OBJECT-TYPE
	SYNTAX     Integer32 (-1|0..255)
	MAX-ACCESS read-write
	STATUS     current
	DESCRIPTION 
		"The PLP group within the current PLP is associated
		
		-1: not Apply
		0...255"
	::= { muxT2plpEntry 8 }

muxT2plpConstellation  OBJECT-TYPE
	SYNTAX     INTEGER {
		notApply (1),
		qpsk (2),
		qam16 (3),
		qam64 (4),
		qam256 (5)
	}
	MAX-ACCESS read-write
	STATUS     current
	DESCRIPTION 
		"Modulation used by this PLP
		
		1: not apply
		2: QPSK
		3: QAM16
		4: QAM64
		5: QAM256
		"
	::= { muxT2plpEntry 9 }

muxT2plpRotCon  OBJECT-TYPE
	SYNTAX     TruthValue
	MAX-ACCESS read-write
	STATUS     current
	DESCRIPTION 
		"Constellation rotation"
	::= { muxT2plpEntry 10 }

muxT2plpFECtype  OBJECT-TYPE
	SYNTAX     INTEGER {
		notApply (1),
		ldpc16K (2),
		ldpc64K (3)
	}
	MAX-ACCESS read-write
	STATUS     current
	DESCRIPTION 
		"FEC type used
		
		1: not Apply
		2: 16K LDPC
		3: 64K LDPC
		"
	::= { muxT2plpEntry 11 }

muxT2plpCodeRate  OBJECT-TYPE
	SYNTAX     INTEGER {
		notApply (1),
		codeRate1div2 (2),
		codeRate3div5 (3),
		codeRate2div3 (4),
		codeRate3div4 (5),
		codeRate4div5 (6),
		codeRate5div6 (7),
		codeRate1div3 (8),
		codeRate2div5 (9)
	}
	MAX-ACCESS read-write
	STATUS     current
	DESCRIPTION 
		"Code Rate used by this PLP
		
		1: not Apply
		2: codeRate1div2
		3: codeRate3div5
		4: codeRate2div3
		5: codeRate3div4
		6: codeRate4div5
		7: codeRate5div6
		8: codeRate1div3
		9: codeRate2div5
		"
	::= { muxT2plpEntry 12 }

muxT2plpnBlocks  OBJECT-TYPE
	SYNTAX     Integer32 (-1|0..1023)
	MAX-ACCESS read-write
	STATUS     current
	DESCRIPTION 
		"Number of blocks FEC
		
		-1: N/A (The multiplex is a Transmitter/Dummy)"
	::= { muxT2plpEntry 13 }

muxT2plpTiType  OBJECT-TYPE
	SYNTAX     INTEGER {
		notApply (1),
		single (2),
		multiple (3)
	}
	MAX-ACCESS read-write
	STATUS     current
	DESCRIPTION 
		"Type of time intervaling
		
		1: not apply
		2: single
		3: multiple
		"
	::= { muxT2plpEntry 14 }

muxT2plpTiLength  OBJECT-TYPE
	SYNTAX     Integer32 (-1|0..255)
	MAX-ACCESS read-write
	STATUS     current
	DESCRIPTION 
		"Length of Interpretation depends on the value of plp1TimeInterleaverType.
		
		-1: N/A (The multiplex is a Transmitter/Dummy)"
	::= { muxT2plpEntry 15 }

muxT2plpIndex  OBJECT-TYPE
	SYNTAX     Integer32 (1..8)
	MAX-ACCESS not-accessible
	STATUS     current
	DESCRIPTION 
		"PLP index (multiPLP)"
	::= { muxT2plpEntry 16 }

muxT2plpIbSignal  OBJECT-TYPE
	SYNTAX     INTEGER {
		null (1),
		onlyB (2),
		onlyA (3),
		aAndB (4),
		unknown (5),
		notApply (6)
	}
	MAX-ACCESS read-write
	STATUS     current
	DESCRIPTION 
		"In Band Signalling
		
		1: null
		2: B
		3: A
		4: A & B
		"
	::= { muxT2plpEntry 17 }

muxT2plpId  OBJECT-TYPE
	SYNTAX     Integer32 (0..255)
	MAX-ACCESS read-write
	STATUS     current
	DESCRIPTION 
		"Plp Identifier
		
		0...255"
	::= { muxT2plpEntry 18 }

muxT2plpTypePlp  OBJECT-TYPE
	SYNTAX     INTEGER {
		typeCommon (1),
		typeData1 (2),
		typeData2 (3),
		unknown (4),
		notApply (5)
	}
	MAX-ACCESS read-write
	STATUS     current
	DESCRIPTION 
		"PLP Type
		
		1: Common
		2: Data 1 -> only this mode can be set
		3: Data 2"
	::= { muxT2plpEntry 19 }

muxT2plpOk  OBJECT-TYPE
	SYNTAX     INTEGER {
		ok (1),
		nok (2)
	}
	MAX-ACCESS read-only
	STATUS     current
	DESCRIPTION 
		"PLP information is OK or not
		
		1: Ok 
		2: Nok
		"
	::= { muxT2plpEntry 20 }

ucaTable  OBJECT-TYPE
	SYNTAX SEQUENCE OF UcaEntry
	MAX-ACCESS not-accessible
	STATUS     current
	DESCRIPTION 
		"This table contains the basic information of each UCA connected to the system."
	::= { uca 1 }

ucaEntry  OBJECT-TYPE
	SYNTAX 	UcaEntry
	MAX-ACCESS not-accessible
	STATUS     current
	DESCRIPTION 
		"Each row is UCA information. There 1 UCA for each subrack."
	INDEX { ucaIndex }
	::= { ucaTable 1 }

UcaEntry ::= SEQUENCE {
	ucaIndex
		Integer32,
	ucaCtrlAddress
		Integer32,
	ucaMux1OnOffReset
		INTEGER,
	ucaMux2OnOffReset
		INTEGER,
	ucaMux3OnOffReset
		INTEGER,
	ucaStatusAlarm
		BitsStates,
	ucaHysteresis
		Integer32,
	ucaFirmware
		DisplayString,
	ucaTrapsConfiguration
		BitsStates
}

ucaIndex  OBJECT-TYPE
	SYNTAX     Integer32 (1..6)
	MAX-ACCESS not-accessible
	STATUS     current
	DESCRIPTION 
		"UCA index"
	::= { ucaEntry 1 }

ucaCtrlAddress  OBJECT-TYPE
	SYNTAX     Integer32 (20..25)
	MAX-ACCESS read-only
	STATUS     current
	DESCRIPTION 
		"Control address."
	::= { ucaEntry 2 }

ucaMux1OnOffReset  OBJECT-TYPE
	SYNTAX     INTEGER {
		ucaMux1On (1),
		ucaMux1Off (2),
		ucaMux1Reset (3)
	}
	MAX-ACCESS read-write
	STATUS     current
	DESCRIPTION 
		"MUX 1 Status. 
		
		1 = On
		2 = Off
		3 = This MUX will be reset"
	::= { ucaEntry 3 }

ucaMux2OnOffReset  OBJECT-TYPE
	SYNTAX     INTEGER {
		ucaMux2On (1),
		ucaMux2Off (2),
		ucaMux2Reset (3)
	}
	MAX-ACCESS read-write
	STATUS     current
	DESCRIPTION 
		"MUX 2 Status.
		
		1 = On
		2 = Off
		3 = This MUX will be reset"
	::= { ucaEntry 4 }

ucaMux3OnOffReset  OBJECT-TYPE
	SYNTAX     INTEGER {
		ucaMux3On (1),
		ucaMux3Off (2),
		ucaMux3Reset (3)
	}
	MAX-ACCESS read-write
	STATUS     current
	DESCRIPTION 
		"MUX 3 Status. 
		
		1 = On
		2 = Off
		3 = This MUX will be reset"
	::= { ucaEntry 5 }

ucaStatusAlarm  OBJECT-TYPE
	SYNTAX     BitsStates
	MAX-ACCESS read-only
	STATUS     deprecated
	DESCRIPTION 
		"Alarm bits status for this UCA"
	::= { ucaEntry 6 }

ucaHysteresis  OBJECT-TYPE
	SYNTAX     Integer32
	UNITS 	"dsec"
	MAX-ACCESS read-write
	STATUS     current
	DESCRIPTION 
		"Time to validate the alarm status."
	::= { ucaEntry 7 }

ucaFirmware  OBJECT-TYPE
	SYNTAX     DisplayString
	MAX-ACCESS read-only
	STATUS     current
	DESCRIPTION 
		"UCA Firmware version"
	::= { ucaEntry 8 }

ucaTrapsConfiguration  OBJECT-TYPE
	SYNTAX     BitsStates
	MAX-ACCESS read-write
	STATUS     deprecated
	DESCRIPTION 
		"Bits array for enable/disable the traps from this module
		
		For each bit:
		     False: disable
		     true: enable
		
		The bits are represented in BitsStates convection"
	::= { ucaEntry 9 }

ucaAlarmsTable  OBJECT-TYPE
	SYNTAX SEQUENCE OF UcaAlarmsEntry
	MAX-ACCESS not-accessible
	STATUS     current
	DESCRIPTION 
		"This table contains the alarm status of each mux."
	::= { uca 2 }

ucaAlarmsEntry  OBJECT-TYPE
	SYNTAX 	UcaAlarmsEntry
	MAX-ACCESS not-accessible
	STATUS     current
	DESCRIPTION 
		"Each row is UCA information. There 1 UCA for each subrack."
	INDEX { ucaAlarmsIndex }
	::= { ucaAlarmsTable 1 }

UcaAlarmsEntry ::= SEQUENCE {
	ucaAlarmsIndex
		Integer32,
	ucaCtrlAddressAlarm
		Integer32,
	ucaMajorAlarm
		TruthValue,
	ucaMinorAlarm
		TruthValue,
	ucaPowerSupply1Alarm
		TruthValue,
	ucaPowerSupply2Alarm
		TruthValue,
	ucaPowerSuppliesAlarm
		TruthValue,
	ucaCommunicationAlarms
		TruthValue
}

ucaAlarmsIndex  OBJECT-TYPE
	SYNTAX     Integer32 (1..6)
	MAX-ACCESS not-accessible
	STATUS     current
	DESCRIPTION 
		"UCA index"
	::= { ucaAlarmsEntry 1 }

ucaCtrlAddressAlarm  OBJECT-TYPE
	SYNTAX     Integer32 (20..25)
	MAX-ACCESS read-only
	STATUS     current
	DESCRIPTION 
		"Control address for this module"
	::= { ucaAlarmsEntry 2 }

ucaMajorAlarm  OBJECT-TYPE
	SYNTAX     TruthValue
	MAX-ACCESS read-only
	STATUS     current
	DESCRIPTION 
		"Major UCA status"
	::= { ucaAlarmsEntry 3 }

ucaMinorAlarm  OBJECT-TYPE
	SYNTAX     TruthValue
	MAX-ACCESS read-only
	STATUS     current
	DESCRIPTION 
		"Minor UCA status"
	::= { ucaAlarmsEntry 4 }

ucaPowerSupply1Alarm  OBJECT-TYPE
	SYNTAX     TruthValue
	MAX-ACCESS read-only
	STATUS     current
	DESCRIPTION 
		"Power supply 1 alarm status"
	::= { ucaAlarmsEntry 5 }

ucaPowerSupply2Alarm  OBJECT-TYPE
	SYNTAX     TruthValue
	MAX-ACCESS read-only
	STATUS     current
	DESCRIPTION 
		"Power supply 2 alarm status"
	::= { ucaAlarmsEntry 6 }

ucaPowerSuppliesAlarm  OBJECT-TYPE
	SYNTAX     TruthValue
	MAX-ACCESS read-only
	STATUS     current
	DESCRIPTION 
		"Power supplies alarm status"
	::= { ucaAlarmsEntry 7 }

ucaCommunicationAlarms  OBJECT-TYPE
	SYNTAX     TruthValue
	MAX-ACCESS read-only
	STATUS     current
	DESCRIPTION 
		"Communication alarm status"
	::= { ucaAlarmsEntry 8 }

ucaEnableAlarmTable  OBJECT-TYPE
	SYNTAX SEQUENCE OF UcaEnableAlarmEntry
	MAX-ACCESS not-accessible
	STATUS     current
	DESCRIPTION 
		"This table contains the alarm status of each mux."
	::= { uca 3 }

ucaEnableAlarmEntry  OBJECT-TYPE
	SYNTAX 	UcaEnableAlarmEntry
	MAX-ACCESS not-accessible
	STATUS     current
	DESCRIPTION 
		"Each row is UCA information. There 1 UCA for each subrack."
	INDEX { ucaEnableAlarmIndex }
	::= { ucaEnableAlarmTable 1 }

UcaEnableAlarmEntry ::= SEQUENCE {
	ucaEnableAlarmIndex
		Integer32,
	ucaCtrlAddressEnableAlarm
		Integer32,
	ucaPowerSupply1EnableAlarm
		TruthValue,
	ucaPowerSupply2EnableAlarm
		TruthValue,
	ucaPowerSuppliesEnableAlarm
		TruthValue
}

ucaEnableAlarmIndex  OBJECT-TYPE
	SYNTAX     Integer32 (1..6)
	MAX-ACCESS not-accessible
	STATUS     current
	DESCRIPTION 
		"UCA index"
	::= { ucaEnableAlarmEntry 1 }

ucaCtrlAddressEnableAlarm  OBJECT-TYPE
	SYNTAX     Integer32 (20..25)
	MAX-ACCESS read-only
	STATUS     current
	DESCRIPTION 
		"Control address for this module"
	::= { ucaEnableAlarmEntry 2 }

ucaPowerSupply1EnableAlarm  OBJECT-TYPE
	SYNTAX     TruthValue
	MAX-ACCESS read-write
	STATUS     current
	DESCRIPTION 
		"Enable/Disable trap: Power supply 1 alarm status"
	::= { ucaEnableAlarmEntry 3 }

ucaPowerSupply2EnableAlarm  OBJECT-TYPE
	SYNTAX     TruthValue
	MAX-ACCESS read-write
	STATUS     current
	DESCRIPTION 
		"Enable/Disable trap: Power supply 2 alarm status"
	::= { ucaEnableAlarmEntry 4 }

ucaPowerSuppliesEnableAlarm  OBJECT-TYPE
	SYNTAX     TruthValue
	MAX-ACCESS read-write
	STATUS     current
	DESCRIPTION 
		"Enable/Disable trap: Power supplies alarm status"
	::= { ucaEnableAlarmEntry 5 }

gpsTable  OBJECT-TYPE
	SYNTAX SEQUENCE OF GpsEntry
	MAX-ACCESS not-accessible
	STATUS     current
	DESCRIPTION 
		"This table contains the basic information of each GPS connected to the system."
	::= { gps 1 }

gpsEntry  OBJECT-TYPE
	SYNTAX 	GpsEntry
	MAX-ACCESS not-accessible
	STATUS     current
	DESCRIPTION 
		"Each row is GPS information."
	INDEX { gpsIndex }
	::= { gpsTable 1 }

GpsEntry ::= SEQUENCE {
	gpsIndex
		Integer32,
	gpsCtrlAddress
		Integer32,
	gpsSatellites
		Integer32,
	gpsStatusAlarm
		BitsStates,
	gpsHysteresis
		Integer32,
	gpsFirmware
		DisplayString,
	gpsTrapsConfiguration
		BitsStates,
	gpsLatitude
		DisplayString,
	gpsLongitude
		DisplayString,
	gpsAltitude
		DisplayString,
	gpsState
		INTEGER,
	gpsGMTdate
		DisplayString,
	gpsHardware
		DisplayString,
	gpsHoldoverDrift
		Integer32
}

gpsIndex  OBJECT-TYPE
	SYNTAX     Integer32 (1..2)
	MAX-ACCESS not-accessible
	STATUS     current
	DESCRIPTION 
		"GPS index."
	::= { gpsEntry 1 }

gpsCtrlAddress  OBJECT-TYPE
	SYNTAX     Integer32 (50..51)
	MAX-ACCESS read-only
	STATUS     current
	DESCRIPTION 
		"Control address."
	::= { gpsEntry 2 }

gpsSatellites  OBJECT-TYPE
	SYNTAX     Integer32 (0..8)
	MAX-ACCESS read-only
	STATUS     current
	DESCRIPTION 
		"Number of locked satellites."
	::= { gpsEntry 3 }

gpsStatusAlarm  OBJECT-TYPE
	SYNTAX     BitsStates
	MAX-ACCESS read-only
	STATUS     deprecated
	DESCRIPTION 
		"Alarm bits status for this GPS"
	::= { gpsEntry 4 }

gpsHysteresis  OBJECT-TYPE
	SYNTAX     Integer32
	UNITS 	"dsec"
	MAX-ACCESS read-write
	STATUS     deprecated
	DESCRIPTION 
		"Time to validate the alarm status."
	::= { gpsEntry 5 }

gpsFirmware  OBJECT-TYPE
	SYNTAX     DisplayString
	MAX-ACCESS read-only
	STATUS     current
	DESCRIPTION 
		"GPS Firmware version"
	::= { gpsEntry 6 }

gpsTrapsConfiguration  OBJECT-TYPE
	SYNTAX     BitsStates
	MAX-ACCESS read-write
	STATUS     deprecated
	DESCRIPTION 
		"Bits array for enable/disable the traps from this module
		
		For each bit:
		     False: disable
		     true: enable
		
		The bits are represented in BitsStates convection"
	::= { gpsEntry 7 }

gpsLatitude  OBJECT-TYPE
	SYNTAX     DisplayString
	MAX-ACCESS read-only
	STATUS     current
	DESCRIPTION 
		"Latitude of the GPS antenna"
	::= { gpsEntry 8 }

gpsLongitude  OBJECT-TYPE
	SYNTAX     DisplayString
	MAX-ACCESS read-only
	STATUS     current
	DESCRIPTION 
		"Longitude of the GPS antenna"
	::= { gpsEntry 9 }

gpsAltitude  OBJECT-TYPE
	SYNTAX     DisplayString
	MAX-ACCESS read-only
	STATUS     current
	DESCRIPTION 
		"Altitude of the GPS antenna"
	::= { gpsEntry 10 }

gpsState  OBJECT-TYPE
	SYNTAX     INTEGER {
		gpsStarting (1),
		gpsUnlocked (2),
		gpsHoldover (3),
		gpsLocked (4)
	}
	MAX-ACCESS read-only
	STATUS     current
	DESCRIPTION 
		"GPS state:
		
		1: starting (before GPS module communication)
		2: unlocked - it is not synchronized (error is higher thandrift configuration)
		3: holdover - Synchronization error is lower than drift configuration
		4: locked - boad is synchronized to the reference"
	::= { gpsEntry 11 }

gpsGMTdate  OBJECT-TYPE
	SYNTAX     DisplayString
	MAX-ACCESS read-only
	STATUS     current
	DESCRIPTION 
		"Show GMT from GPS board (GMT when synchronized)"
	::= { gpsEntry 12 }

gpsHardware  OBJECT-TYPE
	SYNTAX     DisplayString
	MAX-ACCESS read-only
	STATUS     current
	DESCRIPTION 
		"GPS hardware information.
		
		Nowadays it could be:
		EBO2 - EBO 2th version 
		EBO3 - EBO 3th version"
	::= { gpsEntry 13 }

gpsHoldoverDrift  OBJECT-TYPE
	SYNTAX     Integer32 (0..255)
	UNITS 	"usec"
	MAX-ACCESS read-write
	STATUS     current
	DESCRIPTION 
		"GPS Drift in holdover mode in microsecond.
		
		"
	::= { gpsEntry 14 }

gpsAlarmsTable  OBJECT-TYPE
	SYNTAX SEQUENCE OF GpsAlarmsEntry
	MAX-ACCESS not-accessible
	STATUS     current
	DESCRIPTION 
		"This table contains the alarm status of each gps."
	::= { gps 2 }

gpsAlarmsEntry  OBJECT-TYPE
	SYNTAX 	GpsAlarmsEntry
	MAX-ACCESS not-accessible
	STATUS     current
	DESCRIPTION 
		"Each row is the GPS information."
	INDEX { gpsAlarmsIndex }
	::= { gpsAlarmsTable 1 }

GpsAlarmsEntry ::= SEQUENCE {
	gpsAlarmsIndex
		Integer32,
	gpsCtrlAddressAlarm
		Integer32,
	gpsMajorAlarm
		TruthValue,
	gpsMinorAlarm
		TruthValue,
	gpsAntennaAlarm
		TruthValue,
	gpsHoldoverAlarm
		TruthValue,
	gpsCommunicationAlarm
		TruthValue,
	gpsSyncAlarm
		TruthValue
}

gpsAlarmsIndex  OBJECT-TYPE
	SYNTAX     Integer32 (1..2)
	MAX-ACCESS not-accessible
	STATUS     current
	DESCRIPTION 
		"GPS index"
	::= { gpsAlarmsEntry 1 }

gpsCtrlAddressAlarm  OBJECT-TYPE
	SYNTAX     Integer32 (50..51)
	MAX-ACCESS read-only
	STATUS     current
	DESCRIPTION 
		"Control address for this module"
	::= { gpsAlarmsEntry 2 }

gpsMajorAlarm  OBJECT-TYPE
	SYNTAX     TruthValue
	MAX-ACCESS read-only
	STATUS     current
	DESCRIPTION 
		"GPS Antenna status"
	::= { gpsAlarmsEntry 3 }

gpsMinorAlarm  OBJECT-TYPE
	SYNTAX     TruthValue
	MAX-ACCESS read-only
	STATUS     current
	DESCRIPTION 
		"GPS receiver status"
	::= { gpsAlarmsEntry 4 }

gpsAntennaAlarm  OBJECT-TYPE
	SYNTAX     TruthValue
	MAX-ACCESS read-only
	STATUS     current
	DESCRIPTION 
		"GPS Antenna status"
	::= { gpsAlarmsEntry 5 }

gpsHoldoverAlarm  OBJECT-TYPE
	SYNTAX     TruthValue
	MAX-ACCESS read-only
	STATUS     current
	DESCRIPTION 
		"GPS has holdover available
		Alarm Code: AG104 (Phase-frequency WEB Tag)"
	::= { gpsAlarmsEntry 6 }

gpsCommunicationAlarm  OBJECT-TYPE
	SYNTAX     TruthValue
	MAX-ACCESS read-only
	STATUS     current
	DESCRIPTION 
		"Communication alarm status"
	::= { gpsAlarmsEntry 7 }

gpsSyncAlarm  OBJECT-TYPE
	SYNTAX     TruthValue
	MAX-ACCESS read-only
	STATUS     current
	DESCRIPTION 
		"GPS is synchronized
		Alarm Code: AG106 (Unlocked WEB Tag)"
	::= { gpsAlarmsEntry 8 }

gpsEnableAlarmTable  OBJECT-TYPE
	SYNTAX SEQUENCE OF GpsEnableAlarmEntry
	MAX-ACCESS not-accessible
	STATUS     current
	DESCRIPTION 
		"This table contains the enable alarm of each gps."
	::= { gps 3 }

gpsEnableAlarmEntry  OBJECT-TYPE
	SYNTAX 	GpsEnableAlarmEntry
	MAX-ACCESS not-accessible
	STATUS     current
	DESCRIPTION 
		"Each row is the GPS information. "
	INDEX { gpsEnableAlarmIndex }
	::= { gpsEnableAlarmTable 1 }

GpsEnableAlarmEntry ::= SEQUENCE {
	gpsEnableAlarmIndex
		Integer32,
	gpsCtrlAddressEnableAlarm
		Integer32,
	gpsAntennaEnableAlarm
		TruthValue,
	gpsHoldoverEnableAlarm
		TruthValue,
	gpsSyncEnableAlarm
		TruthValue
}

gpsEnableAlarmIndex  OBJECT-TYPE
	SYNTAX     Integer32 (1..2)
	MAX-ACCESS not-accessible
	STATUS     current
	DESCRIPTION 
		"GPS index"
	::= { gpsEnableAlarmEntry 1 }

gpsCtrlAddressEnableAlarm  OBJECT-TYPE
	SYNTAX     Integer32 (50..51)
	MAX-ACCESS read-only
	STATUS     current
	DESCRIPTION 
		"Control address for this module"
	::= { gpsEnableAlarmEntry 2 }

gpsAntennaEnableAlarm  OBJECT-TYPE
	SYNTAX     TruthValue
	MAX-ACCESS read-write
	STATUS     current
	DESCRIPTION 
		"Enable/Disable trap: GPS Antenna status"
	::= { gpsEnableAlarmEntry 3 }

gpsHoldoverEnableAlarm  OBJECT-TYPE
	SYNTAX     TruthValue
	MAX-ACCESS read-write
	STATUS     current
	DESCRIPTION 
		"Enable/Disable trap: GPS holdover status
		Alarm Code: AG104 (Phase-frequency WEB Tag)"
	::= { gpsEnableAlarmEntry 4 }

gpsSyncEnableAlarm  OBJECT-TYPE
	SYNTAX     TruthValue
	MAX-ACCESS read-write
	STATUS     current
	DESCRIPTION 
		"GPS is synchronized Enable Alarm
		Alarm Code: AG106 (Unlocked WEB Tag)"
	::= { gpsEnableAlarmEntry 5 }

gpsEnableTrapTable  OBJECT-TYPE
	SYNTAX SEQUENCE OF GpsEnableTrapEntry
	MAX-ACCESS not-accessible
	STATUS     current
	DESCRIPTION 
		"This table contains the enable trap status for each GPS."
	::= { gps 4 }

gpsEnableTrapEntry  OBJECT-TYPE
	SYNTAX 	GpsEnableTrapEntry
	MAX-ACCESS not-accessible
	STATUS     current
	DESCRIPTION 
		"Each row is the GPS information."
	INDEX { gpsEnableTrapIndex }
	::= { gpsEnableTrapTable 1 }

GpsEnableTrapEntry ::= SEQUENCE {
	gpsEnableTrapIndex
		Integer32,
	gpsCtrlAddressEnableTrap
		Integer32,
	gpsAntennaEnableTrap
		TruthValue,
	gpsHoldoverEnableTrap
		TruthValue,
	gpsCommunicationEnableTrap
		TruthValue,
	gpsSyncEnableTrap
		TruthValue
}

gpsEnableTrapIndex  OBJECT-TYPE
	SYNTAX     Integer32 (1..2)
	MAX-ACCESS not-accessible
	STATUS     current
	DESCRIPTION 
		"GPS index"
	::= { gpsEnableTrapEntry 1 }

gpsCtrlAddressEnableTrap  OBJECT-TYPE
	SYNTAX     Integer32 (50..51)
	MAX-ACCESS read-only
	STATUS     current
	DESCRIPTION 
		"Control address for this module"
	::= { gpsEnableTrapEntry 2 }

gpsAntennaEnableTrap  OBJECT-TYPE
	SYNTAX     TruthValue
	MAX-ACCESS read-write
	STATUS     current
	DESCRIPTION 
		"Enable/Disable trap: GPS Antenna enable/disable trap"
	::= { gpsEnableTrapEntry 3 }

gpsHoldoverEnableTrap  OBJECT-TYPE
	SYNTAX     TruthValue
	MAX-ACCESS read-write
	STATUS     current
	DESCRIPTION 
		"Enable/Disable trap: GPS holdover enable/disable trap
		Alarm Code: AG104 (Phase-frequency WEB Tag)"
	::= { gpsEnableTrapEntry 4 }

gpsCommunicationEnableTrap  OBJECT-TYPE
	SYNTAX     TruthValue
	MAX-ACCESS read-write
	STATUS     current
	DESCRIPTION 
		"Enable/Disable trap: GPS communication enable/disable trap"
	::= { gpsEnableTrapEntry 5 }

gpsSyncEnableTrap  OBJECT-TYPE
	SYNTAX     TruthValue
	MAX-ACCESS read-write
	STATUS     current
	DESCRIPTION 
		"GPS Synchronization enable/disable trap
		Alarm Code: AG106 (Unlocked WEB Tag)"
	::= { gpsEnableTrapEntry 6 }

gpsSatellitesTable  OBJECT-TYPE
	SYNTAX SEQUENCE OF GpsSatellitesEntry
	MAX-ACCESS not-accessible
	STATUS     current
	DESCRIPTION 
		"This table contains the satellites information for GPSs modules."
	::= { gps 5 }

gpsSatellitesEntry  OBJECT-TYPE
	SYNTAX 	GpsSatellitesEntry
	MAX-ACCESS not-accessible
	STATUS     current
	DESCRIPTION 
		"Each row is the Satellite information. 
		
		Can be 8 locked satellites for each GPS."
	INDEX { gpsSatellitesIndex }
	::= { gpsSatellitesTable 1 }

GpsSatellitesEntry ::= SEQUENCE {
	gpsSatellitesIndex
		Integer32,
	gps1IdSatellite
		Integer32,
	gps1LockedSatellite
		TruthValue,
	gps1SnrSatellite
		Integer32,
	gps2IdSatellite
		Integer32,
	gps2LockedSatellite
		TruthValue,
	gps2SnrSatellite
		Integer32
}

gpsSatellitesIndex  OBJECT-TYPE
	SYNTAX     Integer32 (1..8)
	MAX-ACCESS not-accessible
	STATUS     current
	DESCRIPTION 
		"GPS index.
		
		There are 8 satellite information for each GPS."
	::= { gpsSatellitesEntry 1 }

gps1IdSatellite  OBJECT-TYPE
	SYNTAX     Integer32 (-1|0..127)
	MAX-ACCESS read-only
	STATUS     current
	DESCRIPTION 
		"ID Satellite (GPS1)
		
		-1: GPS 1 not connected
		0...127: ID Satellite"
	::= { gpsSatellitesEntry 2 }

gps1LockedSatellite  OBJECT-TYPE
	SYNTAX     TruthValue
	MAX-ACCESS read-only
	STATUS     current
	DESCRIPTION 
		"This Satellite is 
		
		True: Locked
		False: Unlocked
		
		This value will be false if GPS 1 is not connected."
	::= { gpsSatellitesEntry 3 }

gps1SnrSatellite  OBJECT-TYPE
	SYNTAX     Integer32 (-1|0..255)
	MAX-ACCESS read-only
	STATUS     current
	DESCRIPTION 
		"SNR Satellite (GPS1)
		
		-1: GPS 1 not connected
		0...255: SNR Satellite"
	::= { gpsSatellitesEntry 4 }

gps2IdSatellite  OBJECT-TYPE
	SYNTAX     Integer32 (-1|0..127)
	MAX-ACCESS read-only
	STATUS     current
	DESCRIPTION 
		"ID Satellite (GPS2)
		
		-1: GPS 2 not connected
		0...127: ID Satellite"
	::= { gpsSatellitesEntry 5 }

gps2LockedSatellite  OBJECT-TYPE
	SYNTAX     TruthValue
	MAX-ACCESS read-only
	STATUS     current
	DESCRIPTION 
		"This Satellite is 
		
		True: Locked
		False: Unlocked
		
		This value will be false if GPS 2 is not connected."
	::= { gpsSatellitesEntry 6 }

gps2SnrSatellite  OBJECT-TYPE
	SYNTAX     Integer32 (-1|0..255)
	MAX-ACCESS read-only
	STATUS     current
	DESCRIPTION 
		"SNR Satellite (GPS2)
		
		-1: GPS 2 not connected
		0...255: SNR Satellite"
	::= { gpsSatellitesEntry 7 }

gpsSplitterTable  OBJECT-TYPE
	SYNTAX SEQUENCE OF GpsSplitterEntry
	MAX-ACCESS not-accessible
	STATUS     current
	DESCRIPTION 
		"This table contains the alarm status of each gps."
	::= { gps 6 }

gpsSplitterEntry  OBJECT-TYPE
	SYNTAX 	GpsSplitterEntry
	MAX-ACCESS not-accessible
	STATUS     current
	DESCRIPTION 
		"Each row is the GPS splitter information."
	INDEX { gpsSplitterIndex }
	::= { gpsSplitterTable 1 }

GpsSplitterEntry ::= SEQUENCE {
	gpsSplitterIndex
		Integer32,
	gpsSplitterCtrlAddress
		Integer32,
	gpsSplitterActivedOutput
		INTEGER,
	gpsSplitterCommunicationAlarm
		TruthValue,
	gpsSplitterGPS1Status
		INTEGER,
	gpsSplitterGPS2Status
		INTEGER
}

gpsSplitterIndex  OBJECT-TYPE
	SYNTAX     Integer32 (1..255)
	MAX-ACCESS not-accessible
	STATUS     current
	DESCRIPTION 
		"GPS index"
	::= { gpsSplitterEntry 1 }

gpsSplitterCtrlAddress  OBJECT-TYPE
	SYNTAX     Integer32 (1..255)
	MAX-ACCESS read-only
	STATUS     current
	DESCRIPTION 
		"Control address for this module"
	::= { gpsSplitterEntry 2 }

gpsSplitterActivedOutput  OBJECT-TYPE
	SYNTAX     INTEGER {
		splitterNullOutput (1),
		splitterGPS1Output (2),
		splitterGPS2Output (3),
		splitterExternalOutput (4)
	}
	MAX-ACCESS read-only
	STATUS     current
	DESCRIPTION 
		"Actived output
		
		1: Output Null
		2: GPS 1
		3: GPS 2
		4: External output"
	::= { gpsSplitterEntry 3 }

gpsSplitterCommunicationAlarm  OBJECT-TYPE
	SYNTAX     TruthValue
	MAX-ACCESS read-only
	STATUS     current
	DESCRIPTION 
		"GPS splitter Commnication 
		
		False: there is communication
		True: there is not communication, so module is alarmed"
	::= { gpsSplitterEntry 4 }

gpsSplitterGPS1Status  OBJECT-TYPE
	SYNTAX     INTEGER {
		gpsDisconnected (1),
		gpsDetected (2),
		gpsConnected (3),
		gpsNotConfigured (4),
		gpsUnlocked (5),
		gpsLocked (6),
		gpsHoldover (7),
		gpsPostHoldover (8),
		gpsBrokenDown (9),
		gpsNotDetected (10),
		gpsSfnNok (11)
	}
	MAX-ACCESS read-only
	STATUS     current
	DESCRIPTION 
		"GPS 1 status
		
		1: Disconnect
		2: Detected
		3: Connected
		4: Not configured
		5: Unlocked
		6: Locked
		7: Holdover
		8: Post-Holdover
		9: Broken down
		10: Not detected
		11: SFN nok
		"
	::= { gpsSplitterEntry 5 }

gpsSplitterGPS2Status  OBJECT-TYPE
	SYNTAX     INTEGER {
		gpsDisconnected (1),
		gpsDetected (2),
		gpsConnected (3),
		gpsNotConfigured (4),
		gpsUnlocked (5),
		gpsLocked (6),
		gpsHoldover (7),
		gpsPostHoldover (8),
		gpsBrokenDown (9),
		gpsNotDetected (10),
		gpsSfnNok (11)
	}
	MAX-ACCESS read-only
	STATUS     current
	DESCRIPTION 
		"GPS 2 status
		
		1: Disconnect
		2: Detected
		3: Connected
		4: Not configured
		5: Unlocked
		6: Locked
		7: Holdover
		8: Post-Holdover
		9: Broken down
		10: Not detected
		11: SFN nok
		"
	::= { gpsSplitterEntry 6 }

contactsInputTable  OBJECT-TYPE
	SYNTAX SEQUENCE OF ContactsInputEntry
	MAX-ACCESS not-accessible
	STATUS     current
	DESCRIPTION 
		"This table contains the basic information of realys module"
	::= { contacts 1 }

contactsInputEntry  OBJECT-TYPE
	SYNTAX 	ContactsInputEntry
	MAX-ACCESS not-accessible
	STATUS     current
	DESCRIPTION 
		"Inputs row"
	INDEX { contactsInputIndex }
	::= { contactsInputTable 1 }

ContactsInputEntry ::= SEQUENCE {
	contactsInputIndex
		Integer32,
	contactsInputState
		Integer32,
	contactsInputAction
		Integer32,
	contactsInputPulse
		Integer32,
	contactsInputDescription
		DisplayString,
	contactsInputSimulate
		TruthValue
}

contactsInputIndex  OBJECT-TYPE
	SYNTAX     Integer32 (1..15)
	MAX-ACCESS not-accessible
	STATUS     current
	DESCRIPTION 
		"Input index"
	::= { contactsInputEntry 1 }

contactsInputState  OBJECT-TYPE
	SYNTAX     Integer32 (0|1)
	MAX-ACCESS read-only
	STATUS     current
	DESCRIPTION 
		"The input state could be,
		0 = open
		1 = close
		"
	::= { contactsInputEntry 2 }

contactsInputAction  OBJECT-TYPE
	SYNTAX     Integer32 (-1|0..5)
	MAX-ACCESS read-write
	STATUS     current
	DESCRIPTION 
		"The inputs could modifie the indicated output whenever this value is different to 0.
		"
	::= { contactsInputEntry 3 }

contactsInputPulse  OBJECT-TYPE
	SYNTAX     Integer32 (0|1..28800)
	UNITS 	"seconds"
	MAX-ACCESS read-write
	STATUS     current
	DESCRIPTION 
		"The input pulse duration to act on the indicated output.
		If the action value is 0, this value (pulse) does not apply."
	::= { contactsInputEntry 4 }

contactsInputDescription  OBJECT-TYPE
	SYNTAX     DisplayString
	MAX-ACCESS read-only
	STATUS     current
	DESCRIPTION 
		"Input description."
	::= { contactsInputEntry 5 }

contactsInputSimulate  OBJECT-TYPE
	SYNTAX     TruthValue
	MAX-ACCESS read-write
	STATUS     current
	DESCRIPTION 
		"Simulate an input actuation."
	::= { contactsInputEntry 6 }

contactsOutputTable  OBJECT-TYPE
	SYNTAX SEQUENCE OF ContactsOutputEntry
	MAX-ACCESS not-accessible
	STATUS     current
	DESCRIPTION 
		"This table contains the basic information of realys module"
	::= { contacts 2 }

contactsOutputEntry  OBJECT-TYPE
	SYNTAX 	ContactsOutputEntry
	MAX-ACCESS not-accessible
	STATUS     current
	DESCRIPTION 
		"Inputs row"
	INDEX { contactsOutputIndex }
	::= { contactsOutputTable 1 }

ContactsOutputEntry ::= SEQUENCE {
	contactsOutputIndex
		Integer32,
	contactsOutputState
		Integer32,
	contactsOutputRest
		Integer32,
	contactsOutputDuration
		Integer32,
	contactsOutputDescription
		DisplayString
}

contactsOutputIndex  OBJECT-TYPE
	SYNTAX     Integer32 (1..21)
	MAX-ACCESS not-accessible
	STATUS     current
	DESCRIPTION 
		"Output index"
	::= { contactsOutputEntry 1 }

contactsOutputState  OBJECT-TYPE
	SYNTAX     Integer32 (0|1)
	MAX-ACCESS read-write
	STATUS     current
	DESCRIPTION 
		"The output state could be,
		0 = open
		1 = close
		"
	::= { contactsOutputEntry 2 }

contactsOutputRest  OBJECT-TYPE
	SYNTAX     Integer32
	MAX-ACCESS read-write
	STATUS     current
	DESCRIPTION 
		"The rest of this realy (the default output state)
		0 = open
		1 = close"
	::= { contactsOutputEntry 3 }

contactsOutputDuration  OBJECT-TYPE
	SYNTAX     Integer32
	MAX-ACCESS read-write
	STATUS     current
	DESCRIPTION 
		"Output duration.
		0 = infinite state
		otherwise, seconds of the output pulse"
	::= { contactsOutputEntry 4 }

contactsOutputDescription  OBJECT-TYPE
	SYNTAX     DisplayString
	MAX-ACCESS read-only
	STATUS     current
	DESCRIPTION 
		"Output description."
	::= { contactsOutputEntry 5 }

contactsCtrlAddress  OBJECT-TYPE
	SYNTAX     Integer32
	MAX-ACCESS read-only
	STATUS     obsolete
	DESCRIPTION 
		"Control address."
	::= { contacts 3 }

contactsHysteresis  OBJECT-TYPE
	SYNTAX     Integer32
	MAX-ACCESS read-write
	STATUS     deprecated
	DESCRIPTION 
		"Time to validate the alarm status."
	::= { contacts 4 }

contactsFirmware  OBJECT-TYPE
	SYNTAX     DisplayString
	MAX-ACCESS read-only
	STATUS     current
	DESCRIPTION 
		"Contacts firmware version"
	::= { contacts 5 }

ucanLocal  OBJECT-TYPE
	SYNTAX     TruthValue
	MAX-ACCESS read-only
	STATUS     current
	DESCRIPTION 
		"UCA n+1 remote/local configuration.
		
		False: UCA n+1 could be remote-configurated 
		Truth: UCA n+1 only could by local-configurated
		"
	::= { ucanStateConfiguration 1 }

ucanManual  OBJECT-TYPE
	SYNTAX     TruthValue
	MAX-ACCESS read-write
	STATUS     current
	DESCRIPTION 
		"UCA n+1 automatic/manuall configuration.
		
		False: UCA n+1 is in automatic mode.
		Truth: UCA n+1 is in manual mode, there are manual commutations.
		"
	::= { ucanStateConfiguration 2 }

ucanHysteresis  OBJECT-TYPE
	SYNTAX     Integer32
	MAX-ACCESS read-write
	STATUS     current
	DESCRIPTION 
		"UCA n+1 Hysteresis"
	::= { ucanStateConfiguration 3 }

ucanNoPriority  OBJECT-TYPE
	SYNTAX     TruthValue
	MAX-ACCESS read-write
	STATUS     current
	DESCRIPTION 
		"UCA n+1 on/off priorities:
		
		False: the priority-list are on.
		Truth: the priority-list are off.
		"
	::= { ucanStateConfiguration 4 }

ucanAutoOff  OBJECT-TYPE
	SYNTAX     TruthValue
	MAX-ACCESS read-write
	STATUS     current
	DESCRIPTION 
		"Auto-switch on!off the principal MUX when is switched"
	::= { ucanStateConfiguration 5 }

ucanAutoReturn  OBJECT-TYPE
	SYNTAX     TruthValue
	MAX-ACCESS read-write
	STATUS     current
	DESCRIPTION 
		"It is possible to return to principal MUX when the module is OK again"
	::= { ucanStateConfiguration 6 }

ucanInputTest  OBJECT-TYPE
	SYNTAX     TruthValue
	MAX-ACCESS read-write
	STATUS     current
	DESCRIPTION 
		"The input alarm could be cause for switching"
	::= { ucanStateConfiguration 7 }

ucanReceiver  OBJECT-TYPE
	SYNTAX     TruthValue
	MAX-ACCESS read-write
	STATUS     current
	DESCRIPTION 
		"The receiver alarms could be cause for switching"
	::= { ucanStateConfiguration 8 }

ucanReset  OBJECT-TYPE
	SYNTAX     TruthValue
	MAX-ACCESS read-write
	STATUS     current
	DESCRIPTION 
		"Reset UCA n+1 Status"
	::= { ucanStateConfiguration 9 }

ucanFirmware  OBJECT-TYPE
	SYNTAX     DisplayString
	MAX-ACCESS read-only
	STATUS     current
	DESCRIPTION 
		"UCA n+1 firmware version"
	::= { ucanStateConfiguration 10 }

ucanPrioritiesTable  OBJECT-TYPE
	SYNTAX SEQUENCE OF UcanPrioritiesEntry
	MAX-ACCESS not-accessible
	STATUS     current
	DESCRIPTION 
		"UCA n+1 priorities Table"
	::= { ucanStateConfiguration 11 }

ucanPrioritiesEntry  OBJECT-TYPE
	SYNTAX 	UcanPrioritiesEntry
	MAX-ACCESS not-accessible
	STATUS     current
	DESCRIPTION 
		"UCA n+1 Priorities Entry"
	INDEX { ucanPrioritiesIndex }
	::= { ucanPrioritiesTable 1 }

UcanPrioritiesEntry ::= SEQUENCE {
	ucanPrioritiesIndex
		Integer32,
	ucanPrioritiesMuxAddress
		Integer32,
	ucanPrioritiesMuxValue
		Integer32
}

ucanPrioritiesIndex  OBJECT-TYPE
	SYNTAX     Integer32 (1..15)
	MAX-ACCESS not-accessible
	STATUS     current
	DESCRIPTION 
		"UCA n+1 priorities index"
	::= { ucanPrioritiesEntry 1 }

ucanPrioritiesMuxAddress  OBJECT-TYPE
	SYNTAX     Integer32 (1..15)
	MAX-ACCESS read-only
	STATUS     current
	DESCRIPTION 
		"MUX address priority"
	::= { ucanPrioritiesEntry 2 }

ucanPrioritiesMuxValue  OBJECT-TYPE
	SYNTAX     Integer32 (0..6)
	MAX-ACCESS read-write
	STATUS     current
	DESCRIPTION 
		"MUX address priority value"
	::= { ucanPrioritiesEntry 3 }

ucanReserve  OBJECT-TYPE
	SYNTAX     Integer32 (1..15)
	MAX-ACCESS read-write
	STATUS     current
	DESCRIPTION 
		"Reservation address"
	::= { ucanStateConfiguration 12 }

ucanCommunication  OBJECT-TYPE
	SYNTAX     TruthValue
	MAX-ACCESS read-write
	STATUS     current
	DESCRIPTION 
		"Reservation address"
	::= { ucanStateConfiguration 13 }

ucanStateCommutationTable  OBJECT-TYPE
	SYNTAX SEQUENCE OF UcanStateCommutationEntry
	MAX-ACCESS not-accessible
	STATUS     current
	DESCRIPTION 
		"UCA n+1 State Commutation Table"
	::= { ucanStateCommutation 1 }

ucanStateCommutationEntry  OBJECT-TYPE
	SYNTAX 	UcanStateCommutationEntry
	MAX-ACCESS not-accessible
	STATUS     current
	DESCRIPTION 
		"UCA n+1 State Commutation Entry"
	INDEX { ucanStateCommutationIndex }
	::= { ucanStateCommutationTable 1 }

UcanStateCommutationEntry ::= SEQUENCE {
	ucanStateCommutationIndex
		Integer32,
	ucanStateCommutationMuxAddress
		Integer32,
	ucanStateCommutationValue
		TruthValue
}

ucanStateCommutationIndex  OBJECT-TYPE
	SYNTAX     Integer32 (1..15)
	MAX-ACCESS not-accessible
	STATUS     current
	DESCRIPTION 
		"UCA n+1 State Commutation Index"
	::= { ucanStateCommutationEntry 1 }

ucanStateCommutationMuxAddress  OBJECT-TYPE
	SYNTAX     Integer32 (1..15)
	MAX-ACCESS read-only
	STATUS     current
	DESCRIPTION 
		"UCA n+1 State Commutation MUX Address"
	::= { ucanStateCommutationEntry 2 }

ucanStateCommutationValue  OBJECT-TYPE
	SYNTAX     TruthValue
	MAX-ACCESS read-write
	STATUS     current
	DESCRIPTION 
		"UCA n+1 State Commutation Value"
	::= { ucanStateCommutationEntry 3 }

ucanStateTestTable  OBJECT-TYPE
	SYNTAX SEQUENCE OF UcanStateTestEntry
	MAX-ACCESS not-accessible
	STATUS     current
	DESCRIPTION 
		"UCA n+1 State Test Table"
	::= { ucanStateCommutation 2 }

ucanStateTestEntry  OBJECT-TYPE
	SYNTAX 	UcanStateTestEntry
	MAX-ACCESS not-accessible
	STATUS     current
	DESCRIPTION 
		"UCA n+1 State Test Entry"
	INDEX { ucanStateTestIndex }
	::= { ucanStateTestTable 1 }

UcanStateTestEntry ::= SEQUENCE {
	ucanStateTestIndex
		Integer32,
	ucanStateTestMuxAddress
		Integer32,
	ucanStateTestValue
		TruthValue
}

ucanStateTestIndex  OBJECT-TYPE
	SYNTAX     Integer32 (1..15)
	MAX-ACCESS not-accessible
	STATUS     current
	DESCRIPTION 
		"UCA n+1 State Test Index"
	::= { ucanStateTestEntry 1 }

ucanStateTestMuxAddress  OBJECT-TYPE
	SYNTAX     Integer32 (1..15)
	MAX-ACCESS read-only
	STATUS     current
	DESCRIPTION 
		"UCA n+1 State Test MUX Address"
	::= { ucanStateTestEntry 2 }

ucanStateTestValue  OBJECT-TYPE
	SYNTAX     TruthValue
	MAX-ACCESS read-write
	STATUS     current
	DESCRIPTION 
		"UCA n+1 State Test Value"
	::= { ucanStateTestEntry 3 }

ucanSwitchedMux  OBJECT-TYPE
	SYNTAX     Integer32 (0..15)
	MAX-ACCESS read-write
	STATUS     current
	DESCRIPTION 
		"UCA n+1 Switched MUX"
	::= { ucanStateCommutation 3 }

ucanTestingMux  OBJECT-TYPE
	SYNTAX     Integer32 (0..15)
	MAX-ACCESS read-write
	STATUS     current
	DESCRIPTION 
		"UCA n+1 Switched MUX"
	::= { ucanStateCommutation 4 }

ucanGeneralAlarm  OBJECT-TYPE
	SYNTAX     TruthValue
	MAX-ACCESS read-only
	STATUS     current
	DESCRIPTION 
		"UCA n+1 General Alarm"
	::= { ucanAlarm 1 }

ucanComunicationAlarm  OBJECT-TYPE
	SYNTAX     TruthValue
	MAX-ACCESS read-only
	STATUS     current
	DESCRIPTION 
		"UCA n+1 Comunication Alarm"
	::= { ucanAlarm 2 }

ucanReservationAlarm  OBJECT-TYPE
	SYNTAX     TruthValue
	MAX-ACCESS read-only
	STATUS     current
	DESCRIPTION 
		"Is not possible to switching the reservation module"
	::= { ucanAlarm 3 }

ucanCompactGeneralTable  OBJECT-TYPE
	SYNTAX SEQUENCE OF UcanCompactGeneralEntry
	MAX-ACCESS not-accessible
	STATUS     current
	DESCRIPTION 
		"UCA N+1 for Compact Serie General (state/configuration) table"
	::= { ucanCompact 1 }

ucanCompactGeneralEntry  OBJECT-TYPE
	SYNTAX 	UcanCompactGeneralEntry
	MAX-ACCESS not-accessible
	STATUS     current
	DESCRIPTION 
		"UCA N+1 for Compact Serie General (state/configuration) table"
	INDEX { ucanCompactStateConfigIndex }
	::= { ucanCompactGeneralTable 1 }

UcanCompactGeneralEntry ::= SEQUENCE {
	ucanCompactStateConfigIndex
		Integer32,
	ucanCControlAddress
		Integer32,
	ucanCLocal
		TruthValue,
	ucanCManual
		TruthValue,
	ucanCAntenna
		INTEGER,
	ucanCSwitchedMux
		INTEGER,
	ucanCTestingMux
		INTEGER,
	ucanCAutoOff
		TruthValue,
	ucanCVerification
		TruthValue,
	ucanCVerificationDuration
		Integer32,
	ucanCVerificationA
		TruthValue,
	ucanCVerificationATime
		Integer32,
	ucanCVerificationAInterval
		INTEGER,
	ucanCVerificationB
		TruthValue,
	ucanCVerificationBTime
		OCTET STRING,
	ucanCVerificationC
		TruthValue,
	ucanCVerificationRetries
		Integer32,
	ucanCInputSignalTest
		Integer32,
	ucanCRestoration
		TruthValue,
	ucanCRestorationPerDay
		Integer32,
	ucanCPriorities
		TruthValue
}

ucanCompactStateConfigIndex  OBJECT-TYPE
	SYNTAX     Integer32 (1..254)
	MAX-ACCESS not-accessible
	STATUS     current
	DESCRIPTION 
		"UCA N+1 for Compact Serie General (state/configuration) index table"
	::= { ucanCompactGeneralEntry 1 }

ucanCControlAddress  OBJECT-TYPE
	SYNTAX     Integer32
	MAX-ACCESS read-only
	STATUS     current
	DESCRIPTION 
		"UCA N+1 Compact Serie Address Control"
	::= { ucanCompactGeneralEntry 2 }

ucanCLocal  OBJECT-TYPE
	SYNTAX     TruthValue
	MAX-ACCESS read-only
	STATUS     current
	DESCRIPTION 
		"UCA n+1 remote/local configuration.
		
		False: UCA n+1 could be remote-configurated 
		Truth: UCA n+1 only could by local-configurated
		"
	::= { ucanCompactGeneralEntry 3 }

ucanCManual  OBJECT-TYPE
	SYNTAX     TruthValue
	MAX-ACCESS read-write
	STATUS     current
	DESCRIPTION 
		"UCA n+1 automatic/manuall configuration.
		
		False: UCA n+1 is in automatic mode.
		Truth: UCA n+1 is in manual mode, there are manual commutations.
		"
	::= { ucanCompactGeneralEntry 4 }

ucanCAntenna  OBJECT-TYPE
	SYNTAX     INTEGER {
		antenna1 (1),
		antenna1and2 (3),
		notApply (4)
	}
	MAX-ACCESS read-write
	STATUS     current
	DESCRIPTION 
		"Antenna 1: only connected antenna 1 is switched to output
		Antenna 1 and 2: both antenna (1 and 2) are multiplexed to output"
	::= { ucanCompactGeneralEntry 5 }

ucanCSwitchedMux  OBJECT-TYPE
	SYNTAX     INTEGER {
		relay1Switched (1),
		relay2Switched (2),
		relay3Switched (3),
		relay4Switched (4),
		relay5Switched (5),
		relay6Switched (6),
		notSwitched (7)
	}
	MAX-ACCESS read-write
	STATUS     current
	DESCRIPTION 
		"UCA n+1 Switched MUX"
	::= { ucanCompactGeneralEntry 6 }

ucanCTestingMux  OBJECT-TYPE
	SYNTAX     INTEGER {
		relay1Testing (1),
		relay2Testing (2),
		relay3Testing (3),
		relay4Testing (4),
		relay5Testing (5),
		relay6Testing (6),
		notTesting (7)
	}
	MAX-ACCESS read-write
	STATUS     current
	DESCRIPTION 
		"UCA n+1 Testing MUX. Only input is switched to reserve."
	::= { ucanCompactGeneralEntry 7 }

ucanCAutoOff  OBJECT-TYPE
	SYNTAX     TruthValue
	MAX-ACCESS read-write
	STATUS     current
	DESCRIPTION 
		"Auto-switch on/off the principal MUX when is switched
		
		Truth (1): switch on and switch off the back-up module
		
		False (2): the back-up module is not switched on (off) when is is switched"
	::= { ucanCompactGeneralEntry 8 }

ucanCVerification  OBJECT-TYPE
	SYNTAX     TruthValue
	MAX-ACCESS read-write
	STATUS     current
	DESCRIPTION 
		"Autoverification process will start when A,B or C event happens.
		
		Truth (1): auto-verification is enabled
		
		False (2): auto-verification is disabled"
	::= { ucanCompactGeneralEntry 9 }

ucanCVerificationDuration  OBJECT-TYPE
	SYNTAX     Integer32 (2..65535)
	UNITS 	"seconds"
	MAX-ACCESS read-write
	STATUS     current
	DESCRIPTION 
		"Duration of verification process"
	::= { ucanCompactGeneralEntry 10 }

ucanCVerificationA  OBJECT-TYPE
	SYNTAX     TruthValue
	MAX-ACCESS read-write
	STATUS     current
	DESCRIPTION 
		"Every ucanCVerificationATime verification process will start
		
		
		
		Truth (1): enable verification A
		
		False (2): disabled verification B"
	::= { ucanCompactGeneralEntry 11 }

ucanCVerificationATime  OBJECT-TYPE
	SYNTAX     Integer32 (1..65535)
	UNITS 	"seconds"
	MAX-ACCESS read-write
	STATUS     current
	DESCRIPTION 
		"Time bettwen verification process (depends on ucanCVerificationAInterval)"
	::= { ucanCompactGeneralEntry 12 }

ucanCVerificationAInterval  OBJECT-TYPE
	SYNTAX     INTEGER {
		simple (1),
		double (2),
		triple (3)
	}
	MAX-ACCESS read-write
	STATUS     current
	DESCRIPTION 
		"Factor for ucanCVerificationATime.
		
		Simple: Each ucanCVerificationAInterval.
		Double: ucanCVerificationAInterval is doubled each test.
		Triple: ucanCVerificationAInterval is tripled each test."
	::= { ucanCompactGeneralEntry 13 }

ucanCVerificationB  OBJECT-TYPE
	SYNTAX     TruthValue
	MAX-ACCESS read-write
	STATUS     current
	DESCRIPTION 
		"Enable/Disable a day hour for verification process
		
		Truth (1): enabled daily verification
		
		False (2): disabled daily verification"
	::= { ucanCompactGeneralEntry 14 }

ucanCVerificationBTime  OBJECT-TYPE
	SYNTAX     OCTET STRING
	MAX-ACCESS read-write
	STATUS     current
	DESCRIPTION 
		"Hour for daily verification process. Format - hh:mm"
	::= { ucanCompactGeneralEntry 15 }

ucanCVerificationC  OBJECT-TYPE
	SYNTAX     TruthValue
	MAX-ACCESS read-write
	STATUS     current
	DESCRIPTION 
		"Verification process will start when an event happens
		
		True (1): enabled
		
		False (2): disabled"
	::= { ucanCompactGeneralEntry 16 }

ucanCVerificationRetries  OBJECT-TYPE
	SYNTAX     Integer32 (0..255)
	MAX-ACCESS read-write
	STATUS     current
	DESCRIPTION 
		"Number of verification retries for each MUXs"
	::= { ucanCompactGeneralEntry 17 }

ucanCInputSignalTest  OBJECT-TYPE
	SYNTAX     Integer32 (1..65535)
	UNITS 	"seconds"
	MAX-ACCESS read-write
	STATUS     current
	DESCRIPTION 
		"Duration for input signal test"
	::= { ucanCompactGeneralEntry 18 }

ucanCRestoration  OBJECT-TYPE
	SYNTAX     TruthValue
	MAX-ACCESS read-write
	STATUS     current
	DESCRIPTION 
		"A principal MUX can be restored if it is OK and the reserve is necessary for other MUX
		
		True (1): enabled auto-restaoration
		
		False (2): disabled"
	::= { ucanCompactGeneralEntry 19 }

ucanCRestorationPerDay  OBJECT-TYPE
	SYNTAX     Integer32 (0..255)
	MAX-ACCESS read-write
	STATUS     current
	DESCRIPTION 
		"Quantity of restoration per day"
	::= { ucanCompactGeneralEntry 20 }

ucanCPriorities  OBJECT-TYPE
	SYNTAX     TruthValue
	MAX-ACCESS read-write
	STATUS     current
	DESCRIPTION 
		"Relays Priorities system enabled/disabled
		
		True (1): priorities are enabled
		
		False (2): priorities are disabled"
	::= { ucanCompactGeneralEntry 21 }

ucanCompactRelaysMuxTable  OBJECT-TYPE
	SYNTAX SEQUENCE OF UcanCompactRelaysMuxEntry
	MAX-ACCESS not-accessible
	STATUS     current
	DESCRIPTION 
		"UCA N+1 for Compact Serie Realys & MUXs association table"
	::= { ucanCompact 2 }

ucanCompactRelaysMuxEntry  OBJECT-TYPE
	SYNTAX 	UcanCompactRelaysMuxEntry
	MAX-ACCESS not-accessible
	STATUS     current
	DESCRIPTION 
		"UCA N+1 for Compact Serie Realys & MUXs association table"
	INDEX { ucanCompactRelaysMuxIndex }
	::= { ucanCompactRelaysMuxTable 1 }

UcanCompactRelaysMuxEntry ::= SEQUENCE {
	ucanCompactRelaysMuxIndex
		Integer32,
	ucanCompactRelaysMuxCAddress
		Integer32,
	ucanCompactRelay1Mux
		Integer32,
	ucanCompactRelay2Mux
		Integer32,
	ucanCompactRelay3Mux
		Integer32,
	ucanCompactRelay4Mux
		Integer32,
	ucanCompactRelay5Mux
		Integer32,
	ucanCompactRelay6Mux
		Integer32,
	ucanCompactRelayReserve
		Integer32
}

ucanCompactRelaysMuxIndex  OBJECT-TYPE
	SYNTAX     Integer32 (1..254)
	MAX-ACCESS not-accessible
	STATUS     current
	DESCRIPTION 
		"UCA N+1 for Compact Serie Realys & MUXs association index"
	::= { ucanCompactRelaysMuxEntry 1 }

ucanCompactRelaysMuxCAddress  OBJECT-TYPE
	SYNTAX     Integer32 (1..254)
	MAX-ACCESS read-only
	STATUS     current
	DESCRIPTION 
		"UCA N+1 for Compact Serie Realys & MUXs association.
		UCA Control Address"
	::= { ucanCompactRelaysMuxEntry 2 }

ucanCompactRelay1Mux  OBJECT-TYPE
	SYNTAX     Integer32 (1..254)
	MAX-ACCESS read-only
	STATUS     current
	DESCRIPTION 
		"MUX Control address connected to Relay 1"
	::= { ucanCompactRelaysMuxEntry 3 }

ucanCompactRelay2Mux  OBJECT-TYPE
	SYNTAX     Integer32 (1..254)
	MAX-ACCESS read-only
	STATUS     current
	DESCRIPTION 
		"MUX Control address connected to Relay 2"
	::= { ucanCompactRelaysMuxEntry 4 }

ucanCompactRelay3Mux  OBJECT-TYPE
	SYNTAX     Integer32 (1..254)
	MAX-ACCESS read-only
	STATUS     current
	DESCRIPTION 
		"MUX Control address connected to Relay 3"
	::= { ucanCompactRelaysMuxEntry 5 }

ucanCompactRelay4Mux  OBJECT-TYPE
	SYNTAX     Integer32 (1..254)
	MAX-ACCESS read-only
	STATUS     current
	DESCRIPTION 
		"MUX Control address connected to Relay 4"
	::= { ucanCompactRelaysMuxEntry 6 }

ucanCompactRelay5Mux  OBJECT-TYPE
	SYNTAX     Integer32 (1..254)
	MAX-ACCESS read-only
	STATUS     current
	DESCRIPTION 
		"MUX Control address connected to Relay 5"
	::= { ucanCompactRelaysMuxEntry 7 }

ucanCompactRelay6Mux  OBJECT-TYPE
	SYNTAX     Integer32 (1..254)
	MAX-ACCESS read-only
	STATUS     current
	DESCRIPTION 
		"MUX Control address connected to Relay 6"
	::= { ucanCompactRelaysMuxEntry 8 }

ucanCompactRelayReserve  OBJECT-TYPE
	SYNTAX     Integer32 (1..254)
	MAX-ACCESS read-only
	STATUS     current
	DESCRIPTION 
		"Reserve Control address "
	::= { ucanCompactRelaysMuxEntry 9 }

ucanCompactRelaysPriorityTable  OBJECT-TYPE
	SYNTAX SEQUENCE OF UcanCompactRelaysPriorityEntry
	MAX-ACCESS not-accessible
	STATUS     current
	DESCRIPTION 
		"UCA N+1 for Compact Serie Realys Priority table"
	::= { ucanCompact 3 }

ucanCompactRelaysPriorityEntry  OBJECT-TYPE
	SYNTAX 	UcanCompactRelaysPriorityEntry
	MAX-ACCESS not-accessible
	STATUS     current
	DESCRIPTION 
		"UCA N+1 for Compact Serie Realys Priority table"
	INDEX { ucanCompactRelaysPriorityIndex }
	::= { ucanCompactRelaysPriorityTable 1 }

UcanCompactRelaysPriorityEntry ::= SEQUENCE {
	ucanCompactRelaysPriorityIndex
		Integer32,
	ucanCompactRelaysPriorityAddress
		Integer32,
	ucanCompactRelay1Priority
		Integer32,
	ucanCompactRelay2Priority
		Integer32,
	ucanCompactRelay3Priority
		Integer32,
	ucanCompactRelay4Priority
		Integer32,
	ucanCompactRelay5Priority
		Integer32,
	ucanCompactRelay6Priority
		Integer32
}

ucanCompactRelaysPriorityIndex  OBJECT-TYPE
	SYNTAX     Integer32 (1..254)
	MAX-ACCESS not-accessible
	STATUS     current
	DESCRIPTION 
		"UCA N+1 for Compact Serie Realys Priority Index"
	::= { ucanCompactRelaysPriorityEntry 1 }

ucanCompactRelaysPriorityAddress  OBJECT-TYPE
	SYNTAX     Integer32
	MAX-ACCESS read-only
	STATUS     current
	DESCRIPTION 
		"UCA N+1 for Compact Serie Realys Priority.
		UCA Control Address"
	::= { ucanCompactRelaysPriorityEntry 2 }

ucanCompactRelay1Priority  OBJECT-TYPE
	SYNTAX     Integer32 (0|1..6)
	MAX-ACCESS read-write
	STATUS     current
	DESCRIPTION 
		"Relay 1 Priority"
	::= { ucanCompactRelaysPriorityEntry 3 }

ucanCompactRelay2Priority  OBJECT-TYPE
	SYNTAX     Integer32 (0|1..6)
	MAX-ACCESS read-write
	STATUS     current
	DESCRIPTION 
		"Relay 2 Priority"
	::= { ucanCompactRelaysPriorityEntry 4 }

ucanCompactRelay3Priority  OBJECT-TYPE
	SYNTAX     Integer32 (0|1..6)
	MAX-ACCESS read-write
	STATUS     current
	DESCRIPTION 
		"Relay 3 Priority"
	::= { ucanCompactRelaysPriorityEntry 5 }

ucanCompactRelay4Priority  OBJECT-TYPE
	SYNTAX     Integer32 (0|1..6)
	MAX-ACCESS read-write
	STATUS     current
	DESCRIPTION 
		"Relay 4 Priority"
	::= { ucanCompactRelaysPriorityEntry 6 }

ucanCompactRelay5Priority  OBJECT-TYPE
	SYNTAX     Integer32 (0|1..6)
	MAX-ACCESS read-write
	STATUS     current
	DESCRIPTION 
		"Relay 5 Priority"
	::= { ucanCompactRelaysPriorityEntry 7 }

ucanCompactRelay6Priority  OBJECT-TYPE
	SYNTAX     Integer32 (0|1..6)
	MAX-ACCESS read-write
	STATUS     current
	DESCRIPTION 
		"Relay 6 Priority"
	::= { ucanCompactRelaysPriorityEntry 8 }

ucanCompactAlarmTable  OBJECT-TYPE
	SYNTAX SEQUENCE OF UcanCompactAlarmEntry
	MAX-ACCESS not-accessible
	STATUS     current
	DESCRIPTION 
		"UCA N+1 for Compact Serie Alarm Table"
	::= { ucanCompact 4 }

ucanCompactAlarmEntry  OBJECT-TYPE
	SYNTAX 	UcanCompactAlarmEntry
	MAX-ACCESS not-accessible
	STATUS     current
	DESCRIPTION 
		"UCA N+1 for Compact Serie Alarm Table"
	INDEX { ucanCompactAlarmIndex }
	::= { ucanCompactAlarmTable 1 }

UcanCompactAlarmEntry ::= SEQUENCE {
	ucanCompactAlarmIndex
		Integer32,
	ucanCompactAlarmAddress
		Integer32,
	ucanCompactAlarmFault
		TruthValue,
	ucanCompactAlarmWarning
		TruthValue,
	ucanCompactAlarmAlimentationFault
		TruthValue,
	ucanCompactAlarmHW
		TruthValue
}

ucanCompactAlarmIndex  OBJECT-TYPE
	SYNTAX     Integer32 (1..254)
	MAX-ACCESS not-accessible
	STATUS     current
	DESCRIPTION 
		"UCA N+1 for Compact Serie Alarm Index"
	::= { ucanCompactAlarmEntry 1 }

ucanCompactAlarmAddress  OBJECT-TYPE
	SYNTAX     Integer32 (1..254)
	MAX-ACCESS read-only
	STATUS     current
	DESCRIPTION 
		"UCA N+1 for Compact Seire Alarm Table
		UCA Control Address"
	::= { ucanCompactAlarmEntry 2 }

ucanCompactAlarmFault  OBJECT-TYPE
	SYNTAX     TruthValue
	MAX-ACCESS read-only
	STATUS     current
	DESCRIPTION 
		"Fault Alarm"
	::= { ucanCompactAlarmEntry 3 }

ucanCompactAlarmWarning  OBJECT-TYPE
	SYNTAX     TruthValue
	MAX-ACCESS read-only
	STATUS     current
	DESCRIPTION 
		"Warning Alarm"
	::= { ucanCompactAlarmEntry 4 }

ucanCompactAlarmAlimentationFault  OBJECT-TYPE
	SYNTAX     TruthValue
	MAX-ACCESS read-only
	STATUS     current
	DESCRIPTION 
		"Alimentation Alarm"
	::= { ucanCompactAlarmEntry 5 }

ucanCompactAlarmHW  OBJECT-TYPE
	SYNTAX     TruthValue
	MAX-ACCESS read-only
	STATUS     current
	DESCRIPTION 
		"Internal hardware Alarm"
	::= { ucanCompactAlarmEntry 6 }

ucanCompactMuteMuxTable  OBJECT-TYPE
	SYNTAX SEQUENCE OF UcanCompactMuteMuxEntry
	MAX-ACCESS not-accessible
	STATUS     current
	DESCRIPTION 
		"UCA N+1 for Compact Serie Mute MUX"
	::= { ucanCompact 5 }

ucanCompactMuteMuxEntry  OBJECT-TYPE
	SYNTAX 	UcanCompactMuteMuxEntry
	MAX-ACCESS not-accessible
	STATUS     current
	DESCRIPTION 
		"UCA N+1 for Compact Serie Mute MUX"
	INDEX { ucanCompactMuteMuxIndex }
	::= { ucanCompactMuteMuxTable 1 }

UcanCompactMuteMuxEntry ::= SEQUENCE {
	ucanCompactMuteMuxIndex
		Integer32,
	ucanCompactMuteMuxAddress
		Integer32,
	ucanCompactRelay1MuteMux
		Integer32,
	ucanCompactRelay2MuteMux
		Integer32,
	ucanCompactRelay3MuteMux
		Integer32,
	ucanCompactRelay4MuteMux
		Integer32,
	ucanCompactRelay5MuteMux
		Integer32,
	ucanCompactRelay6MuteMux
		Integer32
}

ucanCompactMuteMuxIndex  OBJECT-TYPE
	SYNTAX     Integer32 (1..254)
	MAX-ACCESS not-accessible
	STATUS     current
	DESCRIPTION 
		"UCA N+1 for Compact Serie Realys Mute MUX Index"
	::= { ucanCompactMuteMuxEntry 1 }

ucanCompactMuteMuxAddress  OBJECT-TYPE
	SYNTAX     Integer32 (1..255)
	MAX-ACCESS read-only
	STATUS     current
	DESCRIPTION 
		"UCA N+1 for Compact Serie Realys Mute MUX.
		UCA Control Address"
	::= { ucanCompactMuteMuxEntry 2 }

ucanCompactRelay1MuteMux  OBJECT-TYPE
	SYNTAX     TruthValue
	MAX-ACCESS read-write
	STATUS     current
	DESCRIPTION 
		"Relay 1 Mute MUX"
	::= { ucanCompactMuteMuxEntry 3 }

ucanCompactRelay2MuteMux  OBJECT-TYPE
	SYNTAX     TruthValue
	MAX-ACCESS read-write
	STATUS     current
	DESCRIPTION 
		"Relay 2 Mute MUX"
	::= { ucanCompactMuteMuxEntry 4 }

ucanCompactRelay3MuteMux  OBJECT-TYPE
	SYNTAX     TruthValue
	MAX-ACCESS read-write
	STATUS     current
	DESCRIPTION 
		"Relay 3 Mute MUX"
	::= { ucanCompactMuteMuxEntry 5 }

ucanCompactRelay4MuteMux  OBJECT-TYPE
	SYNTAX     TruthValue
	MAX-ACCESS read-write
	STATUS     current
	DESCRIPTION 
		"Relay 4 Mute MUX"
	::= { ucanCompactMuteMuxEntry 6 }

ucanCompactRelay5MuteMux  OBJECT-TYPE
	SYNTAX     TruthValue
	MAX-ACCESS read-write
	STATUS     current
	DESCRIPTION 
		"Relay 5 Mute MUX"
	::= { ucanCompactMuteMuxEntry 7 }

ucanCompactRelay6MuteMux  OBJECT-TYPE
	SYNTAX     TruthValue
	MAX-ACCESS read-write
	STATUS     current
	DESCRIPTION 
		"Relay 6 Mute MUX"
	::= { ucanCompactMuteMuxEntry 8 }

uca1Table  OBJECT-TYPE
	SYNTAX SEQUENCE OF Uca1Entry
	MAX-ACCESS not-accessible
	STATUS     current
	DESCRIPTION 
		"This table contains the basic information of each UCA connected to the system."
	::= { uca1 1 }

uca1Entry  OBJECT-TYPE
	SYNTAX 	Uca1Entry
	MAX-ACCESS not-accessible
	STATUS     current
	DESCRIPTION 
		"Each row is UCA 1+1 information."
	INDEX { uca1Index }
	::= { uca1Table 1 }

Uca1Entry ::= SEQUENCE {
	uca1Index
		Integer32,
	uca1CtrlAddress
		Integer32,
	uca1Mode
		Integer32,
	uca1Preferential
		INTEGER,
	uca1Antenna
		INTEGER,
	uca1TestDuration
		Integer32,
	uca1NoMute
		TruthValue,
	uca1Firmware
		DisplayString,
	uca1RowIndex
		Integer32,
	uca1Ready
		TruthValue
}

uca1Index  OBJECT-TYPE
	SYNTAX     Integer32 (1..15)
	MAX-ACCESS not-accessible
	STATUS     current
	DESCRIPTION 
		"UCA 1+1 index"
	::= { uca1Entry 1 }

uca1CtrlAddress  OBJECT-TYPE
	SYNTAX     Integer32 (71..85)
	MAX-ACCESS read-only
	STATUS     current
	DESCRIPTION 
		"Control address."
	::= { uca1Entry 2 }

uca1Mode  OBJECT-TYPE
	SYNTAX     Integer32 (0|1|2|3)
	MAX-ACCESS read-write
	STATUS     current
	DESCRIPTION 
		"UCA 1+1 operation mode
		
		0: Manual
		1: Auto-return off
		2: Auto
		3: Auto-return on"
	::= { uca1Entry 3 }

uca1Preferential  OBJECT-TYPE
	SYNTAX     INTEGER {
		uca1PreferentialA (1),
		uca1PreferentialB (2)
	}
	MAX-ACCESS read-write
	STATUS     current
	DESCRIPTION 
		"UCA 1+1 preferential MUX
		
		1: MUX A
		2: MUX B
		
		Note: it is only possible to set this parameter if UCA 1+1 is in automatic mode."
	::= { uca1Entry 4 }

uca1Antenna  OBJECT-TYPE
	SYNTAX     INTEGER {
		uca1AntennaA (1),
		uca1AntennaB (2)
	}
	MAX-ACCESS read-write
	STATUS     current
	DESCRIPTION 
		"MUX to antenna
		
		1: MUX A to antenna
		2: MUX B to antenna
		
		Note: it is only possible set this parameter if UCA 1+1 is in manual mode."
	::= { uca1Entry 5 }

uca1TestDuration  OBJECT-TYPE
	SYNTAX     Integer32 (0..60)
	UNITS 	"Seconds"
	MAX-ACCESS read-write
	STATUS     current
	DESCRIPTION 
		"Test duration of alternative MUX (seconds)
		
		Note: it is only possible set this parameter if UCA 1+1 is in automatic mode."
	::= { uca1Entry 6 }

uca1NoMute  OBJECT-TYPE
	SYNTAX     TruthValue
	UNITS 	"dsec"
	MAX-ACCESS read-write
	STATUS     current
	DESCRIPTION 
		"The alternative MUX switched to load is not muted.
		
		Note: it is only possible set this parameter no Mute if UCA 1+1 is in manual mode"
	::= { uca1Entry 7 }

uca1Firmware  OBJECT-TYPE
	SYNTAX     DisplayString
	MAX-ACCESS read-only
	STATUS     current
	DESCRIPTION 
		"UCA Firmware version"
	::= { uca1Entry 8 }

uca1RowIndex  OBJECT-TYPE
	SYNTAX     Integer32 (1..15)
	MAX-ACCESS read-only
	STATUS     current
	DESCRIPTION 
		"UCA 1+1 index (readable)"
	::= { uca1Entry 9 }

uca1Ready  OBJECT-TYPE
	SYNTAX     TruthValue
	MAX-ACCESS read-only
	STATUS     current
	DESCRIPTION 
		"UCA 1+1 is ready for commutation process.
		
		"
	::= { uca1Entry 10 }

uca1MuxConmutationTable  OBJECT-TYPE
	SYNTAX SEQUENCE OF Uca1MuxConmutationEntry
	MAX-ACCESS not-accessible
	STATUS     current
	DESCRIPTION 
		"With this table, It is possible select wich alarm is event switch."
	::= { uca1 2 }

uca1MuxConmutationEntry  OBJECT-TYPE
	SYNTAX 	Uca1MuxConmutationEntry
	MAX-ACCESS not-accessible
	STATUS     current
	DESCRIPTION 
		"Each row is UCA 1+1 information."
	INDEX { uca1MuxConmutationIndex }
	::= { uca1MuxConmutationTable 1 }

Uca1MuxConmutationEntry ::= SEQUENCE {
	uca1MuxConmutationIndex
		Integer32,
	uca1CtrlAddressConmutationAlarm
		Integer32,
	uca1MuxTransmittedPowerAlarm
		INTEGER,
	uca1MuxTrtCurrentsOutRangeAlarm
		TruthValue,
	uca1MuxReflectedPowerAlarm
		TruthValue,
	uca1MuxUnLockTSAlarm
		TruthValue,
	uca1MuxNoInputSignalAlarm
		TruthValue,
	uca1MuxAsiErrorAlarm
		TruthValue,
	uca1MuxMipErrorAlarm
		TruthValue,
	uca1MuxPpsAlarm
		TruthValue,
	uca1MuxIFDVBTSignalAlarm
		TruthValue,
	uca1MuxGps10MHzAlarm
		TruthValue,
	uca1MuxPowerAmplifierCommunAlarm
		TruthValue,
	uca1MuxTemperatureAlarm
		TruthValue,
	uca1MuxModuleCommunitacionAlarm
		TruthValue,
	uca1MuxCBerAlarm
		TruthValue,
	uca1MuxVBerAlarm
		TruthValue,
	uca1MuxConmutationRowIndex
		Integer32
}

uca1MuxConmutationIndex  OBJECT-TYPE
	SYNTAX     Integer32 (1..15)
	MAX-ACCESS not-accessible
	STATUS     current
	DESCRIPTION 
		"UCA 1+1 index"
	::= { uca1MuxConmutationEntry 1 }

uca1CtrlAddressConmutationAlarm  OBJECT-TYPE
	SYNTAX     Integer32 (71..85)
	MAX-ACCESS read-only
	STATUS     current
	DESCRIPTION 
		"Control address for this module (UCA 1+1)
		
		71 ---> MUX address 001 (A) and 101 (B)
		...
		85 ---> MUX address 015 (A) and 115 (B)
		"
	::= { uca1MuxConmutationEntry 2 }

uca1MuxTransmittedPowerAlarm  OBJECT-TYPE
	SYNTAX     INTEGER {
		disabled (1),
		lessThan6dBs (2),
		lessThan3dBs (3)
	}
	MAX-ACCESS read-write
	STATUS     current
	DESCRIPTION 
		"Transmitted Power lower than nominal
		
		1: disabled
		2: less than 6 dBs
		3: less than 3 dBs"
	::= { uca1MuxConmutationEntry 3 }

uca1MuxTrtCurrentsOutRangeAlarm  OBJECT-TYPE
	SYNTAX     TruthValue
	MAX-ACCESS read-write
	STATUS     current
	DESCRIPTION 
		"Power amplifier firmware version"
	::= { uca1MuxConmutationEntry 4 }

uca1MuxReflectedPowerAlarm  OBJECT-TYPE
	SYNTAX     TruthValue
	MAX-ACCESS read-write
	STATUS     current
	DESCRIPTION 
		"Reflected power alarm status"
	::= { uca1MuxConmutationEntry 5 }

uca1MuxUnLockTSAlarm  OBJECT-TYPE
	SYNTAX     TruthValue
	MAX-ACCESS read-write
	STATUS     current
	DESCRIPTION 
		"Unlock Transport Stream alarm"
	::= { uca1MuxConmutationEntry 6 }

uca1MuxNoInputSignalAlarm  OBJECT-TYPE
	SYNTAX     TruthValue
	MAX-ACCESS read-write
	STATUS     current
	DESCRIPTION 
		"No input signal alarm"
	::= { uca1MuxConmutationEntry 7 }

uca1MuxAsiErrorAlarm  OBJECT-TYPE
	SYNTAX     TruthValue
	MAX-ACCESS read-write
	STATUS     current
	DESCRIPTION 
		"ASI error alarm"
	::= { uca1MuxConmutationEntry 8 }

uca1MuxMipErrorAlarm  OBJECT-TYPE
	SYNTAX     TruthValue
	MAX-ACCESS read-write
	STATUS     current
	DESCRIPTION 
		"MIP error alarm"
	::= { uca1MuxConmutationEntry 9 }

uca1MuxPpsAlarm  OBJECT-TYPE
	SYNTAX     TruthValue
	MAX-ACCESS read-write
	STATUS     current
	DESCRIPTION 
		"1 pps alarm status"
	::= { uca1MuxConmutationEntry 10 }

uca1MuxIFDVBTSignalAlarm  OBJECT-TYPE
	SYNTAX     TruthValue
	MAX-ACCESS read-write
	STATUS     current
	DESCRIPTION 
		"No DVBT IF signal alarm"
	::= { uca1MuxConmutationEntry 11 }

uca1MuxGps10MHzAlarm  OBJECT-TYPE
	SYNTAX     TruthValue
	MAX-ACCESS read-write
	STATUS     current
	DESCRIPTION 
		"10 MHz alarm"
	::= { uca1MuxConmutationEntry 12 }

uca1MuxPowerAmplifierCommunAlarm  OBJECT-TYPE
	SYNTAX     TruthValue
	MAX-ACCESS read-write
	STATUS     current
	DESCRIPTION 
		"Power Amplifier communication"
	::= { uca1MuxConmutationEntry 13 }

uca1MuxTemperatureAlarm  OBJECT-TYPE
	SYNTAX     TruthValue
	MAX-ACCESS read-write
	STATUS     current
	DESCRIPTION 
		"Temperature alarm"
	::= { uca1MuxConmutationEntry 14 }

uca1MuxModuleCommunitacionAlarm  OBJECT-TYPE
	SYNTAX     TruthValue
	MAX-ACCESS read-write
	STATUS     current
	DESCRIPTION 
		"Communication alarm"
	::= { uca1MuxConmutationEntry 15 }

uca1MuxCBerAlarm  OBJECT-TYPE
	SYNTAX     TruthValue
	MAX-ACCESS read-write
	STATUS     current
	DESCRIPTION 
		"Channel BER (pre-Viterbi) alarm status"
	::= { uca1MuxConmutationEntry 16 }

uca1MuxVBerAlarm  OBJECT-TYPE
	SYNTAX     TruthValue
	MAX-ACCESS read-write
	STATUS     current
	DESCRIPTION 
		"VBER (post-Viterbi) alarm status"
	::= { uca1MuxConmutationEntry 17 }

uca1MuxConmutationRowIndex  OBJECT-TYPE
	SYNTAX     Integer32 (1..15)
	MAX-ACCESS read-only
	STATUS     current
	DESCRIPTION 
		"UCA 1+1 index (readable)"
	::= { uca1MuxConmutationEntry 18 }

uca1AlarmsTable  OBJECT-TYPE
	SYNTAX SEQUENCE OF Uca1AlarmsEntry
	MAX-ACCESS not-accessible
	STATUS     current
	DESCRIPTION 
		"This table contains the alarm status for each UCA 1+1"
	::= { uca1 3 }

uca1AlarmsEntry  OBJECT-TYPE
	SYNTAX 	Uca1AlarmsEntry
	MAX-ACCESS not-accessible
	STATUS     current
	DESCRIPTION 
		"Each row is UCA 1+1 information."
	INDEX { uca1AlarmsIndex }
	::= { uca1AlarmsTable 1 }

Uca1AlarmsEntry ::= SEQUENCE {
	uca1AlarmsIndex
		Integer32,
	uca1CtrlAddressAlarm
		Integer32,
	uca1BlockedA
		TruthValue,
	uca1BlockedB
		TruthValue,
	uca1UndeterminatedRelay
		TruthValue,
	uca1IncorrectConfiguration
		TruthValue,
	uca1ConmutationError
		TruthValue,
	uca1MuxA
		TruthValue,
	uca1MuxB
		TruthValue,
	uca1AlarmsRowIndex
		Integer32
}

uca1AlarmsIndex  OBJECT-TYPE
	SYNTAX     Integer32 (1..6)
	MAX-ACCESS not-accessible
	STATUS     current
	DESCRIPTION 
		"UCA 1+1 index"
	::= { uca1AlarmsEntry 1 }

uca1CtrlAddressAlarm  OBJECT-TYPE
	SYNTAX     Integer32 (20..25)
	MAX-ACCESS read-only
	STATUS     current
	DESCRIPTION 
		"Control address for this module"
	::= { uca1AlarmsEntry 2 }

uca1BlockedA  OBJECT-TYPE
	SYNTAX     TruthValue
	MAX-ACCESS read-only
	STATUS     current
	DESCRIPTION 
		"Relay is blocked in A position."
	::= { uca1AlarmsEntry 3 }

uca1BlockedB  OBJECT-TYPE
	SYNTAX     TruthValue
	MAX-ACCESS read-only
	STATUS     current
	DESCRIPTION 
		"Relay is blocked in B position."
	::= { uca1AlarmsEntry 4 }

uca1UndeterminatedRelay  OBJECT-TYPE
	SYNTAX     TruthValue
	MAX-ACCESS read-only
	STATUS     current
	DESCRIPTION 
		"Relay position is unknown."
	::= { uca1AlarmsEntry 5 }

uca1IncorrectConfiguration  OBJECT-TYPE
	SYNTAX     TruthValue
	MAX-ACCESS read-only
	STATUS     current
	DESCRIPTION 
		"The MUX A type is not the same that MUX B type."
	::= { uca1AlarmsEntry 6 }

uca1ConmutationError  OBJECT-TYPE
	SYNTAX     TruthValue
	MAX-ACCESS read-only
	STATUS     current
	DESCRIPTION 
		"UCA 1+1 conmutation error. It was impossible to finish all conmutation process."
	::= { uca1AlarmsEntry 7 }

uca1MuxA  OBJECT-TYPE
	SYNTAX     TruthValue
	MAX-ACCESS read-only
	STATUS     current
	DESCRIPTION 
		"During conmutation process, it was not possible configure MUX A.
		There are not communication with MUX A."
	::= { uca1AlarmsEntry 8 }

uca1MuxB  OBJECT-TYPE
	SYNTAX     TruthValue
	MAX-ACCESS read-only
	STATUS     current
	DESCRIPTION 
		"During conmutation process, it was not possible configure MUX B.
		There are not communication with MUX B."
	::= { uca1AlarmsEntry 9 }

uca1AlarmsRowIndex  OBJECT-TYPE
	SYNTAX     Integer32 (1..15)
	MAX-ACCESS read-only
	STATUS     current
	DESCRIPTION 
		"UCA 1+1 index (readable)"
	::= { uca1AlarmsEntry 10 }

dvbs2AsiRedundanceTable  OBJECT-TYPE
	SYNTAX SEQUENCE OF Dvbs2AsiRedundanceEntry
	MAX-ACCESS not-accessible
	STATUS     current
	DESCRIPTION 
		"An input (RF B) is redundant from another one (RF A) by cloning the configuration.
		The ouput configurated for RF A, will switch to RF B after hysteresis time."
	::= { dvbs2Asi 1 }

dvbs2AsiRedundanceEntry  OBJECT-TYPE
	SYNTAX 	Dvbs2AsiRedundanceEntry
	MAX-ACCESS not-accessible
	STATUS     current
	DESCRIPTION 
		"There are 4 RF inputs, so 4 redundance possibilities"
	INDEX { reduncandeRfIndex, 
		redundanceRfModuleIndex }
	::= { dvbs2AsiRedundanceTable 1 }

Dvbs2AsiRedundanceEntry ::= SEQUENCE {
	redundanceRfModuleIndex
		Integer32,
	redundanceRfCtrlAddress
		Integer32,
	reduncandeRfIndex
		Integer32,
	redundanceInput
		INTEGER
}

redundanceRfModuleIndex  OBJECT-TYPE
	SYNTAX     Integer32 (1..255)
	MAX-ACCESS not-accessible
	STATUS     current
	DESCRIPTION 
		"For each dvb-s2 / ASI module, it will be a redundancy table"
	::= { dvbs2AsiRedundanceEntry 1 }

redundanceRfCtrlAddress  OBJECT-TYPE
	SYNTAX     Integer32 (-1|1..255)
	MAX-ACCESS read-only
	STATUS     current
	DESCRIPTION 
		"Control Address for this module"
	::= { dvbs2AsiRedundanceEntry 2 }

reduncandeRfIndex  OBJECT-TYPE
	SYNTAX     Integer32 (1..4)
	MAX-ACCESS not-accessible
	STATUS     current
	DESCRIPTION 
		"For each module, would be 4 RF inputs"
	::= { dvbs2AsiRedundanceEntry 3 }

redundanceInput  OBJECT-TYPE
	SYNTAX     INTEGER {
		rf1 (1),
		rf2 (2),
		rf3 (3),
		rf4 (4),
		auxRf1 (5),
		auxRf2 (6),
		auxRf3 (7),
		auxRf4 (8),
		notRedundance (9)
	}
	MAX-ACCESS read-write
	STATUS     current
	DESCRIPTION 
		"Configure a redundancy for this module
		
		Configure other input redundance from this - rf1, rf2, rf3, rf4
		This input is configurated like auxiliar from other - auxRf1, auxRf2, auxRf3, auxRf4"
	::= { dvbs2AsiRedundanceEntry 4 }

dvbs2AsiInputRfTable  OBJECT-TYPE
	SYNTAX SEQUENCE OF Dvbs2AsiInputRfEntry
	MAX-ACCESS not-accessible
	STATUS     current
	DESCRIPTION 
		"Configure the ASI inputs"
	::= { dvbs2Asi 2 }

dvbs2AsiInputRfEntry  OBJECT-TYPE
	SYNTAX 	Dvbs2AsiInputRfEntry
	MAX-ACCESS not-accessible
	STATUS     current
	DESCRIPTION 
		"It would be 2 index: the dvbs2Asi module, and the 1...4 possible inputs"
	INDEX { inputRfIndex, 
		inputRfModuleIndex }
	::= { dvbs2AsiInputRfTable 1 }

Dvbs2AsiInputRfEntry ::= SEQUENCE {
	inputRfModuleIndex
		Integer32,
	inputRfCtrlAddress
		Integer32,
	inputRfIndex
		Integer32,
	inputRf
		INTEGER,
	inputRfState
		INTEGER,
	inputRfLnb
		INTEGER,
	inputRfFrequency
		Gauge32,
	inputRfPolarization
		INTEGER,
	inputRfBandFreq
		Gauge32,
	inputRfBandFreqLH
		INTEGER,
	inputRfLnbLowFreq
		Gauge32,
	inputRfLnbDual
		TruthValue,
	inputRfLnbHighFreq
		Gauge32,
	inputRfMode
		INTEGER,
	inputRfSatellite
		INTEGER,
	inputRfPls
		Integer32,
	inputRfSymbolRateAuto
		TruthValue,
	inputRfSymbolRate
		Integer32,
	inputRfSymbolRateCurrent
		Integer32,
	inputRfIqModeCurrent
		INTEGER,
	inputRfStandard
		INTEGER,
	inputRfIsis
		DisplayString,
	inputRfRollOff
		INTEGER,
	inputRfPilot
		INTEGER,
	inputRfFrameLength
		INTEGER,
	inputRfModulation
		INTEGER,
	inputRfFec
		INTEGER,
	inputRfCber
		DisplayString,
	inputRfVber
		DisplayString,
	inputRfCn
		DisplayString,
	inputRfLinkMargin
		DisplayString,
	inputRfPower
		DisplayString
}

inputRfModuleIndex  OBJECT-TYPE
	SYNTAX     Integer32 (1..255)
	MAX-ACCESS not-accessible
	STATUS     current
	DESCRIPTION 
		"Module Index"
	::= { dvbs2AsiInputRfEntry 1 }

inputRfCtrlAddress  OBJECT-TYPE
	SYNTAX     Integer32 (-1|1..255)
	MAX-ACCESS read-only
	STATUS     current
	DESCRIPTION 
		"Module Control Address"
	::= { dvbs2AsiInputRfEntry 2 }

inputRfIndex  OBJECT-TYPE
	SYNTAX     Integer32 (1..4)
	MAX-ACCESS not-accessible
	STATUS     current
	DESCRIPTION 
		"RF Input index (up to 4)"
	::= { dvbs2AsiInputRfEntry 3 }

inputRf  OBJECT-TYPE
	SYNTAX     INTEGER {
		inputRfEnabled (1),
		inputRfDisabled (2),
		inputDeactivated (3)
	}
	MAX-ACCESS read-write
	STATUS     current
	DESCRIPTION 
		"Enable/Disable this RF input for this module"
	::= { dvbs2AsiInputRfEntry 4 }

inputRfState  OBJECT-TYPE
	SYNTAX     INTEGER {
		inputRfLocked (1),
		inputRfUnlocked (2)
	}
	MAX-ACCESS read-only
	STATUS     current
	DESCRIPTION 
		"If this RF input is enabled, its state could be locked or unlocked"
	::= { dvbs2AsiInputRfEntry 5 }

inputRfLnb  OBJECT-TYPE
	SYNTAX     INTEGER {
		lnbOn (1),
		lnbOff (2)
	}
	MAX-ACCESS read-write
	STATUS     current
	DESCRIPTION 
		"LNB is on or off"
	::= { dvbs2AsiInputRfEntry 6 }

inputRfFrequency  OBJECT-TYPE
	SYNTAX     Gauge32
	MAX-ACCESS read-write
	STATUS     current
	DESCRIPTION 
		"When LNB is on, Sat-Frequency must configurated"
	::= { dvbs2AsiInputRfEntry 7 }

inputRfPolarization  OBJECT-TYPE
	SYNTAX     INTEGER {
		polarizationVertical (1),
		polarizationHorizontal (2)
	}
	MAX-ACCESS read-write
	STATUS     current
	DESCRIPTION 
		"When LNB is enabled, its polarization (vertical/horizontal) must be configurated."
	::= { dvbs2AsiInputRfEntry 8 }

inputRfBandFreq  OBJECT-TYPE
	SYNTAX     Gauge32
	MAX-ACCESS read-write
	STATUS     current
	DESCRIPTION 
		"When the LNB is off, it is necessary to configure de Band Frequency.
		If LNB is on, this value will be automatically calculated."
	::= { dvbs2AsiInputRfEntry 9 }

inputRfBandFreqLH  OBJECT-TYPE
	SYNTAX     INTEGER {
		bandLow (1),
		bandHigh (2)
	}
	MAX-ACCESS read-only
	STATUS     current
	DESCRIPTION 
		"LNB 22 Khz tone (Low/High band)"
	::= { dvbs2AsiInputRfEntry 10 }

inputRfLnbLowFreq  OBJECT-TYPE
	SYNTAX     Gauge32
	MAX-ACCESS read-write
	STATUS     current
	DESCRIPTION 
		"Configure the OL Low frequency if LNB is on"
	::= { dvbs2AsiInputRfEntry 11 }

inputRfLnbDual  OBJECT-TYPE
	SYNTAX     TruthValue
	MAX-ACCESS read-write
	STATUS     current
	DESCRIPTION 
		"Enable Dual (Low and high) LNB "
	::= { dvbs2AsiInputRfEntry 12 }

inputRfLnbHighFreq  OBJECT-TYPE
	SYNTAX     Gauge32
	MAX-ACCESS read-write
	STATUS     current
	DESCRIPTION 
		"When dual LNB is on, it configures OL high frequency"
	::= { dvbs2AsiInputRfEntry 13 }

inputRfMode  OBJECT-TYPE
	SYNTAX     INTEGER {
		inputRfModeAuto (1),
		inputRfModeS (2),
		inputRfModeS2 (3)
	}
	MAX-ACCESS read-write
	STATUS     current
	DESCRIPTION 
		"Configure DVB-S version (1 or 2) or automatic mode"
	::= { dvbs2AsiInputRfEntry 14 }

inputRfSatellite  OBJECT-TYPE
	SYNTAX     INTEGER {
		satelliteA (1),
		satelliteB (2),
		satelliteC (3),
		satelliteD (4)
	}
	MAX-ACCESS read-write
	STATUS     current
	DESCRIPTION 
		"DiSEqC switch configuration A,B,C,D"
	::= { dvbs2AsiInputRfEntry 15 }

inputRfPls  OBJECT-TYPE
	SYNTAX     Integer32 (1..65535)
	MAX-ACCESS read-write
	STATUS     current
	DESCRIPTION 
		"PLS code"
	::= { dvbs2AsiInputRfEntry 16 }

inputRfSymbolRateAuto  OBJECT-TYPE
	SYNTAX     TruthValue
	MAX-ACCESS read-write
	STATUS     current
	DESCRIPTION 
		"Enable/Disable automatic symbol rate"
	::= { dvbs2AsiInputRfEntry 17 }

inputRfSymbolRate  OBJECT-TYPE
	SYNTAX     Integer32
	MAX-ACCESS read-write
	STATUS     current
	DESCRIPTION 
		"Manual symbol rate"
	::= { dvbs2AsiInputRfEntry 18 }

inputRfSymbolRateCurrent  OBJECT-TYPE
	SYNTAX     Integer32
	UNITS 	"KS/s"
	MAX-ACCESS read-only
	STATUS     current
	DESCRIPTION 
		"Symbol Rate Current KSymbols/sec"
	::= { dvbs2AsiInputRfEntry 19 }

inputRfIqModeCurrent  OBJECT-TYPE
	SYNTAX     INTEGER {
		inputRfIqModeCurrentNull (1),
		inputRfIqModeCurrentNormal (2),
		inputRfIqModeCurrentInverted (3)
	}
	MAX-ACCESS read-only
	STATUS     current
	DESCRIPTION 
		"IQ state (normal/inverted). Null if unlocked."
	::= { dvbs2AsiInputRfEntry 20 }

inputRfStandard  OBJECT-TYPE
	SYNTAX     INTEGER {
		inputRfDvbS (1),
		inputRfDvbS2 (2),
		inputRfUnlocked (3)
	}
	MAX-ACCESS read-only
	STATUS     current
	DESCRIPTION 
		"When inputRfMode is auto, it shows DVB-S or DVB-S2 input detection"
	::= { dvbs2AsiInputRfEntry 21 }

inputRfIsis  OBJECT-TYPE
	SYNTAX     DisplayString
	MAX-ACCESS read-only
	STATUS     current
	DESCRIPTION 
		"ISIs"
	::= { dvbs2AsiInputRfEntry 22 }

inputRfRollOff  OBJECT-TYPE
	SYNTAX     INTEGER {
		inputRfRollOffNull (1),
		inputRfRollOff035 (2),
		inputRfRollOff025 (3),
		inputRfRollOff020 (4)
	}
	MAX-ACCESS read-only
	STATUS     current
	DESCRIPTION 
		"Roll-Off: possible values: 0.35, 0.25, 0.20"
	::= { dvbs2AsiInputRfEntry 23 }

inputRfPilot  OBJECT-TYPE
	SYNTAX     INTEGER {
		inputRfPilotYes (1),
		inputRfPilotNo (2),
		inputRfPilotNull (3)
	}
	MAX-ACCESS read-only
	STATUS     current
	DESCRIPTION 
		"Pilot"
	::= { dvbs2AsiInputRfEntry 24 }

inputRfFrameLength  OBJECT-TYPE
	SYNTAX     INTEGER {
		inputRfFrameLengthShort (1),
		inputRfFrameLengthLong (2),
		inputRfFrameLengthNull (3)
	}
	MAX-ACCESS read-only
	STATUS     current
	DESCRIPTION 
		"Frame Length"
	::= { dvbs2AsiInputRfEntry 25 }

inputRfModulation  OBJECT-TYPE
	SYNTAX     INTEGER {
		inputRfModulationNull (1),
		inputRfModulationQPSK (2),
		inputRfModulation8PSK (3),
		inputRfModulation16APSK (4),
		inputRfModulation32APSK (5)
	}
	MAX-ACCESS read-only
	STATUS     current
	DESCRIPTION 
		"Modulation"
	::= { dvbs2AsiInputRfEntry 26 }

inputRfFec  OBJECT-TYPE
	SYNTAX     INTEGER {
		inputRfFecNull (1),
		inputRfFec1div2 (2),
		inputRfFec2div3 (3),
		inputRfFec3div4 (4),
		inputRfFec4div5 (5),
		inputRfFec5div6 (6),
		inputRfFec6div7 (7),
		inputRfFec7div8 (8),
		inputRfFec8div9 (9),
		inputRfFecNone (10),
		inputRfFec1div4 (11),
		inputRfFec1div3 (12),
		inputRfFec2div5 (13),
		inputRfFec3div5 (14),
		inputRfFec9div10 (15)
	}
	MAX-ACCESS read-only
	STATUS     current
	DESCRIPTION 
		"FEC (Code Rate) 
		
		1: N/A (The multiplex is a GapFiller)
		2: 1/2 
		3: 2/3 
		4: 3/4
		5: 4/5
		6: 5/6 
		7: 6/7
		8: 7/8
		9: 8/9
		10: 1/4
		11: 1/3
		12: 2/5
		13: 3/5
		14: 9/10"
	::= { dvbs2AsiInputRfEntry 27 }

inputRfCber  OBJECT-TYPE
	SYNTAX     DisplayString
	MAX-ACCESS read-only
	STATUS     current
	DESCRIPTION 
		"CBER(DVB-S) / LDPCBER(DVB-S2)"
	::= { dvbs2AsiInputRfEntry 28 }

inputRfVber  OBJECT-TYPE
	SYNTAX     DisplayString
	MAX-ACCESS read-only
	STATUS     current
	DESCRIPTION 
		"VBER(DVB-S) / PER(DVB-S2)"
	::= { dvbs2AsiInputRfEntry 29 }

inputRfCn  OBJECT-TYPE
	SYNTAX     DisplayString
	UNITS 	"dB"
	MAX-ACCESS read-only
	STATUS     current
	DESCRIPTION 
		"CN"
	::= { dvbs2AsiInputRfEntry 30 }

inputRfLinkMargin  OBJECT-TYPE
	SYNTAX     DisplayString
	UNITS 	"dB"
	MAX-ACCESS read-only
	STATUS     current
	DESCRIPTION 
		"Link Margin"
	::= { dvbs2AsiInputRfEntry 31 }

inputRfPower  OBJECT-TYPE
	SYNTAX     DisplayString
	UNITS 	"dBm"
	MAX-ACCESS read-only
	STATUS     current
	DESCRIPTION 
		"Power"
	::= { dvbs2AsiInputRfEntry 32 }
dvbs2AsiOutputAsiTable  OBJECT-TYPE
	SYNTAX SEQUENCE OF Dvbs2AsiOutputAsiEntry
	MAX-ACCESS not-accessible
	STATUS     current
	DESCRIPTION 
		"Configure the ASI outputs"
	::= { dvbs2Asi 3 }

dvbs2AsiOutputAsiEntry  OBJECT-TYPE
	SYNTAX 	Dvbs2AsiOutputAsiEntry
	MAX-ACCESS not-accessible
	STATUS     current
	DESCRIPTION 
		"It would be 2 index: the dvbs2Asi module, and the 1...7 possible outputs"
	INDEX { outputAsiIndex, 
		outputAsiModuleIndex }
	::= { dvbs2AsiOutputAsiTable 1 }

Dvbs2AsiOutputAsiEntry ::= SEQUENCE {
	outputAsiModuleIndex
		Integer32,
	outputAsiCtrlAddress
		Integer32,
	outputAsiIndex
		Integer32,
	outputAsiState
		INTEGER,
	outputAsiRfInput
		INTEGER,
	outputAsiIsi
		Integer32,
	outputAsiMode
		INTEGER,
	outputAsiBitrate
		DisplayString
}

outputAsiModuleIndex  OBJECT-TYPE
	SYNTAX     Integer32 (1..255)
	MAX-ACCESS not-accessible
	STATUS     current
	DESCRIPTION 
		"Module index"
	::= { dvbs2AsiOutputAsiEntry 1 }

outputAsiCtrlAddress  OBJECT-TYPE
	SYNTAX     Integer32 (-1|1..255)
	MAX-ACCESS read-only
	STATUS     current
	DESCRIPTION 
		"Control Address"
	::= { dvbs2AsiOutputAsiEntry 2 }

outputAsiIndex  OBJECT-TYPE
	SYNTAX     Integer32 (1..7)
	MAX-ACCESS not-accessible
	STATUS     current
	DESCRIPTION 
		"ASI Output index (up to 7)"
	::= { dvbs2AsiOutputAsiEntry 3 }

outputAsiState  OBJECT-TYPE
	SYNTAX     INTEGER {
		asiEnabled (1),
		asiDisabled (2),
		asiDeactivated (3)
	}
	MAX-ACCESS read-write
	STATUS     current
	DESCRIPTION 
		"Enable/Disable this ASI output"
	::= { dvbs2AsiOutputAsiEntry 4 }

outputAsiRfInput  OBJECT-TYPE
	SYNTAX     INTEGER {
		inputRf1 (1),
		inputRf2 (2),
		inputRf3 (3),
		inputRf4 (4)
	}
	MAX-ACCESS read-write
	STATUS     current
	DESCRIPTION 
		"Selects RF Input source for this ASI output.
		If redundancy input is enabled, there will be an automatic switch between RF inputs 
		after hysteresis time"
	::= { dvbs2AsiOutputAsiEntry 5 }

outputAsiIsi  OBJECT-TYPE
	SYNTAX     Integer32 (0..255)
	MAX-ACCESS read-write
	STATUS     current
	DESCRIPTION 
		"Selects Input Stream Identifier for this ASI Input"
	::= { dvbs2AsiOutputAsiEntry 6 }

outputAsiMode  OBJECT-TYPE
	SYNTAX     INTEGER {
		modeByte (1),
		modePacket (2)
	}
	MAX-ACCESS read-write
	STATUS     current
	DESCRIPTION 
		"ASI output mode byte/packet"
	::= { dvbs2AsiOutputAsiEntry 7 }

outputAsiBitrate  OBJECT-TYPE
	SYNTAX     DisplayString
	MAX-ACCESS read-only
	STATUS     current
	DESCRIPTION 
		"When locked, it shows output bitrate"
	::= { dvbs2AsiOutputAsiEntry 8 }

dvbs2AsiControlTable  OBJECT-TYPE
	SYNTAX SEQUENCE OF Dvbs2AsiControlEntry
	MAX-ACCESS not-accessible
	STATUS     current
	DESCRIPTION 
		"Several DVB-S2 - ASI values and configurations"
	::= { dvbs2Asi 4 }

dvbs2AsiControlEntry  OBJECT-TYPE
	SYNTAX 	Dvbs2AsiControlEntry
	MAX-ACCESS not-accessible
	STATUS     current
	DESCRIPTION 
		"The index is the DVB-S2 ASI module"
	INDEX { dvbs2AsiControlIndex }
	::= { dvbs2AsiControlTable 1 }

Dvbs2AsiControlEntry ::= SEQUENCE {
	dvbs2AsiControlIndex
		Integer32,
	dvbs2AsiControlCtrlAddress
		Integer32,
	dvbs2AsiControlTemperature
		Integer32,
	dvbs2AsiControlSerialNumber
		Integer32,
	dvbs2AsiControlVersion
		Integer32,
	dvbs2AsiControlHysteresis
		Integer32
}

dvbs2AsiControlIndex  OBJECT-TYPE
	SYNTAX     Integer32 (1..255)
	MAX-ACCESS not-accessible
	STATUS     current
	DESCRIPTION 
		"Module index"
	::= { dvbs2AsiControlEntry 1 }

dvbs2AsiControlCtrlAddress  OBJECT-TYPE
	SYNTAX     Integer32 (-1|1..255)
	MAX-ACCESS read-only
	STATUS     current
	DESCRIPTION 
		"Control Address"
	::= { dvbs2AsiControlEntry 2 }

dvbs2AsiControlTemperature  OBJECT-TYPE
	SYNTAX     Integer32
	MAX-ACCESS read-only
	STATUS     current
	DESCRIPTION 
		"Temperature"
	::= { dvbs2AsiControlEntry 3 }

dvbs2AsiControlSerialNumber  OBJECT-TYPE
	SYNTAX     Integer32
	MAX-ACCESS read-only
	STATUS     current
	DESCRIPTION 
		"Serial Number"
	::= { dvbs2AsiControlEntry 4 }

dvbs2AsiControlVersion  OBJECT-TYPE
	SYNTAX     Integer32
	MAX-ACCESS read-only
	STATUS     current
	DESCRIPTION 
		"Module Firmware Version"
	::= { dvbs2AsiControlEntry 5 }

dvbs2AsiControlHysteresis  OBJECT-TYPE
	SYNTAX     Integer32
	MAX-ACCESS read-write
	STATUS     current
	DESCRIPTION 
		"When redundance on and an input fail, it takes this time for switching to other RF input"
	::= { dvbs2AsiControlEntry 6 }

dvbs2AsiAlarmsTable  OBJECT-TYPE
	SYNTAX SEQUENCE OF Dvbs2AsiAlarmsEntry
	MAX-ACCESS not-accessible
	STATUS     current
	DESCRIPTION 
		"DVB-S2 / ASI alarm table"
	::= { dvbs2Asi 5 }

dvbs2AsiAlarmsEntry  OBJECT-TYPE
	SYNTAX 	Dvbs2AsiAlarmsEntry
	MAX-ACCESS not-accessible
	STATUS     current
	DESCRIPTION 
		"The index is the DVB-S2 ASI module"
	INDEX { dvbs2AsiAlarmsIndex }
	::= { dvbs2AsiAlarmsTable 1 }

Dvbs2AsiAlarmsEntry ::= SEQUENCE {
	dvbs2AsiAlarmsIndex
		Integer32,
	dvbs2AsiAlarmsCtrlAddress
		Integer32,
	dvbs2AsiAlarmsFault
		TruthValue,
	dvbs2AsiAlarmsMinor
		TruthValue,
	dvbs2AsiAlarmsInputUnlock1
		INTEGER,
	dvbs2AsiAlarmsInputUnlock2
		INTEGER,
	dvbs2AsiAlarmsInputUnlock3
		INTEGER,
	dvbs2AsiAlarmsInputUnlock4
		INTEGER,
	dvbs2AsiAlarmsLnb1
		INTEGER,
	dvbs2AsiAlarmsLnb2
		INTEGER,
	dvbs2AsiAlarmsLnb3
		INTEGER,
	dvbs2AsiAlarmsLnb4
		INTEGER,
	dvbs2AsiAlarmsInputQuality1
		INTEGER,
	dvbs2AsiAlarmsInputQuality2
		INTEGER,
	dvbs2AsiAlarmsInputQuality3
		INTEGER,
	dvbs2AsiAlarmsInputQuality4
		INTEGER,
	dvbs2AsiAlarmsOutputAsi1
		INTEGER,
	dvbs2AsiAlarmsOutputAsi2
		INTEGER,
	dvbs2AsiAlarmsOutputAsi3
		INTEGER,
	dvbs2AsiAlarmsOutputAsi4
		INTEGER,
	dvbs2AsiAlarmsOutputAsi5
		INTEGER,
	dvbs2AsiAlarmsOutputAsi6
		INTEGER,
	dvbs2AsiAlarmsOutputAsi7
		INTEGER,
	dvbs2AsiAlarmsTemperature
		TruthValue,
	dvbs2AsiAlarmsHw
		TruthValue
}

dvbs2AsiAlarmsIndex  OBJECT-TYPE
	SYNTAX     Integer32 (1..255)
	MAX-ACCESS not-accessible
	STATUS     current
	DESCRIPTION 
		"Module index"
	::= { dvbs2AsiAlarmsEntry 1 }

dvbs2AsiAlarmsCtrlAddress  OBJECT-TYPE
	SYNTAX     Integer32 (1..255)
	MAX-ACCESS read-only
	STATUS     current
	DESCRIPTION 
		"Control Address"
	::= { dvbs2AsiAlarmsEntry 2 }

dvbs2AsiAlarmsFault  OBJECT-TYPE
	SYNTAX     TruthValue
	MAX-ACCESS read-only
	STATUS     current
	DESCRIPTION 
		"Fault (summation) alarm"
	::= { dvbs2AsiAlarmsEntry 3 }

dvbs2AsiAlarmsMinor  OBJECT-TYPE
	SYNTAX     TruthValue
	MAX-ACCESS read-only
	STATUS     current
	DESCRIPTION 
		"Minor(summation) alarm"
	::= { dvbs2AsiAlarmsEntry 4 }

dvbs2AsiAlarmsInputUnlock1  OBJECT-TYPE
	SYNTAX     INTEGER {
		true (1),
		false (2),
		deactived (3)
	}
	MAX-ACCESS read-only
	STATUS     current
	DESCRIPTION 
		"Input 1 unlocked"
	::= { dvbs2AsiAlarmsEntry 5 }

dvbs2AsiAlarmsInputUnlock2  OBJECT-TYPE
	SYNTAX     INTEGER {
		true (1),
		false (2),
		deactived (3)
	}
	MAX-ACCESS read-only
	STATUS     current
	DESCRIPTION 
		"Input 2 unlocked"
	::= { dvbs2AsiAlarmsEntry 6 }

dvbs2AsiAlarmsInputUnlock3  OBJECT-TYPE
	SYNTAX     INTEGER {
		true (1),
		false (2),
		deactived (3)
	}
	MAX-ACCESS read-only
	STATUS     current
	DESCRIPTION 
		"Input 3 unlocked"
	::= { dvbs2AsiAlarmsEntry 7 }

dvbs2AsiAlarmsInputUnlock4  OBJECT-TYPE
	SYNTAX     INTEGER {
		true (1),
		false (2),
		deactived (3)
	}
	MAX-ACCESS read-only
	STATUS     current
	DESCRIPTION 
		"Input 4 unlocked"
	::= { dvbs2AsiAlarmsEntry 8 }

dvbs2AsiAlarmsLnb1  OBJECT-TYPE
	SYNTAX     INTEGER {
		true (1),
		false (2),
		deactived (3)
	}
	MAX-ACCESS read-only
	STATUS     current
	DESCRIPTION 
		"Short circuit in LNB 1"
	::= { dvbs2AsiAlarmsEntry 9 }

dvbs2AsiAlarmsLnb2  OBJECT-TYPE
	SYNTAX     INTEGER {
		true (1),
		false (2),
		deactived (3)
	}
	MAX-ACCESS read-only
	STATUS     current
	DESCRIPTION 
		"Short circuit in LNB 2"
	::= { dvbs2AsiAlarmsEntry 10 }

dvbs2AsiAlarmsLnb3  OBJECT-TYPE
	SYNTAX     INTEGER {
		true (1),
		false (2),
		deactived (3)
	}
	MAX-ACCESS read-only
	STATUS     current
	DESCRIPTION 
		"Short circuit in LNB 3"
	::= { dvbs2AsiAlarmsEntry 11 }

dvbs2AsiAlarmsLnb4  OBJECT-TYPE
	SYNTAX     INTEGER {
		true (1),
		false (2),
		deactived (3)
	}
	MAX-ACCESS read-only
	STATUS     current
	DESCRIPTION 
		"Short circuit in LNB 4"
	::= { dvbs2AsiAlarmsEntry 12 }

dvbs2AsiAlarmsInputQuality1  OBJECT-TYPE
	SYNTAX     INTEGER {
		true (1),
		false (2),
		deactived (3)
	}
	MAX-ACCESS read-only
	STATUS     current
	DESCRIPTION 
		"Input low quality 1"
	::= { dvbs2AsiAlarmsEntry 13 }

dvbs2AsiAlarmsInputQuality2  OBJECT-TYPE
	SYNTAX     INTEGER {
		true (1),
		false (2),
		deactived (3)
	}
	MAX-ACCESS read-only
	STATUS     current
	DESCRIPTION 
		"Input low quality 2"
	::= { dvbs2AsiAlarmsEntry 14 }

dvbs2AsiAlarmsInputQuality3  OBJECT-TYPE
	SYNTAX     INTEGER {
		true (1),
		false (2),
		deactived (3)
	}
	MAX-ACCESS read-only
	STATUS     current
	DESCRIPTION 
		"Input low quality 3"
	::= { dvbs2AsiAlarmsEntry 15 }

dvbs2AsiAlarmsInputQuality4  OBJECT-TYPE
	SYNTAX     INTEGER {
		true (1),
		false (2),
		deactived (3)
	}
	MAX-ACCESS read-only
	STATUS     current
	DESCRIPTION 
		"Input low quality 4"
	::= { dvbs2AsiAlarmsEntry 16 }

dvbs2AsiAlarmsOutputAsi1  OBJECT-TYPE
	SYNTAX     INTEGER {
		true (1),
		false (2),
		deactived (3)
	}
	MAX-ACCESS read-only
	STATUS     current
	DESCRIPTION 
		"ASI 1 output alarm"
	::= { dvbs2AsiAlarmsEntry 17 }

dvbs2AsiAlarmsOutputAsi2  OBJECT-TYPE
	SYNTAX     INTEGER {
		true (1),
		false (2),
		deactived (3)
	}
	MAX-ACCESS read-only
	STATUS     current
	DESCRIPTION 
		"ASI 2 output alarm"
	::= { dvbs2AsiAlarmsEntry 18 }

dvbs2AsiAlarmsOutputAsi3  OBJECT-TYPE
	SYNTAX     INTEGER {
		true (1),
		false (2),
		deactived (3)
	}
	MAX-ACCESS read-only
	STATUS     current
	DESCRIPTION 
		"ASI 3 output alarm"
	::= { dvbs2AsiAlarmsEntry 19 }

dvbs2AsiAlarmsOutputAsi4  OBJECT-TYPE
	SYNTAX     INTEGER {
		true (1),
		false (2),
		deactived (3)
	}
	MAX-ACCESS read-only
	STATUS     current
	DESCRIPTION 
		"ASI 4 output alarm"
	::= { dvbs2AsiAlarmsEntry 20 }

dvbs2AsiAlarmsOutputAsi5  OBJECT-TYPE
	SYNTAX     INTEGER {
		true (1),
		false (2),
		deactived (3)
	}
	MAX-ACCESS read-only
	STATUS     current
	DESCRIPTION 
		"ASI 5 output alarm"
	::= { dvbs2AsiAlarmsEntry 21 }

dvbs2AsiAlarmsOutputAsi6  OBJECT-TYPE
	SYNTAX     INTEGER {
		true (1),
		false (2),
		deactived (3)
	}
	MAX-ACCESS read-only
	STATUS     current
	DESCRIPTION 
		"ASI 6 output alarm"
	::= { dvbs2AsiAlarmsEntry 22 }

dvbs2AsiAlarmsOutputAsi7  OBJECT-TYPE
	SYNTAX     INTEGER {
		true (1),
		false (2),
		deactived (3)
	}
	MAX-ACCESS read-only
	STATUS     current
	DESCRIPTION 
		"ASI 7 output alarm"
	::= { dvbs2AsiAlarmsEntry 23 }

dvbs2AsiAlarmsTemperature  OBJECT-TYPE
	SYNTAX     TruthValue
	MAX-ACCESS read-only
	STATUS     current
	DESCRIPTION 
		"Hardware module alarm"
	::= { dvbs2AsiAlarmsEntry 24 }

dvbs2AsiAlarmsHw  OBJECT-TYPE
	SYNTAX     TruthValue
	MAX-ACCESS read-only
	STATUS     current
	DESCRIPTION 
		"Hardware module alarm"
	::= { dvbs2AsiAlarmsEntry 25 }

dvbs2AsiEnableAlarmsTable  OBJECT-TYPE
	SYNTAX SEQUENCE OF Dvbs2AsiEnableAlarmsEntry
	MAX-ACCESS not-accessible
	STATUS     current
	DESCRIPTION 
		"DVB-S2 / ASI enable alarm table"
	::= { dvbs2Asi 6 }

dvbs2AsiEnableAlarmsEntry  OBJECT-TYPE
	SYNTAX 	Dvbs2AsiEnableAlarmsEntry
	MAX-ACCESS not-accessible
	STATUS     current
	DESCRIPTION 
		"The index is the DVB-S2 ASI module"
	INDEX { dvbs2AsiEnableAlarmsIndex }
	::= { dvbs2AsiEnableAlarmsTable 1 }

Dvbs2AsiEnableAlarmsEntry ::= SEQUENCE {
	dvbs2AsiEnableAlarmsIndex
		Integer32,
	dvbs2AsiEnableAlarmsCtrlAddress
		Integer32,
	dvbs2AsiEnableAlarmsFault
		TruthValue,
	dvbs2AsiEnableAlarmsMinor
		TruthValue,
	dvbs2AsiEnableAlarmsInputUnlock1
		TruthValue,
	dvbs2AsiEnableAlarmsInputUnlock2
		TruthValue,
	dvbs2AsiEnableAlarmsInputUnlock3
		TruthValue,
	dvbs2AsiEnableAlarmsInputUnlock4
		TruthValue,
	dvbs2AsiEnableAlarmsLnb1
		TruthValue,
	dvbs2AsiEnableAlarmsLnb2
		TruthValue,
	dvbs2AsiEnableAlarmsLnb3
		TruthValue,
	dvbs2AsiEnableAlarmsLnb4
		TruthValue,
	dvbs2AsiEnableAlarmsInputQualit1
		TruthValue,
	dvbs2AsiEnableAlarmsInputQualit2
		TruthValue,
	dvbs2AsiEnableAlarmsInputQualit3
		TruthValue,
	dvbs2AsiEnableAlarmsInputQualit4
		TruthValue,
	dvbs2AsiEnableAlarmsOutputAsi1
		TruthValue,
	dvbs2AsiEnableAlarmsOutputAsi2
		TruthValue,
	dvbs2AsiEnableAlarmsOutputAsi3
		TruthValue,
	dvbs2AsiEnableAlarmsOutputAsi4
		TruthValue,
	dvbs2AsiEnableAlarmsOutputAsi5
		TruthValue,
	dvbs2AsiEnableAlarmsOutputAsi6
		TruthValue,
	dvbs2AsiEnableAlarmsOutputAsi7
		TruthValue,
	dvbs2AsiEnableAlarmsTemperature
		TruthValue,
	dvbs2AsiEnableAlarmsHw
		TruthValue
}

dvbs2AsiEnableAlarmsIndex  OBJECT-TYPE
	SYNTAX     Integer32 (1..255)
	MAX-ACCESS not-accessible
	STATUS     current
	DESCRIPTION 
		"Module index"
	::= { dvbs2AsiEnableAlarmsEntry 1 }

dvbs2AsiEnableAlarmsCtrlAddress  OBJECT-TYPE
	SYNTAX     Integer32 (1..255)
	MAX-ACCESS read-only
	STATUS     current
	DESCRIPTION 
		"Control Address"
	::= { dvbs2AsiEnableAlarmsEntry 2 }

dvbs2AsiEnableAlarmsFault  OBJECT-TYPE
	SYNTAX     TruthValue
	MAX-ACCESS read-write
	STATUS     current
	DESCRIPTION 
		"Fault (summation) alarm enable/disable"
	::= { dvbs2AsiEnableAlarmsEntry 3 }

dvbs2AsiEnableAlarmsMinor  OBJECT-TYPE
	SYNTAX     TruthValue
	MAX-ACCESS read-write
	STATUS     current
	DESCRIPTION 
		"Minor(summation) alarm enable/disable"
	::= { dvbs2AsiEnableAlarmsEntry 4 }

dvbs2AsiEnableAlarmsInputUnlock1  OBJECT-TYPE
	SYNTAX     TruthValue
	MAX-ACCESS read-write
	STATUS     current
	DESCRIPTION 
		"Input 1 unlocked alarm enable/disable"
	::= { dvbs2AsiEnableAlarmsEntry 5 }

dvbs2AsiEnableAlarmsInputUnlock2  OBJECT-TYPE
	SYNTAX     TruthValue
	MAX-ACCESS read-write
	STATUS     current
	DESCRIPTION 
		"Input 2 unlocked alarm enable/disable"
	::= { dvbs2AsiEnableAlarmsEntry 6 }

dvbs2AsiEnableAlarmsInputUnlock3  OBJECT-TYPE
	SYNTAX     TruthValue
	MAX-ACCESS read-write
	STATUS     current
	DESCRIPTION 
		"Input 3 unlocked alarm enable/disable"
	::= { dvbs2AsiEnableAlarmsEntry 7 }

dvbs2AsiEnableAlarmsInputUnlock4  OBJECT-TYPE
	SYNTAX     TruthValue
	MAX-ACCESS read-write
	STATUS     current
	DESCRIPTION 
		"Input 4 unlocked alarm enable/disable"
	::= { dvbs2AsiEnableAlarmsEntry 8 }

dvbs2AsiEnableAlarmsLnb1  OBJECT-TYPE
	SYNTAX     TruthValue
	MAX-ACCESS read-write
	STATUS     current
	DESCRIPTION 
		"Short circuit in LNB 1 alarm enable/disable"
	::= { dvbs2AsiEnableAlarmsEntry 9 }

dvbs2AsiEnableAlarmsLnb2  OBJECT-TYPE
	SYNTAX     TruthValue
	MAX-ACCESS read-write
	STATUS     current
	DESCRIPTION 
		"Short circuit in LNB 2 alarm enable/disable"
	::= { dvbs2AsiEnableAlarmsEntry 10 }

dvbs2AsiEnableAlarmsLnb3  OBJECT-TYPE
	SYNTAX     TruthValue
	MAX-ACCESS read-write
	STATUS     current
	DESCRIPTION 
		"Short circuit in LNB 3 alarm enable/disable"
	::= { dvbs2AsiEnableAlarmsEntry 11 }

dvbs2AsiEnableAlarmsLnb4  OBJECT-TYPE
	SYNTAX     TruthValue
	MAX-ACCESS read-write
	STATUS     current
	DESCRIPTION 
		"Short circuit in LNB 4 alarm enable/disable"
	::= { dvbs2AsiEnableAlarmsEntry 12 }

dvbs2AsiEnableAlarmsInputQualit1  OBJECT-TYPE
	SYNTAX     TruthValue
	MAX-ACCESS read-write
	STATUS     current
	DESCRIPTION 
		"Input low quality 1 alarm enable/disable"
	::= { dvbs2AsiEnableAlarmsEntry 13 }

dvbs2AsiEnableAlarmsInputQualit2  OBJECT-TYPE
	SYNTAX     TruthValue
	MAX-ACCESS read-write
	STATUS     current
	DESCRIPTION 
		"Input low quality 2 alarm enable/disable"
	::= { dvbs2AsiEnableAlarmsEntry 14 }

dvbs2AsiEnableAlarmsInputQualit3  OBJECT-TYPE
	SYNTAX     TruthValue
	MAX-ACCESS read-write
	STATUS     current
	DESCRIPTION 
		"Input low quality 3 alarm enable/disable"
	::= { dvbs2AsiEnableAlarmsEntry 15 }

dvbs2AsiEnableAlarmsInputQualit4  OBJECT-TYPE
	SYNTAX     TruthValue
	MAX-ACCESS read-write
	STATUS     current
	DESCRIPTION 
		"Input low quality 4 alarm enable/disable"
	::= { dvbs2AsiEnableAlarmsEntry 16 }

dvbs2AsiEnableAlarmsOutputAsi1  OBJECT-TYPE
	SYNTAX     TruthValue
	MAX-ACCESS read-write
	STATUS     current
	DESCRIPTION 
		"ASI 1 output alarm enable/disable"
	::= { dvbs2AsiEnableAlarmsEntry 17 }

dvbs2AsiEnableAlarmsOutputAsi2  OBJECT-TYPE
	SYNTAX     TruthValue
	MAX-ACCESS read-write
	STATUS     current
	DESCRIPTION 
		"ASI 2 output alarm enable/disable"
	::= { dvbs2AsiEnableAlarmsEntry 18 }

dvbs2AsiEnableAlarmsOutputAsi3  OBJECT-TYPE
	SYNTAX     TruthValue
	MAX-ACCESS read-write
	STATUS     current
	DESCRIPTION 
		"ASI 3 output alarm enable/disable"
	::= { dvbs2AsiEnableAlarmsEntry 19 }

dvbs2AsiEnableAlarmsOutputAsi4  OBJECT-TYPE
	SYNTAX     TruthValue
	MAX-ACCESS read-write
	STATUS     current
	DESCRIPTION 
		"ASI 4 output alarm enable/disable"
	::= { dvbs2AsiEnableAlarmsEntry 20 }

dvbs2AsiEnableAlarmsOutputAsi5  OBJECT-TYPE
	SYNTAX     TruthValue
	MAX-ACCESS read-write
	STATUS     current
	DESCRIPTION 
		"ASI 5 output alarm enable/disable"
	::= { dvbs2AsiEnableAlarmsEntry 21 }

dvbs2AsiEnableAlarmsOutputAsi6  OBJECT-TYPE
	SYNTAX     TruthValue
	MAX-ACCESS read-write
	STATUS     current
	DESCRIPTION 
		"ASI 6 output alarm enable/disable"
	::= { dvbs2AsiEnableAlarmsEntry 22 }

dvbs2AsiEnableAlarmsOutputAsi7  OBJECT-TYPE
	SYNTAX     TruthValue
	MAX-ACCESS read-write
	STATUS     current
	DESCRIPTION 
		"ASI 7 output alarm enable/disable"
	::= { dvbs2AsiEnableAlarmsEntry 23 }

dvbs2AsiEnableAlarmsTemperature  OBJECT-TYPE
	SYNTAX     TruthValue
	MAX-ACCESS read-write
	STATUS     current
	DESCRIPTION 
		"Hardware module alarm enable/disable"
	::= { dvbs2AsiEnableAlarmsEntry 24 }

dvbs2AsiEnableAlarmsHw  OBJECT-TYPE
	SYNTAX     TruthValue
	MAX-ACCESS read-write
	STATUS     current
	DESCRIPTION 
		"Hardware module alarm enable/disable"
	::= { dvbs2AsiEnableAlarmsEntry 25 }

dvbs2AsiEnableTrapTable  OBJECT-TYPE
	SYNTAX SEQUENCE OF Dvbs2AsiEnableTrapEntry
	MAX-ACCESS not-accessible
	STATUS     current
	DESCRIPTION 
		"DVB-S2 / ASI trap enable/disable table"
	::= { dvbs2Asi 7 }

dvbs2AsiEnableTrapEntry  OBJECT-TYPE
	SYNTAX 	Dvbs2AsiEnableTrapEntry
	MAX-ACCESS not-accessible
	STATUS     current
	DESCRIPTION 
		"The index is the DVB-S2 ASI module"
	INDEX { dvbs2AsiEnableTrapIndex }
	::= { dvbs2AsiEnableTrapTable 1 }

Dvbs2AsiEnableTrapEntry ::= SEQUENCE {
	dvbs2AsiEnableTrapIndex
		Integer32,
	dvbs2AsiEnableTrapCtrlAddress
		Integer32,
	dvbs2AsiEnableTrapFault
		TruthValue,
	dvbs2AsiEnableTrapMinor
		TruthValue,
	dvbs2AsiEnableTrapInputUnlock1
		TruthValue,
	dvbs2AsiEnableTrapInputUnlock2
		TruthValue,
	dvbs2AsiEnableTrapInputUnlock3
		TruthValue,
	dvbs2AsiEnableTrapInputUnlock4
		TruthValue,
	dvbs2AsiEnableTrapLnb1
		TruthValue,
	dvbs2AsiEnableTrapLnb2
		TruthValue,
	dvbs2AsiEnableTrapLnb3
		TruthValue,
	dvbs2AsiEnableTrapLnb4
		TruthValue,
	dvbs2AsiEnableTrapInputQuality1
		TruthValue,
	dvbs2AsiEnableTrapInputQuality2
		TruthValue,
	dvbs2AsiEnableTrapInputQuality3
		TruthValue,
	dvbs2AsiEnableTrapInputQuality4
		TruthValue,
	dvbs2AsiEnableTrapOutputAsi1
		TruthValue,
	dvbs2AsiEnableTrapOutputAsi2
		TruthValue,
	dvbs2AsiEnableTrapOutputAsi3
		TruthValue,
	dvbs2AsiEnableTrapOutputAsi4
		TruthValue,
	dvbs2AsiEnableTrapOutputAsi5
		TruthValue,
	dvbs2AsiEnableTrapOutputAsi6
		TruthValue,
	dvbs2AsiEnableTrapOutputAsi7
		TruthValue,
	dvbs2AsiEnableTrapTemperature
		TruthValue,
	dvbs2AsiEnableTrapHw
		TruthValue
}

dvbs2AsiEnableTrapIndex  OBJECT-TYPE
	SYNTAX     Integer32 (1..255)
	MAX-ACCESS not-accessible
	STATUS     current
	DESCRIPTION 
		"Module index"
	::= { dvbs2AsiEnableTrapEntry 1 }

dvbs2AsiEnableTrapCtrlAddress  OBJECT-TYPE
	SYNTAX     Integer32 (1..255)
	MAX-ACCESS read-only
	STATUS     current
	DESCRIPTION 
		"Control Address"
	::= { dvbs2AsiEnableTrapEntry 2 }

dvbs2AsiEnableTrapFault  OBJECT-TYPE
	SYNTAX     TruthValue
	MAX-ACCESS read-write
	STATUS     current
	DESCRIPTION 
		"Fault (summation) trap enable/disable"
	::= { dvbs2AsiEnableTrapEntry 3 }

dvbs2AsiEnableTrapMinor  OBJECT-TYPE
	SYNTAX     TruthValue
	MAX-ACCESS read-write
	STATUS     current
	DESCRIPTION 
		"Minor(summation) trap enable/disable"
	::= { dvbs2AsiEnableTrapEntry 4 }

dvbs2AsiEnableTrapInputUnlock1  OBJECT-TYPE
	SYNTAX     TruthValue
	MAX-ACCESS read-write
	STATUS     current
	DESCRIPTION 
		"Input 1 unlocked trap enable/disable"
	::= { dvbs2AsiEnableTrapEntry 5 }

dvbs2AsiEnableTrapInputUnlock2  OBJECT-TYPE
	SYNTAX     TruthValue
	MAX-ACCESS read-write
	STATUS     current
	DESCRIPTION 
		"Input 2 unlocked trap enable/disable"
	::= { dvbs2AsiEnableTrapEntry 6 }

dvbs2AsiEnableTrapInputUnlock3  OBJECT-TYPE
	SYNTAX     TruthValue
	MAX-ACCESS read-write
	STATUS     current
	DESCRIPTION 
		"Input 3 unlocked trap enable/disable"
	::= { dvbs2AsiEnableTrapEntry 7 }

dvbs2AsiEnableTrapInputUnlock4  OBJECT-TYPE
	SYNTAX     TruthValue
	MAX-ACCESS read-write
	STATUS     current
	DESCRIPTION 
		"Input 4 unlocked trap enable/disable"
	::= { dvbs2AsiEnableTrapEntry 8 }

dvbs2AsiEnableTrapLnb1  OBJECT-TYPE
	SYNTAX     TruthValue
	MAX-ACCESS read-write
	STATUS     current
	DESCRIPTION 
		"Short circuit in LNB 1 trap enable/disable"
	::= { dvbs2AsiEnableTrapEntry 9 }

dvbs2AsiEnableTrapLnb2  OBJECT-TYPE
	SYNTAX     TruthValue
	MAX-ACCESS read-write
	STATUS     current
	DESCRIPTION 
		"Short circuit in LNB 2 trap enable/disable"
	::= { dvbs2AsiEnableTrapEntry 10 }

dvbs2AsiEnableTrapLnb3  OBJECT-TYPE
	SYNTAX     TruthValue
	MAX-ACCESS read-write
	STATUS     current
	DESCRIPTION 
		"Short circuit in LNB 3 trap enable/disable"
	::= { dvbs2AsiEnableTrapEntry 11 }

dvbs2AsiEnableTrapLnb4  OBJECT-TYPE
	SYNTAX     TruthValue
	MAX-ACCESS read-write
	STATUS     current
	DESCRIPTION 
		"Short circuit in LNB 4 trap enable/disable"
	::= { dvbs2AsiEnableTrapEntry 12 }

dvbs2AsiEnableTrapInputQuality1  OBJECT-TYPE
	SYNTAX     TruthValue
	MAX-ACCESS read-write
	STATUS     current
	DESCRIPTION 
		"Input low quality 1 trap enable/disable"
	::= { dvbs2AsiEnableTrapEntry 13 }

dvbs2AsiEnableTrapInputQuality2  OBJECT-TYPE
	SYNTAX     TruthValue
	MAX-ACCESS read-write
	STATUS     current
	DESCRIPTION 
		"Input low quality 2 trap enable/disable"
	::= { dvbs2AsiEnableTrapEntry 14 }

dvbs2AsiEnableTrapInputQuality3  OBJECT-TYPE
	SYNTAX     TruthValue
	MAX-ACCESS read-write
	STATUS     current
	DESCRIPTION 
		"Input low quality 3 trap enable/disable"
	::= { dvbs2AsiEnableTrapEntry 15 }

dvbs2AsiEnableTrapInputQuality4  OBJECT-TYPE
	SYNTAX     TruthValue
	MAX-ACCESS read-write
	STATUS     current
	DESCRIPTION 
		"Input low quality 4 trap enable/disable"
	::= { dvbs2AsiEnableTrapEntry 16 }

dvbs2AsiEnableTrapOutputAsi1  OBJECT-TYPE
	SYNTAX     TruthValue
	MAX-ACCESS read-write
	STATUS     current
	DESCRIPTION 
		"ASI 1 output trap enable/disable"
	::= { dvbs2AsiEnableTrapEntry 17 }

dvbs2AsiEnableTrapOutputAsi2  OBJECT-TYPE
	SYNTAX     TruthValue
	MAX-ACCESS read-write
	STATUS     current
	DESCRIPTION 
		"ASI 2 output trap enable/disable"
	::= { dvbs2AsiEnableTrapEntry 18 }

dvbs2AsiEnableTrapOutputAsi3  OBJECT-TYPE
	SYNTAX     TruthValue
	MAX-ACCESS read-write
	STATUS     current
	DESCRIPTION 
		"ASI 3 output trap enable/disable"
	::= { dvbs2AsiEnableTrapEntry 19 }

dvbs2AsiEnableTrapOutputAsi4  OBJECT-TYPE
	SYNTAX     TruthValue
	MAX-ACCESS read-write
	STATUS     current
	DESCRIPTION 
		"ASI 4 output trap enable/disable"
	::= { dvbs2AsiEnableTrapEntry 20 }

dvbs2AsiEnableTrapOutputAsi5  OBJECT-TYPE
	SYNTAX     TruthValue
	MAX-ACCESS read-write
	STATUS     current
	DESCRIPTION 
		"ASI 5 output trap enable/disable"
	::= { dvbs2AsiEnableTrapEntry 21 }

dvbs2AsiEnableTrapOutputAsi6  OBJECT-TYPE
	SYNTAX     TruthValue
	MAX-ACCESS read-write
	STATUS     current
	DESCRIPTION 
		"ASI 6 output trap enable/disable"
	::= { dvbs2AsiEnableTrapEntry 22 }

dvbs2AsiEnableTrapOutputAsi7  OBJECT-TYPE
	SYNTAX     TruthValue
	MAX-ACCESS read-write
	STATUS     current
	DESCRIPTION 
		"ASI 7 output trap enable/disable"
	::= { dvbs2AsiEnableTrapEntry 23 }

dvbs2AsiEnableTrapTemperature  OBJECT-TYPE
	SYNTAX     TruthValue
	MAX-ACCESS read-write
	STATUS     current
	DESCRIPTION 
		"Hardware module trap enable/disable"
	::= { dvbs2AsiEnableTrapEntry 24 }

dvbs2AsiEnableTrapHw  OBJECT-TYPE
	SYNTAX     TruthValue
	MAX-ACCESS read-write
	STATUS     current
	DESCRIPTION 
		"Hardware module trap enable/disable"
	::= { dvbs2AsiEnableTrapEntry 25 }

ip2AsiGeralTable  OBJECT-TYPE
	SYNTAX SEQUENCE OF Ip2AsiGeralEntry
	MAX-ACCESS not-accessible
	STATUS     current
	DESCRIPTION 
		"IP/ASI geral values table"
	::= { ip2Asi 1 }

ip2AsiGeralEntry  OBJECT-TYPE
	SYNTAX 	Ip2AsiGeralEntry
	MAX-ACCESS not-accessible
	STATUS     current
	DESCRIPTION 
		"IP/ASI geral values entry"
	INDEX { ip2AsiIndex }
	::= { ip2AsiGeralTable 1 }

Ip2AsiGeralEntry ::= SEQUENCE {
	ip2AsiIndex
		Integer32,
	ip2AsiGeralAddress
		Integer32,
	ip2AsiGeralDhcp
		TruthValue,
	ip2AsiGeralIp
		IpAddress,
	ip2AsiGeralNetmask
		IpAddress,
	ip2AsiGeralGateway
		IpAddress,
	ip2AsiGeralVlan
		TruthValue,
	ip2AsiGeralVlanId
		Integer32,
	ip2AsiGeralIgmpV
		INTEGER,
	ip2AsiGeralInput1State
		DisplayString,
	ip2AsiGeralInput2State
		DisplayString,
	ip2AsiGeralMAC
		MacAddress,
	ip2AsiGeralTemperature
		DisplayString,
	ip2AsiGeralVersion
		DisplayString,
	ip2AsiGeralSerialNumber
		DisplayString
}

ip2AsiIndex  OBJECT-TYPE
	SYNTAX     Integer32 (1..10)
	MAX-ACCESS not-accessible
	STATUS     current
	DESCRIPTION 
		"Module index"
	::= { ip2AsiGeralEntry 1 }

ip2AsiGeralAddress  OBJECT-TYPE
	SYNTAX     Integer32 (61..70)
	MAX-ACCESS read-only
	STATUS     current
	DESCRIPTION 
		"IP/ASI Control Addres"
	::= { ip2AsiGeralEntry 2 }

ip2AsiGeralDhcp  OBJECT-TYPE
	SYNTAX     TruthValue
	MAX-ACCESS read-write
	STATUS     current
	DESCRIPTION 
		"Enable/disble DHCP"
	::= { ip2AsiGeralEntry 3 }

ip2AsiGeralIp  OBJECT-TYPE
	SYNTAX     IpAddress
	MAX-ACCESS read-write
	STATUS     current
	DESCRIPTION 
		"Host IP"
	::= { ip2AsiGeralEntry 4 }

ip2AsiGeralNetmask  OBJECT-TYPE
	SYNTAX     IpAddress
	MAX-ACCESS read-write
	STATUS     current
	DESCRIPTION 
		"Netmask IP"
	::= { ip2AsiGeralEntry 5 }

ip2AsiGeralGateway  OBJECT-TYPE
	SYNTAX     IpAddress
	MAX-ACCESS read-write
	STATUS     current
	DESCRIPTION 
		"Gatewary IP"
	::= { ip2AsiGeralEntry 6 }

ip2AsiGeralVlan  OBJECT-TYPE
	SYNTAX     TruthValue
	MAX-ACCESS read-write
	STATUS     current
	DESCRIPTION 
		"Vlan enable/disable"
	::= { ip2AsiGeralEntry 7 }

ip2AsiGeralVlanId  OBJECT-TYPE
	SYNTAX     Integer32 (1..4094)
	MAX-ACCESS read-write
	STATUS     current
	DESCRIPTION 
		"VLAN ID (apply if enabled)"
	::= { ip2AsiGeralEntry 8 }

ip2AsiGeralIgmpV  OBJECT-TYPE
	SYNTAX     INTEGER {
		igmpV2 (1),
		igmpV3 (2)
	}
	MAX-ACCESS read-write
	STATUS     current
	DESCRIPTION 
		"IGMP Version 2/3"
	::= { ip2AsiGeralEntry 9 }

ip2AsiGeralInput1State  OBJECT-TYPE
	SYNTAX     DisplayString
	MAX-ACCESS read-only
	STATUS     current
	DESCRIPTION 
		"Input 1 state (mbps)"
	::= { ip2AsiGeralEntry 10 }

ip2AsiGeralInput2State  OBJECT-TYPE
	SYNTAX     DisplayString
	MAX-ACCESS read-only
	STATUS     current
	DESCRIPTION 
		"Input 2 state (mbps)"
	::= { ip2AsiGeralEntry 11 }

ip2AsiGeralMAC  OBJECT-TYPE
	SYNTAX     MacAddress
	MAX-ACCESS read-only
	STATUS     current
	DESCRIPTION 
		"IP/ASI MAC address"
	::= { ip2AsiGeralEntry 12 }

ip2AsiGeralTemperature  OBJECT-TYPE
	SYNTAX     DisplayString
	MAX-ACCESS read-only
	STATUS     current
	DESCRIPTION 
		"IP/ASI Temperature"
	::= { ip2AsiGeralEntry 13 }

ip2AsiGeralVersion  OBJECT-TYPE
	SYNTAX     DisplayString
	MAX-ACCESS read-only
	STATUS     current
	DESCRIPTION 
		"IP/ASI Firmware version"
	::= { ip2AsiGeralEntry 14 }

ip2AsiGeralSerialNumber  OBJECT-TYPE
	SYNTAX     DisplayString
	MAX-ACCESS read-only
	STATUS     current
	DESCRIPTION 
		"IP/ASI Serial Number"
	::= { ip2AsiGeralEntry 15 }

ip2AsiIOTable  OBJECT-TYPE
	SYNTAX SEQUENCE OF Ip2AsiIOEntry
	MAX-ACCESS not-accessible
	STATUS     current
	DESCRIPTION 
		"IP/ASI Input-Output table"
	::= { ip2Asi 2 }

ip2AsiIOEntry  OBJECT-TYPE
	SYNTAX 	Ip2AsiIOEntry
	MAX-ACCESS not-accessible
	STATUS     current
	DESCRIPTION 
		"IP/ASI Input-Output entry"
	INDEX { ip2AsiIOAddressIndex, 
		ip2AsiIOInOutIndex }
	::= { ip2AsiIOTable 1 }

Ip2AsiIOEntry ::= SEQUENCE {
	ip2AsiIOInOutIndex
		Integer32,
	ip2AsiIOInOut
		Integer32,
	ip2AsiIOAddressIndex
		Integer32,
	ip2AsiIOAddress
		Integer32,
	ip2AsiInput
		TruthValue,
	ip2AsiMulticast
		TruthValue,
	ip2AsiIpMulticast
		IpAddress,
	ip2AsiIpSrc
		IpAddress,
	ip2AsiInputPort
		Integer32,
	ip2AsiInputLatency
		Integer32,
	ip2AsiProtocol
		INTEGER,
	ip2AsiAsiMode
		INTEGER,
	ip2AsiAsiRate
		INTEGER,
	ip2AsiInputState
		DisplayString,
	ip2AsiOutputAsi
		TruthValue,
	ip2AsiSocketIp
		Integer32,
	ip2AsiOutputState
		DisplayString
}

ip2AsiIOInOutIndex  OBJECT-TYPE
	SYNTAX     Integer32 (1..7)
	MAX-ACCESS not-accessible
	STATUS     current
	DESCRIPTION 
		"IP/ASI Input Output Index"
	::= { ip2AsiIOEntry 1 }

ip2AsiIOInOut  OBJECT-TYPE
	SYNTAX     Integer32 (1..7)
	MAX-ACCESS read-only
	STATUS     current
	DESCRIPTION 
		"IP/ASI in/out number"
	::= { ip2AsiIOEntry 2 }

ip2AsiIOAddressIndex  OBJECT-TYPE
	SYNTAX     Integer32 (1..10)
	MAX-ACCESS not-accessible
	STATUS     current
	DESCRIPTION 
		"IP/ASI control address index"
	::= { ip2AsiIOEntry 3 }

ip2AsiIOAddress  OBJECT-TYPE
	SYNTAX     Integer32 (61..70)
	MAX-ACCESS read-only
	STATUS     current
	DESCRIPTION 
		"IP/ASI control address"
	::= { ip2AsiIOEntry 4 }

ip2AsiInput  OBJECT-TYPE
	SYNTAX     TruthValue
	MAX-ACCESS read-write
	STATUS     current
	DESCRIPTION 
		"Enable/disable input"
	::= { ip2AsiIOEntry 5 }

ip2AsiMulticast  OBJECT-TYPE
	SYNTAX     TruthValue
	MAX-ACCESS read-write
	STATUS     current
	DESCRIPTION 
		"IP/ASI Multicast enable/disable"
	::= { ip2AsiIOEntry 6 }

ip2AsiIpMulticast  OBJECT-TYPE
	SYNTAX     IpAddress
	MAX-ACCESS read-write
	STATUS     current
	DESCRIPTION 
		"IP/ASI Multicast IP"
	::= { ip2AsiIOEntry 7 }

ip2AsiIpSrc  OBJECT-TYPE
	SYNTAX     IpAddress
	MAX-ACCESS read-write
	STATUS     current
	DESCRIPTION 
		"IP/ASI Source Multicast IP"
	::= { ip2AsiIOEntry 8 }

ip2AsiInputPort  OBJECT-TYPE
	SYNTAX     Integer32 (0..65535)
	MAX-ACCESS read-write
	STATUS     current
	DESCRIPTION 
		"IP/ASI input socket port"
	::= { ip2AsiIOEntry 9 }

ip2AsiInputLatency  OBJECT-TYPE
	SYNTAX     Integer32 (1..999)
	UNITS 	"ms"
	MAX-ACCESS read-write
	STATUS     current
	DESCRIPTION 
		"Configure latency"
	::= { ip2AsiIOEntry 10 }

ip2AsiProtocol  OBJECT-TYPE
	SYNTAX     INTEGER {
		ip2AsiUdp (1),
		ip2AsiRtp (2)
	}
	MAX-ACCESS read-write
	STATUS     current
	DESCRIPTION 
		"IP/ASI UDP/RTP protocol"
	::= { ip2AsiIOEntry 11 }

ip2AsiAsiMode  OBJECT-TYPE
	SYNTAX     INTEGER {
		ip2AsiByte (1),
		ip2AsiPacket (2)
	}
	MAX-ACCESS read-write
	STATUS     current
	DESCRIPTION 
		"IP/ASI ASI Mode (byte/packet)"
	::= { ip2AsiIOEntry 12 }

ip2AsiAsiRate  OBJECT-TYPE
	SYNTAX     INTEGER {
		ip2AsiNormal (1),
		ip2AsiConstant (2)
	}
	MAX-ACCESS read-write
	STATUS     current
	DESCRIPTION 
		"IP/ASI Rate (normal/constant)"
	::= { ip2AsiIOEntry 13 }

ip2AsiInputState  OBJECT-TYPE
	SYNTAX     DisplayString
	MAX-ACCESS read-only
	STATUS     current
	DESCRIPTION 
		"IP/ASI input (IP-socket) state:
		Bitrate Mbps"
	::= { ip2AsiIOEntry 14 }

ip2AsiOutputAsi  OBJECT-TYPE
	SYNTAX     TruthValue
	MAX-ACCESS read-write
	STATUS     current
	DESCRIPTION 
		"Enable/disable output"
	::= { ip2AsiIOEntry 15 }

ip2AsiSocketIp  OBJECT-TYPE
	SYNTAX     Integer32 (1..7)
	MAX-ACCESS read-write
	STATUS     current
	DESCRIPTION 
		"Select the Socket-IP (input) for this output"
	::= { ip2AsiIOEntry 16 }

ip2AsiOutputState  OBJECT-TYPE
	SYNTAX     DisplayString
	MAX-ACCESS read-only
	STATUS     current
	DESCRIPTION 
		"IP/ASI output (ASI) state:
		Bitrate Mbps / Latency / Latency min"
	::= { ip2AsiIOEntry 17 }

ip2AsiAlarmsTable  OBJECT-TYPE
	SYNTAX SEQUENCE OF Ip2AsiAlarmsEntry
	MAX-ACCESS not-accessible
	STATUS     current
	DESCRIPTION 
		"This table contains the alarm status of each IP/ASI"
	::= { ip2Asi 3 }

ip2AsiAlarmsEntry  OBJECT-TYPE
	SYNTAX 	Ip2AsiAlarmsEntry
	MAX-ACCESS not-accessible
	STATUS     current
	DESCRIPTION 
		"Each row is the IP2ASI information."
	INDEX { ip2AsiAlarmsIndex }
	::= { ip2AsiAlarmsTable 1 }

Ip2AsiAlarmsEntry ::= SEQUENCE {
	ip2AsiAlarmsIndex
		Integer32,
	ip2AsiCtrlAddressAlarm
		Integer32,
	ip2AsiMajorAlarm
		INTEGER,
	ip2AsiMinorAlarm
		INTEGER,
	ip2AsiTemperatureAlarm
		INTEGER,
	ip2AsiHwAlarm
		INTEGER,
	ip2AsiCommunicationAlarm
		INTEGER,
	ip2AsiSocketIp01Alarm
		INTEGER,
	ip2AsiAsiOutput01Alarm
		INTEGER,
	ip2AsiSocketIp02Alarm
		INTEGER,
	ip2AsiAsiOutput02Alarm
		INTEGER,
	ip2AsiSocketIp03Alarm
		INTEGER,
	ip2AsiAsiOutput03Alarm
		INTEGER,
	ip2AsiSocketIp04Alarm
		INTEGER,
	ip2AsiAsiOutput04Alarm
		INTEGER,
	ip2AsiSocketIp05Alarm
		INTEGER,
	ip2AsiAsiOutput05Alarm
		INTEGER,
	ip2AsiSocketIp06Alarm
		INTEGER,
	ip2AsiAsiOutput06Alarm
		INTEGER,
	ip2AsiSocketIp07Alarm
		INTEGER,
	ip2AsiAsiOutput07Alarm
		INTEGER
}

ip2AsiAlarmsIndex  OBJECT-TYPE
	SYNTAX     Integer32 (1..2)
	MAX-ACCESS not-accessible
	STATUS     current
	DESCRIPTION 
		"GPS index"
	::= { ip2AsiAlarmsEntry 1 }

ip2AsiCtrlAddressAlarm  OBJECT-TYPE
	SYNTAX     Integer32 (50..51)
	MAX-ACCESS read-only
	STATUS     current
	DESCRIPTION 
		"Control address for this module"
	::= { ip2AsiAlarmsEntry 2 }

ip2AsiMajorAlarm  OBJECT-TYPE
	SYNTAX     INTEGER {
		true (1),
		false (2)
	}
	MAX-ACCESS read-only
	STATUS     current
	DESCRIPTION 
		"IP2ASI Major Alarm status"
	::= { ip2AsiAlarmsEntry 3 }

ip2AsiMinorAlarm  OBJECT-TYPE
	SYNTAX     INTEGER {
		true (1),
		false (2)
	}
	MAX-ACCESS read-only
	STATUS     current
	DESCRIPTION 
		"IP2ASI Minor Alarm status"
	::= { ip2AsiAlarmsEntry 4 }

ip2AsiTemperatureAlarm  OBJECT-TYPE
	SYNTAX     INTEGER {
		true (1),
		false (2)
	}
	MAX-ACCESS read-only
	STATUS     current
	DESCRIPTION 
		"Temperature Alarm"
	::= { ip2AsiAlarmsEntry 5 }

ip2AsiHwAlarm  OBJECT-TYPE
	SYNTAX     INTEGER {
		true (1),
		false (2)
	}
	MAX-ACCESS read-only
	STATUS     current
	DESCRIPTION 
		"Hardware Error"
	::= { ip2AsiAlarmsEntry 6 }

ip2AsiCommunicationAlarm  OBJECT-TYPE
	SYNTAX     INTEGER {
		true (1),
		false (2)
	}
	MAX-ACCESS read-only
	STATUS     current
	DESCRIPTION 
		"Communication alarm status"
	::= { ip2AsiAlarmsEntry 7 }

ip2AsiSocketIp01Alarm  OBJECT-TYPE
	SYNTAX     INTEGER {
		true (1),
		false (2),
		deactived (3)
	}
	MAX-ACCESS read-only
	STATUS     current
	DESCRIPTION 
		"IP2ASI socket IP 01"
	::= { ip2AsiAlarmsEntry 8 }

ip2AsiAsiOutput01Alarm  OBJECT-TYPE
	SYNTAX     INTEGER {
		true (1),
		false (2),
		deactived (3)
	}
	MAX-ACCESS read-only
	STATUS     current
	DESCRIPTION 
		"IP2ASI ASI output 01"
	::= { ip2AsiAlarmsEntry 9 }

ip2AsiSocketIp02Alarm  OBJECT-TYPE
	SYNTAX     INTEGER {
		true (1),
		false (2),
		deactived (3)
	}
	MAX-ACCESS read-only
	STATUS     current
	DESCRIPTION 
		"IP2ASI socket IP 02"
	::= { ip2AsiAlarmsEntry 10 }

ip2AsiAsiOutput02Alarm  OBJECT-TYPE
	SYNTAX     INTEGER {
		true (1),
		false (2),
		deactived (3)
	}
	MAX-ACCESS read-only
	STATUS     current
	DESCRIPTION 
		"IP2ASI ASI output 02"
	::= { ip2AsiAlarmsEntry 11 }

ip2AsiSocketIp03Alarm  OBJECT-TYPE
	SYNTAX     INTEGER {
		true (1),
		false (2),
		deactived (3)
	}
	MAX-ACCESS read-only
	STATUS     current
	DESCRIPTION 
		"IP2ASI socket IP 03"
	::= { ip2AsiAlarmsEntry 12 }

ip2AsiAsiOutput03Alarm  OBJECT-TYPE
	SYNTAX     INTEGER {
		true (1),
		false (2),
		deactived (3)
	}
	MAX-ACCESS read-only
	STATUS     current
	DESCRIPTION 
		"IP2ASI ASI output 03"
	::= { ip2AsiAlarmsEntry 13 }

ip2AsiSocketIp04Alarm  OBJECT-TYPE
	SYNTAX     INTEGER {
		true (1),
		false (2),
		deactived (3)
	}
	MAX-ACCESS read-only
	STATUS     current
	DESCRIPTION 
		"IP2ASI socket IP 04"
	::= { ip2AsiAlarmsEntry 14 }

ip2AsiAsiOutput04Alarm  OBJECT-TYPE
	SYNTAX     INTEGER {
		true (1),
		false (2),
		deactived (3)
	}
	MAX-ACCESS read-only
	STATUS     current
	DESCRIPTION 
		"IP2ASI ASI output 04"
	::= { ip2AsiAlarmsEntry 15 }

ip2AsiSocketIp05Alarm  OBJECT-TYPE
	SYNTAX     INTEGER {
		true (1),
		false (2),
		deactived (3)
	}
	MAX-ACCESS read-only
	STATUS     current
	DESCRIPTION 
		"IP2ASI socket IP 05"
	::= { ip2AsiAlarmsEntry 16 }

ip2AsiAsiOutput05Alarm  OBJECT-TYPE
	SYNTAX     INTEGER {
		true (1),
		false (2),
		deactived (3)
	}
	MAX-ACCESS read-only
	STATUS     current
	DESCRIPTION 
		"IP2ASI ASI output 05"
	::= { ip2AsiAlarmsEntry 17 }

ip2AsiSocketIp06Alarm  OBJECT-TYPE
	SYNTAX     INTEGER {
		true (1),
		false (2),
		deactived (3)
	}
	MAX-ACCESS read-only
	STATUS     current
	DESCRIPTION 
		"IP2ASI socket IP 06"
	::= { ip2AsiAlarmsEntry 18 }

ip2AsiAsiOutput06Alarm  OBJECT-TYPE
	SYNTAX     INTEGER {
		true (1),
		false (2),
		deactived (3)
	}
	MAX-ACCESS read-only
	STATUS     current
	DESCRIPTION 
		"IP2ASI ASI output 06"
	::= { ip2AsiAlarmsEntry 19 }

ip2AsiSocketIp07Alarm  OBJECT-TYPE
	SYNTAX     INTEGER {
		true (1),
		false (2),
		deactived (3)
	}
	MAX-ACCESS read-only
	STATUS     current
	DESCRIPTION 
		"IP2ASI socket IP 07"
	::= { ip2AsiAlarmsEntry 20 }

ip2AsiAsiOutput07Alarm  OBJECT-TYPE
	SYNTAX     INTEGER {
		true (1),
		false (2),
		deactived (3)
	}
	MAX-ACCESS read-only
	STATUS     current
	DESCRIPTION 
		"IP2ASI ASI output 07"
	::= { ip2AsiAlarmsEntry 21 }

ip2AsiEnableAlarmsTable  OBJECT-TYPE
	SYNTAX SEQUENCE OF Ip2AsiEnableAlarmsEntry
	MAX-ACCESS not-accessible
	STATUS     current
	DESCRIPTION 
		"Enable/Disable alarms"
	::= { ip2Asi 4 }

ip2AsiEnableAlarmsEntry  OBJECT-TYPE
	SYNTAX 	Ip2AsiEnableAlarmsEntry
	MAX-ACCESS not-accessible
	STATUS     current
	DESCRIPTION 
		"Each row is the IP2ASI information."
	INDEX { ip2AsiEnableAIndex }
	::= { ip2AsiEnableAlarmsTable 1 }

Ip2AsiEnableAlarmsEntry ::= SEQUENCE {
	ip2AsiEnableAIndex
		Integer32,
	ip2AsiCtrlAddressEnableA
		Integer32,
	ip2AsiMajorEnableA
		TruthValue,
	ip2AsiMinorEnableA
		TruthValue,
	ip2AsiTemperatureEnableA
		TruthValue,
	ip2AsiHwEnableA
		TruthValue,
	ip2AsiCommunicationEnableA
		TruthValue,
	ip2AsiSocketIp01EnableA
		TruthValue,
	ip2AsiAsiOutput01EnableA
		TruthValue,
	ip2AsiSocketIp02EnableA
		TruthValue,
	ip2AsiAsiOutput02EnableA
		TruthValue,
	ip2AsiSocketIp03EnableA
		TruthValue,
	ip2AsiAsiOutput03EnableA
		TruthValue,
	ip2AsiSocketIp04EnableA
		TruthValue,
	ip2AsiAsiOutput04EnableA
		TruthValue,
	ip2AsiSocketIp05EnableA
		TruthValue,
	ip2AsiAsiOutput05EnableA
		TruthValue,
	ip2AsiSocketIp06EnableA
		TruthValue,
	ip2AsiAsiOutput06EnableA
		TruthValue,
	ip2AsiSocketIp07EnableA
		TruthValue,
	ip2AsiAsiOutput07EnableA
		TruthValue
}

ip2AsiEnableAIndex  OBJECT-TYPE
	SYNTAX     Integer32 (1..2)
	MAX-ACCESS not-accessible
	STATUS     current
	DESCRIPTION 
		"GPS index"
	::= { ip2AsiEnableAlarmsEntry 1 }

ip2AsiCtrlAddressEnableA  OBJECT-TYPE
	SYNTAX     Integer32 (50..51)
	MAX-ACCESS read-only
	STATUS     current
	DESCRIPTION 
		"Control address for this module"
	::= { ip2AsiEnableAlarmsEntry 2 }

ip2AsiMajorEnableA  OBJECT-TYPE
	SYNTAX     TruthValue
	MAX-ACCESS read-write
	STATUS     current
	DESCRIPTION 
		"IP2ASI Major Alarm status"
	::= { ip2AsiEnableAlarmsEntry 3 }

ip2AsiMinorEnableA  OBJECT-TYPE
	SYNTAX     TruthValue
	MAX-ACCESS read-write
	STATUS     current
	DESCRIPTION 
		"IP2ASI Minor Alarm status"
	::= { ip2AsiEnableAlarmsEntry 4 }

ip2AsiTemperatureEnableA  OBJECT-TYPE
	SYNTAX     TruthValue
	MAX-ACCESS read-write
	STATUS     current
	DESCRIPTION 
		"Temperature Alarm"
	::= { ip2AsiEnableAlarmsEntry 5 }

ip2AsiHwEnableA  OBJECT-TYPE
	SYNTAX     TruthValue
	MAX-ACCESS read-write
	STATUS     current
	DESCRIPTION 
		"Hardware Error"
	::= { ip2AsiEnableAlarmsEntry 6 }

ip2AsiCommunicationEnableA  OBJECT-TYPE
	SYNTAX     TruthValue
	MAX-ACCESS read-write
	STATUS     current
	DESCRIPTION 
		"Communication alarm status"
	::= { ip2AsiEnableAlarmsEntry 7 }

ip2AsiSocketIp01EnableA  OBJECT-TYPE
	SYNTAX     TruthValue
	MAX-ACCESS read-write
	STATUS     current
	DESCRIPTION 
		"IP2ASI socket IP 01"
	::= { ip2AsiEnableAlarmsEntry 8 }

ip2AsiAsiOutput01EnableA  OBJECT-TYPE
	SYNTAX     TruthValue
	MAX-ACCESS read-write
	STATUS     current
	DESCRIPTION 
		"IP2ASI ASI output 01"
	::= { ip2AsiEnableAlarmsEntry 9 }

ip2AsiSocketIp02EnableA  OBJECT-TYPE
	SYNTAX     TruthValue
	MAX-ACCESS read-write
	STATUS     current
	DESCRIPTION 
		"IP2ASI socket IP 02"
	::= { ip2AsiEnableAlarmsEntry 10 }

ip2AsiAsiOutput02EnableA  OBJECT-TYPE
	SYNTAX     TruthValue
	MAX-ACCESS read-write
	STATUS     current
	DESCRIPTION 
		"IP2ASI ASI output 02"
	::= { ip2AsiEnableAlarmsEntry 11 }

ip2AsiSocketIp03EnableA  OBJECT-TYPE
	SYNTAX     TruthValue
	MAX-ACCESS read-write
	STATUS     current
	DESCRIPTION 
		"IP2ASI socket IP 03"
	::= { ip2AsiEnableAlarmsEntry 12 }

ip2AsiAsiOutput03EnableA  OBJECT-TYPE
	SYNTAX     TruthValue
	MAX-ACCESS read-write
	STATUS     current
	DESCRIPTION 
		"IP2ASI ASI output 03"
	::= { ip2AsiEnableAlarmsEntry 13 }

ip2AsiSocketIp04EnableA  OBJECT-TYPE
	SYNTAX     TruthValue
	MAX-ACCESS read-write
	STATUS     current
	DESCRIPTION 
		"IP2ASI socket IP 04"
	::= { ip2AsiEnableAlarmsEntry 14 }

ip2AsiAsiOutput04EnableA  OBJECT-TYPE
	SYNTAX     TruthValue
	MAX-ACCESS read-write
	STATUS     current
	DESCRIPTION 
		"IP2ASI ASI output 04"
	::= { ip2AsiEnableAlarmsEntry 15 }

ip2AsiSocketIp05EnableA  OBJECT-TYPE
	SYNTAX     TruthValue
	MAX-ACCESS read-write
	STATUS     current
	DESCRIPTION 
		"IP2ASI socket IP 05"
	::= { ip2AsiEnableAlarmsEntry 16 }

ip2AsiAsiOutput05EnableA  OBJECT-TYPE
	SYNTAX     TruthValue
	MAX-ACCESS read-write
	STATUS     current
	DESCRIPTION 
		"IP2ASI ASI output 05"
	::= { ip2AsiEnableAlarmsEntry 17 }

ip2AsiSocketIp06EnableA  OBJECT-TYPE
	SYNTAX     TruthValue
	MAX-ACCESS read-write
	STATUS     current
	DESCRIPTION 
		"IP2ASI socket IP 06"
	::= { ip2AsiEnableAlarmsEntry 18 }

ip2AsiAsiOutput06EnableA  OBJECT-TYPE
	SYNTAX     TruthValue
	MAX-ACCESS read-write
	STATUS     current
	DESCRIPTION 
		"IP2ASI ASI output 06"
	::= { ip2AsiEnableAlarmsEntry 19 }

ip2AsiSocketIp07EnableA  OBJECT-TYPE
	SYNTAX     TruthValue
	MAX-ACCESS read-write
	STATUS     current
	DESCRIPTION 
		"IP2ASI socket IP 07"
	::= { ip2AsiEnableAlarmsEntry 20 }

ip2AsiAsiOutput07EnableA  OBJECT-TYPE
	SYNTAX     TruthValue
	MAX-ACCESS read-write
	STATUS     current
	DESCRIPTION 
		"IP2ASI ASI output 07"
	::= { ip2AsiEnableAlarmsEntry 21 }

ip2AsiEnableTrapsTable  OBJECT-TYPE
	SYNTAX SEQUENCE OF Ip2AsiEnableTrapsEntry
	MAX-ACCESS not-accessible
	STATUS     current
	DESCRIPTION 
		"Enable/Disable traps"
	::= { ip2Asi 5 }

ip2AsiEnableTrapsEntry  OBJECT-TYPE
	SYNTAX 	Ip2AsiEnableTrapsEntry
	MAX-ACCESS not-accessible
	STATUS     current
	DESCRIPTION 
		"Each row is the IP2ASI information."
	INDEX { ip2AsiEnableTIndex }
	::= { ip2AsiEnableTrapsTable 1 }

Ip2AsiEnableTrapsEntry ::= SEQUENCE {
	ip2AsiEnableTIndex
		Integer32,
	ip2AsiCtrlAddressEnableT
		Integer32,
	ip2AsiMajorEnableT
		TruthValue,
	ip2AsiMinorEnableT
		TruthValue,
	ip2AsiTemperatureEnableT
		TruthValue,
	ip2AsiHwEnableT
		TruthValue,
	ip2AsiCommunicationEnableT
		TruthValue,
	ip2AsiSocketIp01EnableT
		TruthValue,
	ip2AsiAsiOutput01EnableT
		TruthValue,
	ip2AsiSocketIp02EnableT
		TruthValue,
	ip2AsiAsiOutput02EnableT
		TruthValue,
	ip2AsiSocketIp03EnableT
		TruthValue,
	ip2AsiAsiOutput03EnableT
		TruthValue,
	ip2AsiSocketIp04EnableT
		TruthValue,
	ip2AsiAsiOutput04EnableT
		TruthValue,
	ip2AsiSocketIp05EnableT
		TruthValue,
	ip2AsiAsiOutput05EnableT
		TruthValue,
	ip2AsiSocketIp06EnableT
		TruthValue,
	ip2AsiAsiOutput06EnableT
		TruthValue,
	ip2AsiSocketIp07EnableT
		TruthValue,
	ip2AsiAsiOutput07EnableT
		TruthValue
}

ip2AsiEnableTIndex  OBJECT-TYPE
	SYNTAX     Integer32 (1..2)
	MAX-ACCESS not-accessible
	STATUS     current
	DESCRIPTION 
		"GPS index"
	::= { ip2AsiEnableTrapsEntry 1 }

ip2AsiCtrlAddressEnableT  OBJECT-TYPE
	SYNTAX     Integer32 (50..51)
	MAX-ACCESS read-only
	STATUS     current
	DESCRIPTION 
		"Control address for this module"
	::= { ip2AsiEnableTrapsEntry 2 }

ip2AsiMajorEnableT  OBJECT-TYPE
	SYNTAX     TruthValue
	MAX-ACCESS read-write
	STATUS     current
	DESCRIPTION 
		"IP2ASI Major Alarm status"
	::= { ip2AsiEnableTrapsEntry 3 }

ip2AsiMinorEnableT  OBJECT-TYPE
	SYNTAX     TruthValue
	MAX-ACCESS read-write
	STATUS     current
	DESCRIPTION 
		"IP2ASI Minor Alarm status"
	::= { ip2AsiEnableTrapsEntry 4 }

ip2AsiTemperatureEnableT  OBJECT-TYPE
	SYNTAX     TruthValue
	MAX-ACCESS read-write
	STATUS     current
	DESCRIPTION 
		"Temperature Alarm"
	::= { ip2AsiEnableTrapsEntry 5 }

ip2AsiHwEnableT  OBJECT-TYPE
	SYNTAX     TruthValue
	MAX-ACCESS read-write
	STATUS     current
	DESCRIPTION 
		"Hardware Error"
	::= { ip2AsiEnableTrapsEntry 6 }

ip2AsiCommunicationEnableT  OBJECT-TYPE
	SYNTAX     TruthValue
	MAX-ACCESS read-write
	STATUS     current
	DESCRIPTION 
		"Communication alarm status"
	::= { ip2AsiEnableTrapsEntry 7 }

ip2AsiSocketIp01EnableT  OBJECT-TYPE
	SYNTAX     TruthValue
	MAX-ACCESS read-write
	STATUS     current
	DESCRIPTION 
		"IP2ASI socket IP 01"
	::= { ip2AsiEnableTrapsEntry 8 }

ip2AsiAsiOutput01EnableT  OBJECT-TYPE
	SYNTAX     TruthValue
	MAX-ACCESS read-write
	STATUS     current
	DESCRIPTION 
		"IP2ASI ASI output 01"
	::= { ip2AsiEnableTrapsEntry 9 }

ip2AsiSocketIp02EnableT  OBJECT-TYPE
	SYNTAX     TruthValue
	MAX-ACCESS read-write
	STATUS     current
	DESCRIPTION 
		"IP2ASI socket IP 02"
	::= { ip2AsiEnableTrapsEntry 10 }

ip2AsiAsiOutput02EnableT  OBJECT-TYPE
	SYNTAX     TruthValue
	MAX-ACCESS read-write
	STATUS     current
	DESCRIPTION 
		"IP2ASI ASI output 02"
	::= { ip2AsiEnableTrapsEntry 11 }

ip2AsiSocketIp03EnableT  OBJECT-TYPE
	SYNTAX     TruthValue
	MAX-ACCESS read-write
	STATUS     current
	DESCRIPTION 
		"IP2ASI socket IP 03"
	::= { ip2AsiEnableTrapsEntry 12 }

ip2AsiAsiOutput03EnableT  OBJECT-TYPE
	SYNTAX     TruthValue
	MAX-ACCESS read-write
	STATUS     current
	DESCRIPTION 
		"IP2ASI ASI output 03"
	::= { ip2AsiEnableTrapsEntry 13 }

ip2AsiSocketIp04EnableT  OBJECT-TYPE
	SYNTAX     TruthValue
	MAX-ACCESS read-write
	STATUS     current
	DESCRIPTION 
		"IP2ASI socket IP 04"
	::= { ip2AsiEnableTrapsEntry 14 }

ip2AsiAsiOutput04EnableT  OBJECT-TYPE
	SYNTAX     TruthValue
	MAX-ACCESS read-write
	STATUS     current
	DESCRIPTION 
		"IP2ASI ASI output 04"
	::= { ip2AsiEnableTrapsEntry 15 }

ip2AsiSocketIp05EnableT  OBJECT-TYPE
	SYNTAX     TruthValue
	MAX-ACCESS read-write
	STATUS     current
	DESCRIPTION 
		"IP2ASI socket IP 05"
	::= { ip2AsiEnableTrapsEntry 16 }

ip2AsiAsiOutput05EnableT  OBJECT-TYPE
	SYNTAX     TruthValue
	MAX-ACCESS read-write
	STATUS     current
	DESCRIPTION 
		"IP2ASI ASI output 05"
	::= { ip2AsiEnableTrapsEntry 17 }

ip2AsiSocketIp06EnableT  OBJECT-TYPE
	SYNTAX     TruthValue
	MAX-ACCESS read-write
	STATUS     current
	DESCRIPTION 
		"IP2ASI socket IP 06"
	::= { ip2AsiEnableTrapsEntry 18 }

ip2AsiAsiOutput06EnableT  OBJECT-TYPE
	SYNTAX     TruthValue
	MAX-ACCESS read-write
	STATUS     current
	DESCRIPTION 
		"IP2ASI ASI output 06"
	::= { ip2AsiEnableTrapsEntry 19 }

ip2AsiSocketIp07EnableT  OBJECT-TYPE
	SYNTAX     TruthValue
	MAX-ACCESS read-write
	STATUS     current
	DESCRIPTION 
		"IP2ASI socket IP 07"
	::= { ip2AsiEnableTrapsEntry 20 }

ip2AsiAsiOutput07EnableT  OBJECT-TYPE
	SYNTAX     TruthValue
	MAX-ACCESS read-write
	STATUS     current
	DESCRIPTION 
		"IP2ASI ASI output 07"
	::= { ip2AsiEnableTrapsEntry 21 }


transmittedPower1Trap  NOTIFICATION-TYPE
	OBJECTS { eventIdTrap, 
		notificationIdTrap, 
		perceivedSeverityTrap, 
		timeStampTrap, 
		additionalTextTrap }
	STATUS     current
	DESCRIPTION 
		"MUX index 1"
	::= { transmittedPowerTrapsPrefix 1 }

transmittedPower2Trap  NOTIFICATION-TYPE
	OBJECTS { eventIdTrap, 
		notificationIdTrap, 
		perceivedSeverityTrap, 
		timeStampTrap, 
		additionalTextTrap }
	STATUS     current
	DESCRIPTION 
		"MUX index 2"
	::= { transmittedPowerTrapsPrefix 2 }

transmittedPower3Trap  NOTIFICATION-TYPE
	OBJECTS { eventIdTrap, 
		notificationIdTrap, 
		perceivedSeverityTrap, 
		timeStampTrap, 
		additionalTextTrap }
	STATUS     current
	DESCRIPTION 
		"MUX index 3"
	::= { transmittedPowerTrapsPrefix 3 }

transmittedPower4Trap  NOTIFICATION-TYPE
	OBJECTS { eventIdTrap, 
		notificationIdTrap, 
		perceivedSeverityTrap, 
		timeStampTrap, 
		additionalTextTrap }
	STATUS     current
	DESCRIPTION 
		"MUX index 4"
	::= { transmittedPowerTrapsPrefix 4 }

transmittedPower5Trap  NOTIFICATION-TYPE
	OBJECTS { eventIdTrap, 
		notificationIdTrap, 
		perceivedSeverityTrap, 
		timeStampTrap, 
		additionalTextTrap }
	STATUS     current
	DESCRIPTION 
		"MUX index 5"
	::= { transmittedPowerTrapsPrefix 5 }

transmittedPower6Trap  NOTIFICATION-TYPE
	OBJECTS { eventIdTrap, 
		notificationIdTrap, 
		perceivedSeverityTrap, 
		timeStampTrap, 
		additionalTextTrap }
	STATUS     current
	DESCRIPTION 
		"MUX index 6"
	::= { transmittedPowerTrapsPrefix 6 }

transmittedPower7Trap  NOTIFICATION-TYPE
	OBJECTS { eventIdTrap, 
		notificationIdTrap, 
		perceivedSeverityTrap, 
		timeStampTrap, 
		additionalTextTrap }
	STATUS     current
	DESCRIPTION 
		"MUX index 7"
	::= { transmittedPowerTrapsPrefix 7 }

transmittedPower8Trap  NOTIFICATION-TYPE
	OBJECTS { eventIdTrap, 
		notificationIdTrap, 
		perceivedSeverityTrap, 
		timeStampTrap, 
		additionalTextTrap }
	STATUS     current
	DESCRIPTION 
		"MUX index 8"
	::= { transmittedPowerTrapsPrefix 8 }

transmittedPower9Trap  NOTIFICATION-TYPE
	OBJECTS { eventIdTrap, 
		notificationIdTrap, 
		perceivedSeverityTrap, 
		timeStampTrap, 
		additionalTextTrap }
	STATUS     current
	DESCRIPTION 
		"MUX index 9"
	::= { transmittedPowerTrapsPrefix 9 }

transmittedPower10Trap  NOTIFICATION-TYPE
	OBJECTS { eventIdTrap, 
		notificationIdTrap, 
		perceivedSeverityTrap, 
		timeStampTrap, 
		additionalTextTrap }
	STATUS     current
	DESCRIPTION 
		"MUX index 10"
	::= { transmittedPowerTrapsPrefix 10 }

transmittedPower11Trap  NOTIFICATION-TYPE
	OBJECTS { eventIdTrap, 
		notificationIdTrap, 
		perceivedSeverityTrap, 
		timeStampTrap, 
		additionalTextTrap }
	STATUS     current
	DESCRIPTION 
		"MUX index 11"
	::= { transmittedPowerTrapsPrefix 11 }

transmittedPower12Trap  NOTIFICATION-TYPE
	OBJECTS { eventIdTrap, 
		notificationIdTrap, 
		perceivedSeverityTrap, 
		timeStampTrap, 
		additionalTextTrap }
	STATUS     current
	DESCRIPTION 
		"MUX index 12"
	::= { transmittedPowerTrapsPrefix 12 }

transmittedPower13Trap  NOTIFICATION-TYPE
	OBJECTS { eventIdTrap, 
		notificationIdTrap, 
		perceivedSeverityTrap, 
		timeStampTrap, 
		additionalTextTrap }
	STATUS     current
	DESCRIPTION 
		"MUX index 13"
	::= { transmittedPowerTrapsPrefix 13 }

transmittedPower14Trap  NOTIFICATION-TYPE
	OBJECTS { eventIdTrap, 
		notificationIdTrap, 
		perceivedSeverityTrap, 
		timeStampTrap, 
		additionalTextTrap }
	STATUS     current
	DESCRIPTION 
		"MUX index 14"
	::= { transmittedPowerTrapsPrefix 14 }

transmittedPower15Trap  NOTIFICATION-TYPE
	OBJECTS { eventIdTrap, 
		notificationIdTrap, 
		perceivedSeverityTrap, 
		timeStampTrap, 
		additionalTextTrap }
	STATUS     current
	DESCRIPTION 
		"MUX index 15"
	::= { transmittedPowerTrapsPrefix 15 }

transmittedPower16Trap  NOTIFICATION-TYPE
	OBJECTS { eventIdTrap, 
		notificationIdTrap, 
		perceivedSeverityTrap, 
		timeStampTrap, 
		additionalTextTrap }
	STATUS     current
	DESCRIPTION 
		"MUX index 16"
	::= { transmittedPowerTrapsPrefix 16 }

transmittedPower17Trap  NOTIFICATION-TYPE
	OBJECTS { eventIdTrap, 
		notificationIdTrap, 
		perceivedSeverityTrap, 
		timeStampTrap, 
		additionalTextTrap }
	STATUS     current
	DESCRIPTION 
		"MUX index 17"
	::= { transmittedPowerTrapsPrefix 17 }

transmittedPower18Trap  NOTIFICATION-TYPE
	OBJECTS { eventIdTrap, 
		notificationIdTrap, 
		perceivedSeverityTrap, 
		timeStampTrap, 
		additionalTextTrap }
	STATUS     current
	DESCRIPTION 
		"MUX index 18"
	::= { transmittedPowerTrapsPrefix 18 }

transmittedPower19Trap  NOTIFICATION-TYPE
	OBJECTS { eventIdTrap, 
		notificationIdTrap, 
		perceivedSeverityTrap, 
		timeStampTrap, 
		additionalTextTrap }
	STATUS     current
	DESCRIPTION 
		"MUX index 19"
	::= { transmittedPowerTrapsPrefix 19 }

transmittedPower20Trap  NOTIFICATION-TYPE
	OBJECTS { eventIdTrap, 
		notificationIdTrap, 
		perceivedSeverityTrap, 
		timeStampTrap, 
		additionalTextTrap }
	STATUS     current
	DESCRIPTION 
		"MUX index 20"
	::= { transmittedPowerTrapsPrefix 20 }

transmittedPower21Trap  NOTIFICATION-TYPE
	OBJECTS { eventIdTrap, 
		notificationIdTrap, 
		perceivedSeverityTrap, 
		timeStampTrap, 
		additionalTextTrap }
	STATUS     current
	DESCRIPTION 
		"MUX index 21"
	::= { transmittedPowerTrapsPrefix 21 }

transmittedPower22Trap  NOTIFICATION-TYPE
	OBJECTS { eventIdTrap, 
		notificationIdTrap, 
		perceivedSeverityTrap, 
		timeStampTrap, 
		additionalTextTrap }
	STATUS     current
	DESCRIPTION 
		"MUX index 22"
	::= { transmittedPowerTrapsPrefix 22 }

transmittedPower23Trap  NOTIFICATION-TYPE
	OBJECTS { eventIdTrap, 
		notificationIdTrap, 
		perceivedSeverityTrap, 
		timeStampTrap, 
		additionalTextTrap }
	STATUS     current
	DESCRIPTION 
		"MUX index 23"
	::= { transmittedPowerTrapsPrefix 23 }

transmittedPower24Trap  NOTIFICATION-TYPE
	OBJECTS { eventIdTrap, 
		notificationIdTrap, 
		perceivedSeverityTrap, 
		timeStampTrap, 
		additionalTextTrap }
	STATUS     current
	DESCRIPTION 
		"MUX index 24"
	::= { transmittedPowerTrapsPrefix 24 }

transmittedPower25Trap  NOTIFICATION-TYPE
	OBJECTS { eventIdTrap, 
		notificationIdTrap, 
		perceivedSeverityTrap, 
		timeStampTrap, 
		additionalTextTrap }
	STATUS     current
	DESCRIPTION 
		"MUX index 25"
	::= { transmittedPowerTrapsPrefix 25 }

transmittedPower26Trap  NOTIFICATION-TYPE
	OBJECTS { eventIdTrap, 
		notificationIdTrap, 
		perceivedSeverityTrap, 
		timeStampTrap, 
		additionalTextTrap }
	STATUS     current
	DESCRIPTION 
		"MUX index 26"
	::= { transmittedPowerTrapsPrefix 26 }

transmittedPower27Trap  NOTIFICATION-TYPE
	OBJECTS { eventIdTrap, 
		notificationIdTrap, 
		perceivedSeverityTrap, 
		timeStampTrap, 
		additionalTextTrap }
	STATUS     current
	DESCRIPTION 
		"MUX index 27"
	::= { transmittedPowerTrapsPrefix 27 }

transmittedPower28Trap  NOTIFICATION-TYPE
	OBJECTS { eventIdTrap, 
		notificationIdTrap, 
		perceivedSeverityTrap, 
		timeStampTrap, 
		additionalTextTrap }
	STATUS     current
	DESCRIPTION 
		"MUX index 28"
	::= { transmittedPowerTrapsPrefix 28 }

transmittedPower29Trap  NOTIFICATION-TYPE
	OBJECTS { eventIdTrap, 
		notificationIdTrap, 
		perceivedSeverityTrap, 
		timeStampTrap, 
		additionalTextTrap }
	STATUS     current
	DESCRIPTION 
		"MUX index 29"
	::= { transmittedPowerTrapsPrefix 29 }

transmittedPower30Trap  NOTIFICATION-TYPE
	OBJECTS { eventIdTrap, 
		notificationIdTrap, 
		perceivedSeverityTrap, 
		timeStampTrap, 
		additionalTextTrap }
	STATUS     current
	DESCRIPTION 
		"MUX index 30"
	::= { transmittedPowerTrapsPrefix 30 }

trtCurrentsOutRange1Trap  NOTIFICATION-TYPE
	OBJECTS { eventIdTrap, 
		notificationIdTrap, 
		perceivedSeverityTrap, 
		timeStampTrap, 
		additionalTextTrap }
	STATUS     current
	DESCRIPTION 
		"MUX index 1"
	::= { trtCurrectsOutRangeTrapsPrefix 1 }

trtCurrentsOutRange2Trap  NOTIFICATION-TYPE
	OBJECTS { eventIdTrap, 
		notificationIdTrap, 
		perceivedSeverityTrap, 
		timeStampTrap, 
		additionalTextTrap }
	STATUS     current
	DESCRIPTION 
		"MUX index 2"
	::= { trtCurrectsOutRangeTrapsPrefix 2 }

trtCurrentsOutRange3Trap  NOTIFICATION-TYPE
	OBJECTS { eventIdTrap, 
		notificationIdTrap, 
		perceivedSeverityTrap, 
		timeStampTrap, 
		additionalTextTrap }
	STATUS     current
	DESCRIPTION 
		"MUX index 3"
	::= { trtCurrectsOutRangeTrapsPrefix 3 }

trtCurrentsOutRange4Trap  NOTIFICATION-TYPE
	OBJECTS { eventIdTrap, 
		notificationIdTrap, 
		perceivedSeverityTrap, 
		timeStampTrap, 
		additionalTextTrap }
	STATUS     current
	DESCRIPTION 
		"MUX index 4"
	::= { trtCurrectsOutRangeTrapsPrefix 4 }

trtCurrentsOutRange5Trap  NOTIFICATION-TYPE
	OBJECTS { eventIdTrap, 
		notificationIdTrap, 
		perceivedSeverityTrap, 
		timeStampTrap, 
		additionalTextTrap }
	STATUS     current
	DESCRIPTION 
		"MUX index 5"
	::= { trtCurrectsOutRangeTrapsPrefix 5 }

trtCurrentsOutRange6Trap  NOTIFICATION-TYPE
	OBJECTS { eventIdTrap, 
		notificationIdTrap, 
		perceivedSeverityTrap, 
		timeStampTrap, 
		additionalTextTrap }
	STATUS     current
	DESCRIPTION 
		"MUX index 6"
	::= { trtCurrectsOutRangeTrapsPrefix 6 }

trtCurrentsOutRange7Trap  NOTIFICATION-TYPE
	OBJECTS { eventIdTrap, 
		notificationIdTrap, 
		perceivedSeverityTrap, 
		timeStampTrap, 
		additionalTextTrap }
	STATUS     current
	DESCRIPTION 
		"MUX index 7"
	::= { trtCurrectsOutRangeTrapsPrefix 7 }

trtCurrentsOutRange8Trap  NOTIFICATION-TYPE
	OBJECTS { eventIdTrap, 
		notificationIdTrap, 
		perceivedSeverityTrap, 
		timeStampTrap, 
		additionalTextTrap }
	STATUS     current
	DESCRIPTION 
		"MUX index 8"
	::= { trtCurrectsOutRangeTrapsPrefix 8 }

trtCurrentsOutRange9Trap  NOTIFICATION-TYPE
	OBJECTS { eventIdTrap, 
		notificationIdTrap, 
		perceivedSeverityTrap, 
		timeStampTrap, 
		additionalTextTrap }
	STATUS     current
	DESCRIPTION 
		"MUX index 9"
	::= { trtCurrectsOutRangeTrapsPrefix 9 }

trtCurrentsOutRange10Trap  NOTIFICATION-TYPE
	OBJECTS { eventIdTrap, 
		notificationIdTrap, 
		perceivedSeverityTrap, 
		timeStampTrap, 
		additionalTextTrap }
	STATUS     current
	DESCRIPTION 
		"MUX index 10"
	::= { trtCurrectsOutRangeTrapsPrefix 10 }

trtCurrentsOutRange11Trap  NOTIFICATION-TYPE
	OBJECTS { eventIdTrap, 
		notificationIdTrap, 
		perceivedSeverityTrap, 
		timeStampTrap, 
		additionalTextTrap }
	STATUS     current
	DESCRIPTION 
		"MUX index 11"
	::= { trtCurrectsOutRangeTrapsPrefix 11 }

trtCurrentsOutRange12Trap  NOTIFICATION-TYPE
	OBJECTS { eventIdTrap, 
		notificationIdTrap, 
		perceivedSeverityTrap, 
		timeStampTrap, 
		additionalTextTrap }
	STATUS     current
	DESCRIPTION 
		"MUX index 12"
	::= { trtCurrectsOutRangeTrapsPrefix 12 }

trtCurrentsOutRange13Trap  NOTIFICATION-TYPE
	OBJECTS { eventIdTrap, 
		notificationIdTrap, 
		perceivedSeverityTrap, 
		timeStampTrap, 
		additionalTextTrap }
	STATUS     current
	DESCRIPTION 
		"MUX index 13"
	::= { trtCurrectsOutRangeTrapsPrefix 13 }

trtCurrentsOutRange14Trap  NOTIFICATION-TYPE
	OBJECTS { eventIdTrap, 
		notificationIdTrap, 
		perceivedSeverityTrap, 
		timeStampTrap, 
		additionalTextTrap }
	STATUS     current
	DESCRIPTION 
		"MUX index 14"
	::= { trtCurrectsOutRangeTrapsPrefix 14 }

trtCurrentsOutRange15Trap  NOTIFICATION-TYPE
	OBJECTS { eventIdTrap, 
		notificationIdTrap, 
		perceivedSeverityTrap, 
		timeStampTrap, 
		additionalTextTrap }
	STATUS     current
	DESCRIPTION 
		"MUX index 15"
	::= { trtCurrectsOutRangeTrapsPrefix 15 }

trtCurrentsOutRange16Trap  NOTIFICATION-TYPE
	OBJECTS { eventIdTrap, 
		notificationIdTrap, 
		perceivedSeverityTrap, 
		timeStampTrap, 
		additionalTextTrap }
	STATUS     current
	DESCRIPTION 
		"MUX index 16"
	::= { trtCurrectsOutRangeTrapsPrefix 16 }

trtCurrentsOutRange17Trap  NOTIFICATION-TYPE
	OBJECTS { eventIdTrap, 
		notificationIdTrap, 
		perceivedSeverityTrap, 
		timeStampTrap, 
		additionalTextTrap }
	STATUS     current
	DESCRIPTION 
		"MUX index 17"
	::= { trtCurrectsOutRangeTrapsPrefix 17 }

trtCurrentsOutRange18Trap  NOTIFICATION-TYPE
	OBJECTS { eventIdTrap, 
		notificationIdTrap, 
		perceivedSeverityTrap, 
		timeStampTrap, 
		additionalTextTrap }
	STATUS     current
	DESCRIPTION 
		"MUX index 18"
	::= { trtCurrectsOutRangeTrapsPrefix 18 }

trtCurrentsOutRange19Trap  NOTIFICATION-TYPE
	OBJECTS { eventIdTrap, 
		notificationIdTrap, 
		perceivedSeverityTrap, 
		timeStampTrap, 
		additionalTextTrap }
	STATUS     current
	DESCRIPTION 
		"MUX index 19"
	::= { trtCurrectsOutRangeTrapsPrefix 19 }

trtCurrentsOutRange20Trap  NOTIFICATION-TYPE
	OBJECTS { eventIdTrap, 
		notificationIdTrap, 
		perceivedSeverityTrap, 
		timeStampTrap, 
		additionalTextTrap }
	STATUS     current
	DESCRIPTION 
		"MUX index 20"
	::= { trtCurrectsOutRangeTrapsPrefix 20 }

trtCurrentsOutRange21Trap  NOTIFICATION-TYPE
	OBJECTS { eventIdTrap, 
		notificationIdTrap, 
		perceivedSeverityTrap, 
		timeStampTrap, 
		additionalTextTrap }
	STATUS     current
	DESCRIPTION 
		"MUX index 21"
	::= { trtCurrectsOutRangeTrapsPrefix 21 }

trtCurrentsOutRange22Trap  NOTIFICATION-TYPE
	OBJECTS { eventIdTrap, 
		notificationIdTrap, 
		perceivedSeverityTrap, 
		timeStampTrap, 
		additionalTextTrap }
	STATUS     current
	DESCRIPTION 
		"MUX index 22"
	::= { trtCurrectsOutRangeTrapsPrefix 22 }

trtCurrentsOutRange23Trap  NOTIFICATION-TYPE
	OBJECTS { eventIdTrap, 
		notificationIdTrap, 
		perceivedSeverityTrap, 
		timeStampTrap, 
		additionalTextTrap }
	STATUS     current
	DESCRIPTION 
		"MUX index 23"
	::= { trtCurrectsOutRangeTrapsPrefix 23 }

trtCurrentsOutRange24Trap  NOTIFICATION-TYPE
	OBJECTS { eventIdTrap, 
		notificationIdTrap, 
		perceivedSeverityTrap, 
		timeStampTrap, 
		additionalTextTrap }
	STATUS     current
	DESCRIPTION 
		"MUX index 24"
	::= { trtCurrectsOutRangeTrapsPrefix 24 }

trtCurrentsOutRange25Trap  NOTIFICATION-TYPE
	OBJECTS { eventIdTrap, 
		notificationIdTrap, 
		perceivedSeverityTrap, 
		timeStampTrap, 
		additionalTextTrap }
	STATUS     current
	DESCRIPTION 
		"MUX index 25"
	::= { trtCurrectsOutRangeTrapsPrefix 25 }

trtCurrentsOutRange26Trap  NOTIFICATION-TYPE
	OBJECTS { eventIdTrap, 
		notificationIdTrap, 
		perceivedSeverityTrap, 
		timeStampTrap, 
		additionalTextTrap }
	STATUS     current
	DESCRIPTION 
		"MUX index 26"
	::= { trtCurrectsOutRangeTrapsPrefix 26 }

trtCurrentsOutRange27Trap  NOTIFICATION-TYPE
	OBJECTS { eventIdTrap, 
		notificationIdTrap, 
		perceivedSeverityTrap, 
		timeStampTrap, 
		additionalTextTrap }
	STATUS     current
	DESCRIPTION 
		"MUX index 27"
	::= { trtCurrectsOutRangeTrapsPrefix 27 }

trtCurrentsOutRange28Trap  NOTIFICATION-TYPE
	OBJECTS { eventIdTrap, 
		notificationIdTrap, 
		perceivedSeverityTrap, 
		timeStampTrap, 
		additionalTextTrap }
	STATUS     current
	DESCRIPTION 
		"MUX index 28"
	::= { trtCurrectsOutRangeTrapsPrefix 28 }

trtCurrentsOutRange29Trap  NOTIFICATION-TYPE
	OBJECTS { eventIdTrap, 
		notificationIdTrap, 
		perceivedSeverityTrap, 
		timeStampTrap, 
		additionalTextTrap }
	STATUS     current
	DESCRIPTION 
		"MUX index 29"
	::= { trtCurrectsOutRangeTrapsPrefix 29 }

trtCurrentsOutRange30Trap  NOTIFICATION-TYPE
	OBJECTS { eventIdTrap, 
		notificationIdTrap, 
		perceivedSeverityTrap, 
		timeStampTrap, 
		additionalTextTrap }
	STATUS     current
	DESCRIPTION 
		"MUX index 30"
	::= { trtCurrectsOutRangeTrapsPrefix 30 }

reflectedPower1Trap  NOTIFICATION-TYPE
	OBJECTS { eventIdTrap, 
		notificationIdTrap, 
		perceivedSeverityTrap, 
		timeStampTrap, 
		additionalTextTrap }
	STATUS     current
	DESCRIPTION 
		"MUX index 1"
	::= { reflectedPowerTrapsPrefix 1 }

reflectedPower2Trap  NOTIFICATION-TYPE
	OBJECTS { eventIdTrap, 
		notificationIdTrap, 
		perceivedSeverityTrap, 
		timeStampTrap, 
		additionalTextTrap }
	STATUS     current
	DESCRIPTION 
		"MUX index 2"
	::= { reflectedPowerTrapsPrefix 2 }

reflectedPower3Trap  NOTIFICATION-TYPE
	OBJECTS { eventIdTrap, 
		notificationIdTrap, 
		perceivedSeverityTrap, 
		timeStampTrap, 
		additionalTextTrap }
	STATUS     current
	DESCRIPTION 
		"MUX index 3"
	::= { reflectedPowerTrapsPrefix 3 }

reflectedPower4Trap  NOTIFICATION-TYPE
	OBJECTS { eventIdTrap, 
		notificationIdTrap, 
		perceivedSeverityTrap, 
		timeStampTrap, 
		additionalTextTrap }
	STATUS     current
	DESCRIPTION 
		"MUX index 4"
	::= { reflectedPowerTrapsPrefix 4 }

reflectedPower5Trap  NOTIFICATION-TYPE
	OBJECTS { eventIdTrap, 
		notificationIdTrap, 
		perceivedSeverityTrap, 
		timeStampTrap, 
		additionalTextTrap }
	STATUS     current
	DESCRIPTION 
		"MUX index 5"
	::= { reflectedPowerTrapsPrefix 5 }

reflectedPower6Trap  NOTIFICATION-TYPE
	OBJECTS { eventIdTrap, 
		notificationIdTrap, 
		perceivedSeverityTrap, 
		timeStampTrap, 
		additionalTextTrap }
	STATUS     current
	DESCRIPTION 
		"MUX index 6"
	::= { reflectedPowerTrapsPrefix 6 }

reflectedPower7Trap  NOTIFICATION-TYPE
	OBJECTS { eventIdTrap, 
		notificationIdTrap, 
		perceivedSeverityTrap, 
		timeStampTrap, 
		additionalTextTrap }
	STATUS     current
	DESCRIPTION 
		"MUX index 7"
	::= { reflectedPowerTrapsPrefix 7 }

reflectedPower8Trap  NOTIFICATION-TYPE
	OBJECTS { eventIdTrap, 
		notificationIdTrap, 
		perceivedSeverityTrap, 
		timeStampTrap, 
		additionalTextTrap }
	STATUS     current
	DESCRIPTION 
		"MUX index 8"
	::= { reflectedPowerTrapsPrefix 8 }

reflectedPower9Trap  NOTIFICATION-TYPE
	OBJECTS { eventIdTrap, 
		notificationIdTrap, 
		perceivedSeverityTrap, 
		timeStampTrap, 
		additionalTextTrap }
	STATUS     current
	DESCRIPTION 
		"MUX index 9"
	::= { reflectedPowerTrapsPrefix 9 }

reflectedPower10Trap  NOTIFICATION-TYPE
	OBJECTS { eventIdTrap, 
		notificationIdTrap, 
		perceivedSeverityTrap, 
		timeStampTrap, 
		additionalTextTrap }
	STATUS     current
	DESCRIPTION 
		"MUX index 10"
	::= { reflectedPowerTrapsPrefix 10 }

reflectedPower11Trap  NOTIFICATION-TYPE
	OBJECTS { eventIdTrap, 
		notificationIdTrap, 
		perceivedSeverityTrap, 
		timeStampTrap, 
		additionalTextTrap }
	STATUS     current
	DESCRIPTION 
		"MUX index 11"
	::= { reflectedPowerTrapsPrefix 11 }

reflectedPower12Trap  NOTIFICATION-TYPE
	OBJECTS { eventIdTrap, 
		notificationIdTrap, 
		perceivedSeverityTrap, 
		timeStampTrap, 
		additionalTextTrap }
	STATUS     current
	DESCRIPTION 
		"MUX index 12"
	::= { reflectedPowerTrapsPrefix 12 }

reflectedPower13Trap  NOTIFICATION-TYPE
	OBJECTS { eventIdTrap, 
		notificationIdTrap, 
		perceivedSeverityTrap, 
		timeStampTrap, 
		additionalTextTrap }
	STATUS     current
	DESCRIPTION 
		"MUX index 13"
	::= { reflectedPowerTrapsPrefix 13 }

reflectedPower14Trap  NOTIFICATION-TYPE
	OBJECTS { eventIdTrap, 
		notificationIdTrap, 
		perceivedSeverityTrap, 
		timeStampTrap, 
		additionalTextTrap }
	STATUS     current
	DESCRIPTION 
		"MUX index 14"
	::= { reflectedPowerTrapsPrefix 14 }

reflectedPower15Trap  NOTIFICATION-TYPE
	OBJECTS { eventIdTrap, 
		notificationIdTrap, 
		perceivedSeverityTrap, 
		timeStampTrap, 
		additionalTextTrap }
	STATUS     current
	DESCRIPTION 
		"MUX index 15"
	::= { reflectedPowerTrapsPrefix 15 }

reflectedPower16Trap  NOTIFICATION-TYPE
	OBJECTS { eventIdTrap, 
		notificationIdTrap, 
		perceivedSeverityTrap, 
		timeStampTrap, 
		additionalTextTrap }
	STATUS     current
	DESCRIPTION 
		"MUX index 16"
	::= { reflectedPowerTrapsPrefix 16 }

reflectedPower17Trap  NOTIFICATION-TYPE
	OBJECTS { eventIdTrap, 
		notificationIdTrap, 
		perceivedSeverityTrap, 
		timeStampTrap, 
		additionalTextTrap }
	STATUS     current
	DESCRIPTION 
		"MUX index 17"
	::= { reflectedPowerTrapsPrefix 17 }

reflectedPower18Trap  NOTIFICATION-TYPE
	OBJECTS { eventIdTrap, 
		notificationIdTrap, 
		perceivedSeverityTrap, 
		timeStampTrap, 
		additionalTextTrap }
	STATUS     current
	DESCRIPTION 
		"MUX index 18"
	::= { reflectedPowerTrapsPrefix 18 }

reflectedPower19Trap  NOTIFICATION-TYPE
	OBJECTS { eventIdTrap, 
		notificationIdTrap, 
		perceivedSeverityTrap, 
		timeStampTrap, 
		additionalTextTrap }
	STATUS     current
	DESCRIPTION 
		"MUX index 19"
	::= { reflectedPowerTrapsPrefix 19 }

reflectedPower20Trap  NOTIFICATION-TYPE
	OBJECTS { eventIdTrap, 
		notificationIdTrap, 
		perceivedSeverityTrap, 
		timeStampTrap, 
		additionalTextTrap }
	STATUS     current
	DESCRIPTION 
		"MUX index 20"
	::= { reflectedPowerTrapsPrefix 20 }

reflectedPower21Trap  NOTIFICATION-TYPE
	OBJECTS { eventIdTrap, 
		notificationIdTrap, 
		perceivedSeverityTrap, 
		timeStampTrap, 
		additionalTextTrap }
	STATUS     current
	DESCRIPTION 
		"MUX index 21"
	::= { reflectedPowerTrapsPrefix 21 }

reflectedPower22Trap  NOTIFICATION-TYPE
	OBJECTS { eventIdTrap, 
		notificationIdTrap, 
		perceivedSeverityTrap, 
		timeStampTrap, 
		additionalTextTrap }
	STATUS     current
	DESCRIPTION 
		"MUX index 22"
	::= { reflectedPowerTrapsPrefix 22 }

reflectedPower23Trap  NOTIFICATION-TYPE
	OBJECTS { eventIdTrap, 
		notificationIdTrap, 
		perceivedSeverityTrap, 
		timeStampTrap, 
		additionalTextTrap }
	STATUS     current
	DESCRIPTION 
		"MUX index 23"
	::= { reflectedPowerTrapsPrefix 23 }

reflectedPower24Trap  NOTIFICATION-TYPE
	OBJECTS { eventIdTrap, 
		notificationIdTrap, 
		perceivedSeverityTrap, 
		timeStampTrap, 
		additionalTextTrap }
	STATUS     current
	DESCRIPTION 
		"MUX index 24"
	::= { reflectedPowerTrapsPrefix 24 }

reflectedPower25Trap  NOTIFICATION-TYPE
	OBJECTS { eventIdTrap, 
		notificationIdTrap, 
		perceivedSeverityTrap, 
		timeStampTrap, 
		additionalTextTrap }
	STATUS     current
	DESCRIPTION 
		"MUX index 25"
	::= { reflectedPowerTrapsPrefix 25 }

reflectedPower26Trap  NOTIFICATION-TYPE
	OBJECTS { eventIdTrap, 
		notificationIdTrap, 
		perceivedSeverityTrap, 
		timeStampTrap, 
		additionalTextTrap }
	STATUS     current
	DESCRIPTION 
		"MUX index 26"
	::= { reflectedPowerTrapsPrefix 26 }

reflectedPower27Trap  NOTIFICATION-TYPE
	OBJECTS { eventIdTrap, 
		notificationIdTrap, 
		perceivedSeverityTrap, 
		timeStampTrap, 
		additionalTextTrap }
	STATUS     current
	DESCRIPTION 
		"MUX index 27"
	::= { reflectedPowerTrapsPrefix 27 }

reflectedPower28Trap  NOTIFICATION-TYPE
	OBJECTS { eventIdTrap, 
		notificationIdTrap, 
		perceivedSeverityTrap, 
		timeStampTrap, 
		additionalTextTrap }
	STATUS     current
	DESCRIPTION 
		"MUX index 28"
	::= { reflectedPowerTrapsPrefix 28 }

reflectedPower29Trap  NOTIFICATION-TYPE
	OBJECTS { eventIdTrap, 
		notificationIdTrap, 
		perceivedSeverityTrap, 
		timeStampTrap, 
		additionalTextTrap }
	STATUS     current
	DESCRIPTION 
		"MUX index 29"
	::= { reflectedPowerTrapsPrefix 29 }

reflectedPower30Trap  NOTIFICATION-TYPE
	OBJECTS { eventIdTrap, 
		notificationIdTrap, 
		perceivedSeverityTrap, 
		timeStampTrap, 
		additionalTextTrap }
	STATUS     current
	DESCRIPTION 
		"MUX index 30"
	::= { reflectedPowerTrapsPrefix 30 }

unlockTS1Trap  NOTIFICATION-TYPE
	OBJECTS { eventIdTrap, 
		notificationIdTrap, 
		perceivedSeverityTrap, 
		timeStampTrap, 
		additionalTextTrap }
	STATUS     current
	DESCRIPTION 
		"MUX index 1"
	::= { unlockTSTrapsPrefix 1 }

unlockTS2Trap  NOTIFICATION-TYPE
	OBJECTS { eventIdTrap, 
		notificationIdTrap, 
		perceivedSeverityTrap, 
		timeStampTrap, 
		additionalTextTrap }
	STATUS     current
	DESCRIPTION 
		"MUX index 2"
	::= { unlockTSTrapsPrefix 2 }

unlockTS3Trap  NOTIFICATION-TYPE
	OBJECTS { eventIdTrap, 
		notificationIdTrap, 
		perceivedSeverityTrap, 
		timeStampTrap, 
		additionalTextTrap }
	STATUS     current
	DESCRIPTION 
		"MUX index 3"
	::= { unlockTSTrapsPrefix 3 }

unlockTS4Trap  NOTIFICATION-TYPE
	OBJECTS { eventIdTrap, 
		notificationIdTrap, 
		perceivedSeverityTrap, 
		timeStampTrap, 
		additionalTextTrap }
	STATUS     current
	DESCRIPTION 
		"MUX index 4"
	::= { unlockTSTrapsPrefix 4 }

unlockTS5Trap  NOTIFICATION-TYPE
	OBJECTS { eventIdTrap, 
		notificationIdTrap, 
		perceivedSeverityTrap, 
		timeStampTrap, 
		additionalTextTrap }
	STATUS     current
	DESCRIPTION 
		"MUX index 5"
	::= { unlockTSTrapsPrefix 5 }

unlockTS6Trap  NOTIFICATION-TYPE
	OBJECTS { eventIdTrap, 
		notificationIdTrap, 
		perceivedSeverityTrap, 
		timeStampTrap, 
		additionalTextTrap }
	STATUS     current
	DESCRIPTION 
		"MUX index 6"
	::= { unlockTSTrapsPrefix 6 }

unlockTS7Trap  NOTIFICATION-TYPE
	OBJECTS { eventIdTrap, 
		notificationIdTrap, 
		perceivedSeverityTrap, 
		timeStampTrap, 
		additionalTextTrap }
	STATUS     current
	DESCRIPTION 
		"MUX index 7"
	::= { unlockTSTrapsPrefix 7 }

unlockTS8Trap  NOTIFICATION-TYPE
	OBJECTS { eventIdTrap, 
		notificationIdTrap, 
		perceivedSeverityTrap, 
		timeStampTrap, 
		additionalTextTrap }
	STATUS     current
	DESCRIPTION 
		"MUX index 8"
	::= { unlockTSTrapsPrefix 8 }

unlockTS9Trap  NOTIFICATION-TYPE
	OBJECTS { eventIdTrap, 
		notificationIdTrap, 
		perceivedSeverityTrap, 
		timeStampTrap, 
		additionalTextTrap }
	STATUS     current
	DESCRIPTION 
		"MUX index 9"
	::= { unlockTSTrapsPrefix 9 }

unlockTS10Trap  NOTIFICATION-TYPE
	OBJECTS { eventIdTrap, 
		notificationIdTrap, 
		perceivedSeverityTrap, 
		timeStampTrap, 
		additionalTextTrap }
	STATUS     current
	DESCRIPTION 
		"MUX index 10"
	::= { unlockTSTrapsPrefix 10 }

unlockTS11Trap  NOTIFICATION-TYPE
	OBJECTS { eventIdTrap, 
		notificationIdTrap, 
		perceivedSeverityTrap, 
		timeStampTrap, 
		additionalTextTrap }
	STATUS     current
	DESCRIPTION 
		"MUX index 11"
	::= { unlockTSTrapsPrefix 11 }

unlockTS12Trap  NOTIFICATION-TYPE
	OBJECTS { eventIdTrap, 
		notificationIdTrap, 
		perceivedSeverityTrap, 
		timeStampTrap, 
		additionalTextTrap }
	STATUS     current
	DESCRIPTION 
		"MUX index 12"
	::= { unlockTSTrapsPrefix 12 }

unlockTS13Trap  NOTIFICATION-TYPE
	OBJECTS { eventIdTrap, 
		notificationIdTrap, 
		perceivedSeverityTrap, 
		timeStampTrap, 
		additionalTextTrap }
	STATUS     current
	DESCRIPTION 
		"MUX index 13"
	::= { unlockTSTrapsPrefix 13 }

unlockTS14Trap  NOTIFICATION-TYPE
	OBJECTS { eventIdTrap, 
		notificationIdTrap, 
		perceivedSeverityTrap, 
		timeStampTrap, 
		additionalTextTrap }
	STATUS     current
	DESCRIPTION 
		"MUX index 14"
	::= { unlockTSTrapsPrefix 14 }

unlockTS15Trap  NOTIFICATION-TYPE
	OBJECTS { eventIdTrap, 
		notificationIdTrap, 
		perceivedSeverityTrap, 
		timeStampTrap, 
		additionalTextTrap }
	STATUS     current
	DESCRIPTION 
		"MUX index 15"
	::= { unlockTSTrapsPrefix 15 }

unlockTS16Trap  NOTIFICATION-TYPE
	OBJECTS { eventIdTrap, 
		notificationIdTrap, 
		perceivedSeverityTrap, 
		timeStampTrap, 
		additionalTextTrap }
	STATUS     current
	DESCRIPTION 
		"MUX index 16"
	::= { unlockTSTrapsPrefix 16 }

unlockTS17Trap  NOTIFICATION-TYPE
	OBJECTS { eventIdTrap, 
		notificationIdTrap, 
		perceivedSeverityTrap, 
		timeStampTrap, 
		additionalTextTrap }
	STATUS     current
	DESCRIPTION 
		"MUX index 17"
	::= { unlockTSTrapsPrefix 17 }

unlockTS18Trap  NOTIFICATION-TYPE
	OBJECTS { eventIdTrap, 
		notificationIdTrap, 
		perceivedSeverityTrap, 
		timeStampTrap, 
		additionalTextTrap }
	STATUS     current
	DESCRIPTION 
		"MUX index 18"
	::= { unlockTSTrapsPrefix 18 }

unlockTS19Trap  NOTIFICATION-TYPE
	OBJECTS { eventIdTrap, 
		notificationIdTrap, 
		perceivedSeverityTrap, 
		timeStampTrap, 
		additionalTextTrap }
	STATUS     current
	DESCRIPTION 
		"MUX index 19"
	::= { unlockTSTrapsPrefix 19 }

unlockTS20Trap  NOTIFICATION-TYPE
	OBJECTS { eventIdTrap, 
		notificationIdTrap, 
		perceivedSeverityTrap, 
		timeStampTrap, 
		additionalTextTrap }
	STATUS     current
	DESCRIPTION 
		"MUX index 20"
	::= { unlockTSTrapsPrefix 20 }

unlockTS21Trap  NOTIFICATION-TYPE
	OBJECTS { eventIdTrap, 
		notificationIdTrap, 
		perceivedSeverityTrap, 
		timeStampTrap, 
		additionalTextTrap }
	STATUS     current
	DESCRIPTION 
		"MUX index 21"
	::= { unlockTSTrapsPrefix 21 }

unlockTS22Trap  NOTIFICATION-TYPE
	OBJECTS { eventIdTrap, 
		notificationIdTrap, 
		perceivedSeverityTrap, 
		timeStampTrap, 
		additionalTextTrap }
	STATUS     current
	DESCRIPTION 
		"MUX index 22"
	::= { unlockTSTrapsPrefix 22 }

unlockTS23Trap  NOTIFICATION-TYPE
	OBJECTS { eventIdTrap, 
		notificationIdTrap, 
		perceivedSeverityTrap, 
		timeStampTrap, 
		additionalTextTrap }
	STATUS     current
	DESCRIPTION 
		"MUX index 23"
	::= { unlockTSTrapsPrefix 23 }

unlockTS24Trap  NOTIFICATION-TYPE
	OBJECTS { eventIdTrap, 
		notificationIdTrap, 
		perceivedSeverityTrap, 
		timeStampTrap, 
		additionalTextTrap }
	STATUS     current
	DESCRIPTION 
		"MUX index 24"
	::= { unlockTSTrapsPrefix 24 }

unlockTS25Trap  NOTIFICATION-TYPE
	OBJECTS { eventIdTrap, 
		notificationIdTrap, 
		perceivedSeverityTrap, 
		timeStampTrap, 
		additionalTextTrap }
	STATUS     current
	DESCRIPTION 
		"MUX index 25"
	::= { unlockTSTrapsPrefix 25 }

unlockTS26Trap  NOTIFICATION-TYPE
	OBJECTS { eventIdTrap, 
		notificationIdTrap, 
		perceivedSeverityTrap, 
		timeStampTrap, 
		additionalTextTrap }
	STATUS     current
	DESCRIPTION 
		"MUX index 26"
	::= { unlockTSTrapsPrefix 26 }

unlockTS27Trap  NOTIFICATION-TYPE
	OBJECTS { eventIdTrap, 
		notificationIdTrap, 
		perceivedSeverityTrap, 
		timeStampTrap, 
		additionalTextTrap }
	STATUS     current
	DESCRIPTION 
		"MUX index 27"
	::= { unlockTSTrapsPrefix 27 }

unlockTS28Trap  NOTIFICATION-TYPE
	OBJECTS { eventIdTrap, 
		notificationIdTrap, 
		perceivedSeverityTrap, 
		timeStampTrap, 
		additionalTextTrap }
	STATUS     current
	DESCRIPTION 
		"MUX index 28"
	::= { unlockTSTrapsPrefix 28 }

unlockTS29Trap  NOTIFICATION-TYPE
	OBJECTS { eventIdTrap, 
		notificationIdTrap, 
		perceivedSeverityTrap, 
		timeStampTrap, 
		additionalTextTrap }
	STATUS     current
	DESCRIPTION 
		"MUX index 29"
	::= { unlockTSTrapsPrefix 29 }

unlockTS30Trap  NOTIFICATION-TYPE
	OBJECTS { eventIdTrap, 
		notificationIdTrap, 
		perceivedSeverityTrap, 
		timeStampTrap, 
		additionalTextTrap }
	STATUS     current
	DESCRIPTION 
		"MUX index 30"
	::= { unlockTSTrapsPrefix 30 }

noInputSignal1Trap  NOTIFICATION-TYPE
	OBJECTS { eventIdTrap, 
		notificationIdTrap, 
		perceivedSeverityTrap, 
		timeStampTrap, 
		additionalTextTrap }
	STATUS     current
	DESCRIPTION 
		"MUX index 1"
	::= { noInputSignalTrapsPrefix 1 }

noInputSignal2Trap  NOTIFICATION-TYPE
	OBJECTS { eventIdTrap, 
		notificationIdTrap, 
		perceivedSeverityTrap, 
		timeStampTrap, 
		additionalTextTrap }
	STATUS     current
	DESCRIPTION 
		"MUX index 2"
	::= { noInputSignalTrapsPrefix 2 }

noInputSignal3Trap  NOTIFICATION-TYPE
	OBJECTS { eventIdTrap, 
		notificationIdTrap, 
		perceivedSeverityTrap, 
		timeStampTrap, 
		additionalTextTrap }
	STATUS     current
	DESCRIPTION 
		"MUX index 3"
	::= { noInputSignalTrapsPrefix 3 }

noInputSignal4Trap  NOTIFICATION-TYPE
	OBJECTS { eventIdTrap, 
		notificationIdTrap, 
		perceivedSeverityTrap, 
		timeStampTrap, 
		additionalTextTrap }
	STATUS     current
	DESCRIPTION 
		"MUX index 4"
	::= { noInputSignalTrapsPrefix 4 }

noInputSignal5Trap  NOTIFICATION-TYPE
	OBJECTS { eventIdTrap, 
		notificationIdTrap, 
		perceivedSeverityTrap, 
		timeStampTrap, 
		additionalTextTrap }
	STATUS     current
	DESCRIPTION 
		"MUX index 5"
	::= { noInputSignalTrapsPrefix 5 }

noInputSignal6Trap  NOTIFICATION-TYPE
	OBJECTS { eventIdTrap, 
		notificationIdTrap, 
		perceivedSeverityTrap, 
		timeStampTrap, 
		additionalTextTrap }
	STATUS     current
	DESCRIPTION 
		"MUX index 6"
	::= { noInputSignalTrapsPrefix 6 }

noInputSignal7Trap  NOTIFICATION-TYPE
	OBJECTS { eventIdTrap, 
		notificationIdTrap, 
		perceivedSeverityTrap, 
		timeStampTrap, 
		additionalTextTrap }
	STATUS     current
	DESCRIPTION 
		"MUX index 7"
	::= { noInputSignalTrapsPrefix 7 }

noInputSignal8Trap  NOTIFICATION-TYPE
	OBJECTS { eventIdTrap, 
		notificationIdTrap, 
		perceivedSeverityTrap, 
		timeStampTrap, 
		additionalTextTrap }
	STATUS     current
	DESCRIPTION 
		"MUX index 8"
	::= { noInputSignalTrapsPrefix 8 }

noInputSignal9Trap  NOTIFICATION-TYPE
	OBJECTS { eventIdTrap, 
		notificationIdTrap, 
		perceivedSeverityTrap, 
		timeStampTrap, 
		additionalTextTrap }
	STATUS     current
	DESCRIPTION 
		"MUX index 9"
	::= { noInputSignalTrapsPrefix 9 }

noInputSignal10Trap  NOTIFICATION-TYPE
	OBJECTS { eventIdTrap, 
		notificationIdTrap, 
		perceivedSeverityTrap, 
		timeStampTrap, 
		additionalTextTrap }
	STATUS     current
	DESCRIPTION 
		"MUX index 10"
	::= { noInputSignalTrapsPrefix 10 }

noInputSignal11Trap  NOTIFICATION-TYPE
	OBJECTS { eventIdTrap, 
		notificationIdTrap, 
		perceivedSeverityTrap, 
		timeStampTrap, 
		additionalTextTrap }
	STATUS     current
	DESCRIPTION 
		"MUX index 11"
	::= { noInputSignalTrapsPrefix 11 }

noInputSignal12Trap  NOTIFICATION-TYPE
	OBJECTS { eventIdTrap, 
		notificationIdTrap, 
		perceivedSeverityTrap, 
		timeStampTrap, 
		additionalTextTrap }
	STATUS     current
	DESCRIPTION 
		"MUX index 12"
	::= { noInputSignalTrapsPrefix 12 }

noInputSignal13Trap  NOTIFICATION-TYPE
	OBJECTS { eventIdTrap, 
		notificationIdTrap, 
		perceivedSeverityTrap, 
		timeStampTrap, 
		additionalTextTrap }
	STATUS     current
	DESCRIPTION 
		"MUX index 13"
	::= { noInputSignalTrapsPrefix 13 }

noInputSignal14Trap  NOTIFICATION-TYPE
	OBJECTS { eventIdTrap, 
		notificationIdTrap, 
		perceivedSeverityTrap, 
		timeStampTrap, 
		additionalTextTrap }
	STATUS     current
	DESCRIPTION 
		"MUX index 14"
	::= { noInputSignalTrapsPrefix 14 }

noInputSignal15Trap  NOTIFICATION-TYPE
	OBJECTS { eventIdTrap, 
		notificationIdTrap, 
		perceivedSeverityTrap, 
		timeStampTrap, 
		additionalTextTrap }
	STATUS     current
	DESCRIPTION 
		"MUX index 15"
	::= { noInputSignalTrapsPrefix 15 }

noInputSignal16Trap  NOTIFICATION-TYPE
	OBJECTS { eventIdTrap, 
		notificationIdTrap, 
		perceivedSeverityTrap, 
		timeStampTrap, 
		additionalTextTrap }
	STATUS     current
	DESCRIPTION 
		"MUX index 16"
	::= { noInputSignalTrapsPrefix 16 }

noInputSignal17Trap  NOTIFICATION-TYPE
	OBJECTS { eventIdTrap, 
		notificationIdTrap, 
		perceivedSeverityTrap, 
		timeStampTrap, 
		additionalTextTrap }
	STATUS     current
	DESCRIPTION 
		"MUX index 17"
	::= { noInputSignalTrapsPrefix 17 }

noInputSignal18Trap  NOTIFICATION-TYPE
	OBJECTS { eventIdTrap, 
		notificationIdTrap, 
		perceivedSeverityTrap, 
		timeStampTrap, 
		additionalTextTrap }
	STATUS     current
	DESCRIPTION 
		"MUX index 18"
	::= { noInputSignalTrapsPrefix 18 }

noInputSignal19Trap  NOTIFICATION-TYPE
	OBJECTS { eventIdTrap, 
		notificationIdTrap, 
		perceivedSeverityTrap, 
		timeStampTrap, 
		additionalTextTrap }
	STATUS     current
	DESCRIPTION 
		"MUX index 19"
	::= { noInputSignalTrapsPrefix 19 }

noInputSignal20Trap  NOTIFICATION-TYPE
	OBJECTS { eventIdTrap, 
		notificationIdTrap, 
		perceivedSeverityTrap, 
		timeStampTrap, 
		additionalTextTrap }
	STATUS     current
	DESCRIPTION 
		"MUX index 20"
	::= { noInputSignalTrapsPrefix 20 }

noInputSignal21Trap  NOTIFICATION-TYPE
	OBJECTS { eventIdTrap, 
		notificationIdTrap, 
		perceivedSeverityTrap, 
		timeStampTrap, 
		additionalTextTrap }
	STATUS     current
	DESCRIPTION 
		"MUX index 21"
	::= { noInputSignalTrapsPrefix 21 }

noInputSignal22Trap  NOTIFICATION-TYPE
	OBJECTS { eventIdTrap, 
		notificationIdTrap, 
		perceivedSeverityTrap, 
		timeStampTrap, 
		additionalTextTrap }
	STATUS     current
	DESCRIPTION 
		"MUX index 22"
	::= { noInputSignalTrapsPrefix 22 }

noInputSignal23Trap  NOTIFICATION-TYPE
	OBJECTS { eventIdTrap, 
		notificationIdTrap, 
		perceivedSeverityTrap, 
		timeStampTrap, 
		additionalTextTrap }
	STATUS     current
	DESCRIPTION 
		"MUX index 23"
	::= { noInputSignalTrapsPrefix 23 }

noInputSignal24Trap  NOTIFICATION-TYPE
	OBJECTS { eventIdTrap, 
		notificationIdTrap, 
		perceivedSeverityTrap, 
		timeStampTrap, 
		additionalTextTrap }
	STATUS     current
	DESCRIPTION 
		"MUX index 24"
	::= { noInputSignalTrapsPrefix 24 }

noInputSignal25Trap  NOTIFICATION-TYPE
	OBJECTS { eventIdTrap, 
		notificationIdTrap, 
		perceivedSeverityTrap, 
		timeStampTrap, 
		additionalTextTrap }
	STATUS     current
	DESCRIPTION 
		"MUX index 25"
	::= { noInputSignalTrapsPrefix 25 }

noInputSignal26Trap  NOTIFICATION-TYPE
	OBJECTS { eventIdTrap, 
		notificationIdTrap, 
		perceivedSeverityTrap, 
		timeStampTrap, 
		additionalTextTrap }
	STATUS     current
	DESCRIPTION 
		"MUX index 26"
	::= { noInputSignalTrapsPrefix 26 }

noInputSignal27Trap  NOTIFICATION-TYPE
	OBJECTS { eventIdTrap, 
		notificationIdTrap, 
		perceivedSeverityTrap, 
		timeStampTrap, 
		additionalTextTrap }
	STATUS     current
	DESCRIPTION 
		"MUX index 27"
	::= { noInputSignalTrapsPrefix 27 }

noInputSignal28Trap  NOTIFICATION-TYPE
	OBJECTS { eventIdTrap, 
		notificationIdTrap, 
		perceivedSeverityTrap, 
		timeStampTrap, 
		additionalTextTrap }
	STATUS     current
	DESCRIPTION 
		"MUX index 28"
	::= { noInputSignalTrapsPrefix 28 }

noInputSignal29Trap  NOTIFICATION-TYPE
	OBJECTS { eventIdTrap, 
		notificationIdTrap, 
		perceivedSeverityTrap, 
		timeStampTrap, 
		additionalTextTrap }
	STATUS     current
	DESCRIPTION 
		"MUX index 29"
	::= { noInputSignalTrapsPrefix 29 }

noInputSignal30Trap  NOTIFICATION-TYPE
	OBJECTS { eventIdTrap, 
		notificationIdTrap, 
		perceivedSeverityTrap, 
		timeStampTrap, 
		additionalTextTrap }
	STATUS     current
	DESCRIPTION 
		"MUX index 30"
	::= { noInputSignalTrapsPrefix 30 }

asi1Error1Trap  NOTIFICATION-TYPE
	OBJECTS { eventIdTrap, 
		notificationIdTrap, 
		perceivedSeverityTrap, 
		timeStampTrap, 
		additionalTextTrap }
	STATUS     current
	DESCRIPTION 
		"MUX index 1"
	::= { asi1ErrorTrapsPrefix 1 }

asi1Error2Trap  NOTIFICATION-TYPE
	OBJECTS { eventIdTrap, 
		notificationIdTrap, 
		perceivedSeverityTrap, 
		timeStampTrap, 
		additionalTextTrap }
	STATUS     current
	DESCRIPTION 
		"MUX index 2"
	::= { asi1ErrorTrapsPrefix 2 }

asi1Error3Trap  NOTIFICATION-TYPE
	OBJECTS { eventIdTrap, 
		notificationIdTrap, 
		perceivedSeverityTrap, 
		timeStampTrap, 
		additionalTextTrap }
	STATUS     current
	DESCRIPTION 
		"MUX index 3"
	::= { asi1ErrorTrapsPrefix 3 }

asi1Error4Trap  NOTIFICATION-TYPE
	OBJECTS { eventIdTrap, 
		notificationIdTrap, 
		perceivedSeverityTrap, 
		timeStampTrap, 
		additionalTextTrap }
	STATUS     current
	DESCRIPTION 
		"MUX index 4"
	::= { asi1ErrorTrapsPrefix 4 }

asi1Error5Trap  NOTIFICATION-TYPE
	OBJECTS { eventIdTrap, 
		notificationIdTrap, 
		perceivedSeverityTrap, 
		timeStampTrap, 
		additionalTextTrap }
	STATUS     current
	DESCRIPTION 
		"MUX index 5"
	::= { asi1ErrorTrapsPrefix 5 }

asi1Error6Trap  NOTIFICATION-TYPE
	OBJECTS { eventIdTrap, 
		notificationIdTrap, 
		perceivedSeverityTrap, 
		timeStampTrap, 
		additionalTextTrap }
	STATUS     current
	DESCRIPTION 
		"MUX index 6"
	::= { asi1ErrorTrapsPrefix 6 }

asi1Error7Trap  NOTIFICATION-TYPE
	OBJECTS { eventIdTrap, 
		notificationIdTrap, 
		perceivedSeverityTrap, 
		timeStampTrap, 
		additionalTextTrap }
	STATUS     current
	DESCRIPTION 
		"MUX index 7"
	::= { asi1ErrorTrapsPrefix 7 }

asi1Error8Trap  NOTIFICATION-TYPE
	OBJECTS { eventIdTrap, 
		notificationIdTrap, 
		perceivedSeverityTrap, 
		timeStampTrap, 
		additionalTextTrap }
	STATUS     current
	DESCRIPTION 
		"MUX index 8"
	::= { asi1ErrorTrapsPrefix 8 }

asi1Error9Trap  NOTIFICATION-TYPE
	OBJECTS { eventIdTrap, 
		notificationIdTrap, 
		perceivedSeverityTrap, 
		timeStampTrap, 
		additionalTextTrap }
	STATUS     current
	DESCRIPTION 
		"MUX index 9"
	::= { asi1ErrorTrapsPrefix 9 }

asi1Error10Trap  NOTIFICATION-TYPE
	OBJECTS { eventIdTrap, 
		notificationIdTrap, 
		perceivedSeverityTrap, 
		timeStampTrap, 
		additionalTextTrap }
	STATUS     current
	DESCRIPTION 
		"MUX index 10"
	::= { asi1ErrorTrapsPrefix 10 }

asi1Error11Trap  NOTIFICATION-TYPE
	OBJECTS { eventIdTrap, 
		notificationIdTrap, 
		perceivedSeverityTrap, 
		timeStampTrap, 
		additionalTextTrap }
	STATUS     current
	DESCRIPTION 
		"MUX index 11"
	::= { asi1ErrorTrapsPrefix 11 }

asi1Error12Trap  NOTIFICATION-TYPE
	OBJECTS { eventIdTrap, 
		notificationIdTrap, 
		perceivedSeverityTrap, 
		timeStampTrap, 
		additionalTextTrap }
	STATUS     current
	DESCRIPTION 
		"MUX index 12"
	::= { asi1ErrorTrapsPrefix 12 }

asi1Error13Trap  NOTIFICATION-TYPE
	OBJECTS { eventIdTrap, 
		notificationIdTrap, 
		perceivedSeverityTrap, 
		timeStampTrap, 
		additionalTextTrap }
	STATUS     current
	DESCRIPTION 
		"MUX index 13"
	::= { asi1ErrorTrapsPrefix 13 }

asi1Error14Trap  NOTIFICATION-TYPE
	OBJECTS { eventIdTrap, 
		notificationIdTrap, 
		perceivedSeverityTrap, 
		timeStampTrap, 
		additionalTextTrap }
	STATUS     current
	DESCRIPTION 
		"MUX index 14"
	::= { asi1ErrorTrapsPrefix 14 }

asi1Error15Trap  NOTIFICATION-TYPE
	OBJECTS { eventIdTrap, 
		notificationIdTrap, 
		perceivedSeverityTrap, 
		timeStampTrap, 
		additionalTextTrap }
	STATUS     current
	DESCRIPTION 
		"MUX index 15"
	::= { asi1ErrorTrapsPrefix 15 }

asi1Error16Trap  NOTIFICATION-TYPE
	OBJECTS { eventIdTrap, 
		notificationIdTrap, 
		perceivedSeverityTrap, 
		timeStampTrap, 
		additionalTextTrap }
	STATUS     current
	DESCRIPTION 
		"MUX index 16"
	::= { asi1ErrorTrapsPrefix 16 }

asi1Error17Trap  NOTIFICATION-TYPE
	OBJECTS { eventIdTrap, 
		notificationIdTrap, 
		perceivedSeverityTrap, 
		timeStampTrap, 
		additionalTextTrap }
	STATUS     current
	DESCRIPTION 
		"MUX index 17"
	::= { asi1ErrorTrapsPrefix 17 }

asi1Error18Trap  NOTIFICATION-TYPE
	OBJECTS { eventIdTrap, 
		notificationIdTrap, 
		perceivedSeverityTrap, 
		timeStampTrap, 
		additionalTextTrap }
	STATUS     current
	DESCRIPTION 
		"MUX index 18"
	::= { asi1ErrorTrapsPrefix 18 }

asi1Error19Trap  NOTIFICATION-TYPE
	OBJECTS { eventIdTrap, 
		notificationIdTrap, 
		perceivedSeverityTrap, 
		timeStampTrap, 
		additionalTextTrap }
	STATUS     current
	DESCRIPTION 
		"MUX index 19"
	::= { asi1ErrorTrapsPrefix 19 }

asi1Error20Trap  NOTIFICATION-TYPE
	OBJECTS { eventIdTrap, 
		notificationIdTrap, 
		perceivedSeverityTrap, 
		timeStampTrap, 
		additionalTextTrap }
	STATUS     current
	DESCRIPTION 
		"MUX index 20"
	::= { asi1ErrorTrapsPrefix 20 }

asi1Error21Trap  NOTIFICATION-TYPE
	OBJECTS { eventIdTrap, 
		notificationIdTrap, 
		perceivedSeverityTrap, 
		timeStampTrap, 
		additionalTextTrap }
	STATUS     current
	DESCRIPTION 
		"MUX index 21"
	::= { asi1ErrorTrapsPrefix 21 }

asi1Error22Trap  NOTIFICATION-TYPE
	OBJECTS { eventIdTrap, 
		notificationIdTrap, 
		perceivedSeverityTrap, 
		timeStampTrap, 
		additionalTextTrap }
	STATUS     current
	DESCRIPTION 
		"MUX index 22"
	::= { asi1ErrorTrapsPrefix 22 }

asi1Error23Trap  NOTIFICATION-TYPE
	OBJECTS { eventIdTrap, 
		notificationIdTrap, 
		perceivedSeverityTrap, 
		timeStampTrap, 
		additionalTextTrap }
	STATUS     current
	DESCRIPTION 
		"MUX index 23"
	::= { asi1ErrorTrapsPrefix 23 }

asi1Error24Trap  NOTIFICATION-TYPE
	OBJECTS { eventIdTrap, 
		notificationIdTrap, 
		perceivedSeverityTrap, 
		timeStampTrap, 
		additionalTextTrap }
	STATUS     current
	DESCRIPTION 
		"MUX index 24"
	::= { asi1ErrorTrapsPrefix 24 }

asi1Error25Trap  NOTIFICATION-TYPE
	OBJECTS { eventIdTrap, 
		notificationIdTrap, 
		perceivedSeverityTrap, 
		timeStampTrap, 
		additionalTextTrap }
	STATUS     current
	DESCRIPTION 
		"MUX index 25"
	::= { asi1ErrorTrapsPrefix 25 }

asi1Error26Trap  NOTIFICATION-TYPE
	OBJECTS { eventIdTrap, 
		notificationIdTrap, 
		perceivedSeverityTrap, 
		timeStampTrap, 
		additionalTextTrap }
	STATUS     current
	DESCRIPTION 
		"MUX index 26"
	::= { asi1ErrorTrapsPrefix 26 }

asi1Error27Trap  NOTIFICATION-TYPE
	OBJECTS { eventIdTrap, 
		notificationIdTrap, 
		perceivedSeverityTrap, 
		timeStampTrap, 
		additionalTextTrap }
	STATUS     current
	DESCRIPTION 
		"MUX index 27"
	::= { asi1ErrorTrapsPrefix 27 }

asi1Error28Trap  NOTIFICATION-TYPE
	OBJECTS { eventIdTrap, 
		notificationIdTrap, 
		perceivedSeverityTrap, 
		timeStampTrap, 
		additionalTextTrap }
	STATUS     current
	DESCRIPTION 
		"MUX index 28"
	::= { asi1ErrorTrapsPrefix 28 }

asi1Error29Trap  NOTIFICATION-TYPE
	OBJECTS { eventIdTrap, 
		notificationIdTrap, 
		perceivedSeverityTrap, 
		timeStampTrap, 
		additionalTextTrap }
	STATUS     current
	DESCRIPTION 
		"MUX index 29"
	::= { asi1ErrorTrapsPrefix 29 }

asi1Error30Trap  NOTIFICATION-TYPE
	OBJECTS { eventIdTrap, 
		notificationIdTrap, 
		perceivedSeverityTrap, 
		timeStampTrap, 
		additionalTextTrap }
	STATUS     current
	DESCRIPTION 
		"MUX index 30"
	::= { asi1ErrorTrapsPrefix 30 }

mipError1Trap  NOTIFICATION-TYPE
	OBJECTS { eventIdTrap, 
		notificationIdTrap, 
		perceivedSeverityTrap, 
		timeStampTrap, 
		additionalTextTrap }
	STATUS     current
	DESCRIPTION 
		"MUX index 1"
	::= { mipErrorTrapsPrefix 1 }

mipError2Trap  NOTIFICATION-TYPE
	OBJECTS { eventIdTrap, 
		notificationIdTrap, 
		perceivedSeverityTrap, 
		timeStampTrap, 
		additionalTextTrap }
	STATUS     current
	DESCRIPTION 
		"MUX index 2"
	::= { mipErrorTrapsPrefix 2 }

mipError3Trap  NOTIFICATION-TYPE
	OBJECTS { eventIdTrap, 
		notificationIdTrap, 
		perceivedSeverityTrap, 
		timeStampTrap, 
		additionalTextTrap }
	STATUS     current
	DESCRIPTION 
		"MUX index 3"
	::= { mipErrorTrapsPrefix 3 }

mipError4Trap  NOTIFICATION-TYPE
	OBJECTS { eventIdTrap, 
		notificationIdTrap, 
		perceivedSeverityTrap, 
		timeStampTrap, 
		additionalTextTrap }
	STATUS     current
	DESCRIPTION 
		"MUX index 4"
	::= { mipErrorTrapsPrefix 4 }

mipError5Trap  NOTIFICATION-TYPE
	OBJECTS { eventIdTrap, 
		notificationIdTrap, 
		perceivedSeverityTrap, 
		timeStampTrap, 
		additionalTextTrap }
	STATUS     current
	DESCRIPTION 
		"MUX index 5"
	::= { mipErrorTrapsPrefix 5 }

mipError6Trap  NOTIFICATION-TYPE
	OBJECTS { eventIdTrap, 
		notificationIdTrap, 
		perceivedSeverityTrap, 
		timeStampTrap, 
		additionalTextTrap }
	STATUS     current
	DESCRIPTION 
		"MUX index 6"
	::= { mipErrorTrapsPrefix 6 }

mipError7Trap  NOTIFICATION-TYPE
	OBJECTS { eventIdTrap, 
		notificationIdTrap, 
		perceivedSeverityTrap, 
		timeStampTrap, 
		additionalTextTrap }
	STATUS     current
	DESCRIPTION 
		"MUX index 7"
	::= { mipErrorTrapsPrefix 7 }

mipError8Trap  NOTIFICATION-TYPE
	OBJECTS { eventIdTrap, 
		notificationIdTrap, 
		perceivedSeverityTrap, 
		timeStampTrap, 
		additionalTextTrap }
	STATUS     current
	DESCRIPTION 
		"MUX index 8"
	::= { mipErrorTrapsPrefix 8 }

mipError9Trap  NOTIFICATION-TYPE
	OBJECTS { eventIdTrap, 
		notificationIdTrap, 
		perceivedSeverityTrap, 
		timeStampTrap, 
		additionalTextTrap }
	STATUS     current
	DESCRIPTION 
		"MUX index 9"
	::= { mipErrorTrapsPrefix 9 }

mipError10Trap  NOTIFICATION-TYPE
	OBJECTS { eventIdTrap, 
		notificationIdTrap, 
		perceivedSeverityTrap, 
		timeStampTrap, 
		additionalTextTrap }
	STATUS     current
	DESCRIPTION 
		"MUX index 10"
	::= { mipErrorTrapsPrefix 10 }

mipError11Trap  NOTIFICATION-TYPE
	OBJECTS { eventIdTrap, 
		notificationIdTrap, 
		perceivedSeverityTrap, 
		timeStampTrap, 
		additionalTextTrap }
	STATUS     current
	DESCRIPTION 
		"MUX index 11"
	::= { mipErrorTrapsPrefix 11 }

mipError12Trap  NOTIFICATION-TYPE
	OBJECTS { eventIdTrap, 
		notificationIdTrap, 
		perceivedSeverityTrap, 
		timeStampTrap, 
		additionalTextTrap }
	STATUS     current
	DESCRIPTION 
		"MUX index 12"
	::= { mipErrorTrapsPrefix 12 }

mipError13Trap  NOTIFICATION-TYPE
	OBJECTS { eventIdTrap, 
		notificationIdTrap, 
		perceivedSeverityTrap, 
		timeStampTrap, 
		additionalTextTrap }
	STATUS     current
	DESCRIPTION 
		"MUX index 13"
	::= { mipErrorTrapsPrefix 13 }

mipError14Trap  NOTIFICATION-TYPE
	OBJECTS { eventIdTrap, 
		notificationIdTrap, 
		perceivedSeverityTrap, 
		timeStampTrap, 
		additionalTextTrap }
	STATUS     current
	DESCRIPTION 
		"MUX index 14"
	::= { mipErrorTrapsPrefix 14 }

mipError15Trap  NOTIFICATION-TYPE
	OBJECTS { eventIdTrap, 
		notificationIdTrap, 
		perceivedSeverityTrap, 
		timeStampTrap, 
		additionalTextTrap }
	STATUS     current
	DESCRIPTION 
		"MUX index 15"
	::= { mipErrorTrapsPrefix 15 }

mipError16Trap  NOTIFICATION-TYPE
	OBJECTS { eventIdTrap, 
		notificationIdTrap, 
		perceivedSeverityTrap, 
		timeStampTrap, 
		additionalTextTrap }
	STATUS     current
	DESCRIPTION 
		"MUX index 16"
	::= { mipErrorTrapsPrefix 16 }

mipError17Trap  NOTIFICATION-TYPE
	OBJECTS { eventIdTrap, 
		notificationIdTrap, 
		perceivedSeverityTrap, 
		timeStampTrap, 
		additionalTextTrap }
	STATUS     current
	DESCRIPTION 
		"MUX index 17"
	::= { mipErrorTrapsPrefix 17 }

mipError18Trap  NOTIFICATION-TYPE
	OBJECTS { eventIdTrap, 
		notificationIdTrap, 
		perceivedSeverityTrap, 
		timeStampTrap, 
		additionalTextTrap }
	STATUS     current
	DESCRIPTION 
		"MUX index 18"
	::= { mipErrorTrapsPrefix 18 }

mipError19Trap  NOTIFICATION-TYPE
	OBJECTS { eventIdTrap, 
		notificationIdTrap, 
		perceivedSeverityTrap, 
		timeStampTrap, 
		additionalTextTrap }
	STATUS     current
	DESCRIPTION 
		"MUX index 19"
	::= { mipErrorTrapsPrefix 19 }

mipError20Trap  NOTIFICATION-TYPE
	OBJECTS { eventIdTrap, 
		notificationIdTrap, 
		perceivedSeverityTrap, 
		timeStampTrap, 
		additionalTextTrap }
	STATUS     current
	DESCRIPTION 
		"MUX index 20"
	::= { mipErrorTrapsPrefix 20 }

mipError21Trap  NOTIFICATION-TYPE
	OBJECTS { eventIdTrap, 
		notificationIdTrap, 
		perceivedSeverityTrap, 
		timeStampTrap, 
		additionalTextTrap }
	STATUS     current
	DESCRIPTION 
		"MUX index 21"
	::= { mipErrorTrapsPrefix 21 }

mipError22Trap  NOTIFICATION-TYPE
	OBJECTS { eventIdTrap, 
		notificationIdTrap, 
		perceivedSeverityTrap, 
		timeStampTrap, 
		additionalTextTrap }
	STATUS     current
	DESCRIPTION 
		"MUX index 22"
	::= { mipErrorTrapsPrefix 22 }

mipError23Trap  NOTIFICATION-TYPE
	OBJECTS { eventIdTrap, 
		notificationIdTrap, 
		perceivedSeverityTrap, 
		timeStampTrap, 
		additionalTextTrap }
	STATUS     current
	DESCRIPTION 
		"MUX index 23"
	::= { mipErrorTrapsPrefix 23 }

mipError24Trap  NOTIFICATION-TYPE
	OBJECTS { eventIdTrap, 
		notificationIdTrap, 
		perceivedSeverityTrap, 
		timeStampTrap, 
		additionalTextTrap }
	STATUS     current
	DESCRIPTION 
		"MUX index 24"
	::= { mipErrorTrapsPrefix 24 }

mipError25Trap  NOTIFICATION-TYPE
	OBJECTS { eventIdTrap, 
		notificationIdTrap, 
		perceivedSeverityTrap, 
		timeStampTrap, 
		additionalTextTrap }
	STATUS     current
	DESCRIPTION 
		"MUX index 25"
	::= { mipErrorTrapsPrefix 25 }

mipError26Trap  NOTIFICATION-TYPE
	OBJECTS { eventIdTrap, 
		notificationIdTrap, 
		perceivedSeverityTrap, 
		timeStampTrap, 
		additionalTextTrap }
	STATUS     current
	DESCRIPTION 
		"MUX index 26"
	::= { mipErrorTrapsPrefix 26 }

mipError27Trap  NOTIFICATION-TYPE
	OBJECTS { eventIdTrap, 
		notificationIdTrap, 
		perceivedSeverityTrap, 
		timeStampTrap, 
		additionalTextTrap }
	STATUS     current
	DESCRIPTION 
		"MUX index 27"
	::= { mipErrorTrapsPrefix 27 }

mipError28Trap  NOTIFICATION-TYPE
	OBJECTS { eventIdTrap, 
		notificationIdTrap, 
		perceivedSeverityTrap, 
		timeStampTrap, 
		additionalTextTrap }
	STATUS     current
	DESCRIPTION 
		"MUX index 28"
	::= { mipErrorTrapsPrefix 28 }

mipError29Trap  NOTIFICATION-TYPE
	OBJECTS { eventIdTrap, 
		notificationIdTrap, 
		perceivedSeverityTrap, 
		timeStampTrap, 
		additionalTextTrap }
	STATUS     current
	DESCRIPTION 
		"MUX index 29"
	::= { mipErrorTrapsPrefix 29 }

mipError30Trap  NOTIFICATION-TYPE
	OBJECTS { eventIdTrap, 
		notificationIdTrap, 
		perceivedSeverityTrap, 
		timeStampTrap, 
		additionalTextTrap }
	STATUS     current
	DESCRIPTION 
		"MUX index 30"
	::= { mipErrorTrapsPrefix 30 }

pps1Trap  NOTIFICATION-TYPE
	OBJECTS { eventIdTrap, 
		notificationIdTrap, 
		perceivedSeverityTrap, 
		timeStampTrap, 
		additionalTextTrap }
	STATUS     current
	DESCRIPTION 
		"MUX index 1"
	::= { ppsTrapsPrefix 1 }

pps2Trap  NOTIFICATION-TYPE
	OBJECTS { eventIdTrap, 
		notificationIdTrap, 
		perceivedSeverityTrap, 
		timeStampTrap, 
		additionalTextTrap }
	STATUS     current
	DESCRIPTION 
		"MUX index 2"
	::= { ppsTrapsPrefix 2 }

pps3Trap  NOTIFICATION-TYPE
	OBJECTS { eventIdTrap, 
		notificationIdTrap, 
		perceivedSeverityTrap, 
		timeStampTrap, 
		additionalTextTrap }
	STATUS     current
	DESCRIPTION 
		"MUX index 3"
	::= { ppsTrapsPrefix 3 }

pps4Trap  NOTIFICATION-TYPE
	OBJECTS { eventIdTrap, 
		notificationIdTrap, 
		perceivedSeverityTrap, 
		timeStampTrap, 
		additionalTextTrap }
	STATUS     current
	DESCRIPTION 
		"MUX index 4"
	::= { ppsTrapsPrefix 4 }

pps5Trap  NOTIFICATION-TYPE
	OBJECTS { eventIdTrap, 
		notificationIdTrap, 
		perceivedSeverityTrap, 
		timeStampTrap, 
		additionalTextTrap }
	STATUS     current
	DESCRIPTION 
		"MUX index 5"
	::= { ppsTrapsPrefix 5 }

pps6Trap  NOTIFICATION-TYPE
	OBJECTS { eventIdTrap, 
		notificationIdTrap, 
		perceivedSeverityTrap, 
		timeStampTrap, 
		additionalTextTrap }
	STATUS     current
	DESCRIPTION 
		"MUX index 6"
	::= { ppsTrapsPrefix 6 }

pps7Trap  NOTIFICATION-TYPE
	OBJECTS { eventIdTrap, 
		notificationIdTrap, 
		perceivedSeverityTrap, 
		timeStampTrap, 
		additionalTextTrap }
	STATUS     current
	DESCRIPTION 
		"MUX index 7"
	::= { ppsTrapsPrefix 7 }

pps8Trap  NOTIFICATION-TYPE
	OBJECTS { eventIdTrap, 
		notificationIdTrap, 
		perceivedSeverityTrap, 
		timeStampTrap, 
		additionalTextTrap }
	STATUS     current
	DESCRIPTION 
		"MUX index 8"
	::= { ppsTrapsPrefix 8 }

pps9Trap  NOTIFICATION-TYPE
	OBJECTS { eventIdTrap, 
		notificationIdTrap, 
		perceivedSeverityTrap, 
		timeStampTrap, 
		additionalTextTrap }
	STATUS     current
	DESCRIPTION 
		"MUX index 9"
	::= { ppsTrapsPrefix 9 }

pps10Trap  NOTIFICATION-TYPE
	OBJECTS { eventIdTrap, 
		notificationIdTrap, 
		perceivedSeverityTrap, 
		timeStampTrap, 
		additionalTextTrap }
	STATUS     current
	DESCRIPTION 
		"MUX index 10"
	::= { ppsTrapsPrefix 10 }

pps11Trap  NOTIFICATION-TYPE
	OBJECTS { eventIdTrap, 
		notificationIdTrap, 
		perceivedSeverityTrap, 
		timeStampTrap, 
		additionalTextTrap }
	STATUS     current
	DESCRIPTION 
		"MUX index 11"
	::= { ppsTrapsPrefix 11 }

pps12Trap  NOTIFICATION-TYPE
	OBJECTS { eventIdTrap, 
		notificationIdTrap, 
		perceivedSeverityTrap, 
		timeStampTrap, 
		additionalTextTrap }
	STATUS     current
	DESCRIPTION 
		"MUX index 12"
	::= { ppsTrapsPrefix 12 }

pps13Trap  NOTIFICATION-TYPE
	OBJECTS { eventIdTrap, 
		notificationIdTrap, 
		perceivedSeverityTrap, 
		timeStampTrap, 
		additionalTextTrap }
	STATUS     current
	DESCRIPTION 
		"MUX index 13"
	::= { ppsTrapsPrefix 13 }

pps14Trap  NOTIFICATION-TYPE
	OBJECTS { eventIdTrap, 
		notificationIdTrap, 
		perceivedSeverityTrap, 
		timeStampTrap, 
		additionalTextTrap }
	STATUS     current
	DESCRIPTION 
		"MUX index 14"
	::= { ppsTrapsPrefix 14 }

pps15Trap  NOTIFICATION-TYPE
	OBJECTS { eventIdTrap, 
		notificationIdTrap, 
		perceivedSeverityTrap, 
		timeStampTrap, 
		additionalTextTrap }
	STATUS     current
	DESCRIPTION 
		"MUX index 15"
	::= { ppsTrapsPrefix 15 }

pps16Trap  NOTIFICATION-TYPE
	OBJECTS { eventIdTrap, 
		notificationIdTrap, 
		perceivedSeverityTrap, 
		timeStampTrap, 
		additionalTextTrap }
	STATUS     current
	DESCRIPTION 
		"MUX index 16"
	::= { ppsTrapsPrefix 16 }

pps17Trap  NOTIFICATION-TYPE
	OBJECTS { eventIdTrap, 
		notificationIdTrap, 
		perceivedSeverityTrap, 
		timeStampTrap, 
		additionalTextTrap }
	STATUS     current
	DESCRIPTION 
		"MUX index 17"
	::= { ppsTrapsPrefix 17 }

pps18Trap  NOTIFICATION-TYPE
	OBJECTS { eventIdTrap, 
		notificationIdTrap, 
		perceivedSeverityTrap, 
		timeStampTrap, 
		additionalTextTrap }
	STATUS     current
	DESCRIPTION 
		"MUX index 18"
	::= { ppsTrapsPrefix 18 }

pps19Trap  NOTIFICATION-TYPE
	OBJECTS { eventIdTrap, 
		notificationIdTrap, 
		perceivedSeverityTrap, 
		timeStampTrap, 
		additionalTextTrap }
	STATUS     current
	DESCRIPTION 
		"MUX index 19"
	::= { ppsTrapsPrefix 19 }

pps20Trap  NOTIFICATION-TYPE
	OBJECTS { eventIdTrap, 
		notificationIdTrap, 
		perceivedSeverityTrap, 
		timeStampTrap, 
		additionalTextTrap }
	STATUS     current
	DESCRIPTION 
		"MUX index 20"
	::= { ppsTrapsPrefix 20 }

pps21Trap  NOTIFICATION-TYPE
	OBJECTS { eventIdTrap, 
		notificationIdTrap, 
		perceivedSeverityTrap, 
		timeStampTrap, 
		additionalTextTrap }
	STATUS     current
	DESCRIPTION 
		"MUX index 21"
	::= { ppsTrapsPrefix 21 }

pps22Trap  NOTIFICATION-TYPE
	OBJECTS { eventIdTrap, 
		notificationIdTrap, 
		perceivedSeverityTrap, 
		timeStampTrap, 
		additionalTextTrap }
	STATUS     current
	DESCRIPTION 
		"MUX index 22"
	::= { ppsTrapsPrefix 22 }

pps23Trap  NOTIFICATION-TYPE
	OBJECTS { eventIdTrap, 
		notificationIdTrap, 
		perceivedSeverityTrap, 
		timeStampTrap, 
		additionalTextTrap }
	STATUS     current
	DESCRIPTION 
		"MUX index 23"
	::= { ppsTrapsPrefix 23 }

pps24Trap  NOTIFICATION-TYPE
	OBJECTS { eventIdTrap, 
		notificationIdTrap, 
		perceivedSeverityTrap, 
		timeStampTrap, 
		additionalTextTrap }
	STATUS     current
	DESCRIPTION 
		"MUX index 24"
	::= { ppsTrapsPrefix 24 }

pps25Trap  NOTIFICATION-TYPE
	OBJECTS { eventIdTrap, 
		notificationIdTrap, 
		perceivedSeverityTrap, 
		timeStampTrap, 
		additionalTextTrap }
	STATUS     current
	DESCRIPTION 
		"MUX index 25"
	::= { ppsTrapsPrefix 25 }

pps26Trap  NOTIFICATION-TYPE
	OBJECTS { eventIdTrap, 
		notificationIdTrap, 
		perceivedSeverityTrap, 
		timeStampTrap, 
		additionalTextTrap }
	STATUS     current
	DESCRIPTION 
		"MUX index 26"
	::= { ppsTrapsPrefix 26 }

pps27Trap  NOTIFICATION-TYPE
	OBJECTS { eventIdTrap, 
		notificationIdTrap, 
		perceivedSeverityTrap, 
		timeStampTrap, 
		additionalTextTrap }
	STATUS     current
	DESCRIPTION 
		"MUX index 27"
	::= { ppsTrapsPrefix 27 }

pps28Trap  NOTIFICATION-TYPE
	OBJECTS { eventIdTrap, 
		notificationIdTrap, 
		perceivedSeverityTrap, 
		timeStampTrap, 
		additionalTextTrap }
	STATUS     current
	DESCRIPTION 
		"MUX index 28"
	::= { ppsTrapsPrefix 28 }

pps29Trap  NOTIFICATION-TYPE
	OBJECTS { eventIdTrap, 
		notificationIdTrap, 
		perceivedSeverityTrap, 
		timeStampTrap, 
		additionalTextTrap }
	STATUS     current
	DESCRIPTION 
		"MUX index 29"
	::= { ppsTrapsPrefix 29 }

pps30Trap  NOTIFICATION-TYPE
	OBJECTS { eventIdTrap, 
		notificationIdTrap, 
		perceivedSeverityTrap, 
		timeStampTrap, 
		additionalTextTrap }
	STATUS     current
	DESCRIPTION 
		"MUX index 30"
	::= { ppsTrapsPrefix 30 }

iFDVBTSignal1Trap  NOTIFICATION-TYPE
	OBJECTS { eventIdTrap, 
		notificationIdTrap, 
		perceivedSeverityTrap, 
		timeStampTrap, 
		additionalTextTrap }
	STATUS     current
	DESCRIPTION 
		"MUX index 1"
	::= { iFDVBTSignalTrapsPrefix 1 }

iFDVBTSignal2Trap  NOTIFICATION-TYPE
	OBJECTS { eventIdTrap, 
		notificationIdTrap, 
		perceivedSeverityTrap, 
		timeStampTrap, 
		additionalTextTrap }
	STATUS     current
	DESCRIPTION 
		"MUX index 2"
	::= { iFDVBTSignalTrapsPrefix 2 }

iFDVBTSignal3Trap  NOTIFICATION-TYPE
	OBJECTS { eventIdTrap, 
		notificationIdTrap, 
		perceivedSeverityTrap, 
		timeStampTrap, 
		additionalTextTrap }
	STATUS     current
	DESCRIPTION 
		"MUX index 3"
	::= { iFDVBTSignalTrapsPrefix 3 }

iFDVBTSignal4Trap  NOTIFICATION-TYPE
	OBJECTS { eventIdTrap, 
		notificationIdTrap, 
		perceivedSeverityTrap, 
		timeStampTrap, 
		additionalTextTrap }
	STATUS     current
	DESCRIPTION 
		"MUX index 4"
	::= { iFDVBTSignalTrapsPrefix 4 }

iFDVBTSignal5Trap  NOTIFICATION-TYPE
	OBJECTS { eventIdTrap, 
		notificationIdTrap, 
		perceivedSeverityTrap, 
		timeStampTrap, 
		additionalTextTrap }
	STATUS     current
	DESCRIPTION 
		"MUX index 5"
	::= { iFDVBTSignalTrapsPrefix 5 }

iFDVBTSignal6Trap  NOTIFICATION-TYPE
	OBJECTS { eventIdTrap, 
		notificationIdTrap, 
		perceivedSeverityTrap, 
		timeStampTrap, 
		additionalTextTrap }
	STATUS     current
	DESCRIPTION 
		"MUX index 6"
	::= { iFDVBTSignalTrapsPrefix 6 }

iFDVBTSignal7Trap  NOTIFICATION-TYPE
	OBJECTS { eventIdTrap, 
		notificationIdTrap, 
		perceivedSeverityTrap, 
		timeStampTrap, 
		additionalTextTrap }
	STATUS     current
	DESCRIPTION 
		"MUX index 7"
	::= { iFDVBTSignalTrapsPrefix 7 }

iFDVBTSignal8Trap  NOTIFICATION-TYPE
	OBJECTS { eventIdTrap, 
		notificationIdTrap, 
		perceivedSeverityTrap, 
		timeStampTrap, 
		additionalTextTrap }
	STATUS     current
	DESCRIPTION 
		"MUX index 8"
	::= { iFDVBTSignalTrapsPrefix 8 }

iFDVBTSignal9Trap  NOTIFICATION-TYPE
	OBJECTS { eventIdTrap, 
		notificationIdTrap, 
		perceivedSeverityTrap, 
		timeStampTrap, 
		additionalTextTrap }
	STATUS     current
	DESCRIPTION 
		"MUX index 9"
	::= { iFDVBTSignalTrapsPrefix 9 }

iFDVBTSignal10Trap  NOTIFICATION-TYPE
	OBJECTS { eventIdTrap, 
		notificationIdTrap, 
		perceivedSeverityTrap, 
		timeStampTrap, 
		additionalTextTrap }
	STATUS     current
	DESCRIPTION 
		"MUX index 10"
	::= { iFDVBTSignalTrapsPrefix 10 }

iFDVBTSignal11Trap  NOTIFICATION-TYPE
	OBJECTS { eventIdTrap, 
		notificationIdTrap, 
		perceivedSeverityTrap, 
		timeStampTrap, 
		additionalTextTrap }
	STATUS     current
	DESCRIPTION 
		"MUX index 11"
	::= { iFDVBTSignalTrapsPrefix 11 }

iFDVBTSignal12Trap  NOTIFICATION-TYPE
	OBJECTS { eventIdTrap, 
		notificationIdTrap, 
		perceivedSeverityTrap, 
		timeStampTrap, 
		additionalTextTrap }
	STATUS     current
	DESCRIPTION 
		"MUX index 12"
	::= { iFDVBTSignalTrapsPrefix 12 }

iFDVBTSignal13Trap  NOTIFICATION-TYPE
	OBJECTS { eventIdTrap, 
		notificationIdTrap, 
		perceivedSeverityTrap, 
		timeStampTrap, 
		additionalTextTrap }
	STATUS     current
	DESCRIPTION 
		"MUX index 13"
	::= { iFDVBTSignalTrapsPrefix 13 }

iFDVBTSignal14Trap  NOTIFICATION-TYPE
	OBJECTS { eventIdTrap, 
		notificationIdTrap, 
		perceivedSeverityTrap, 
		timeStampTrap, 
		additionalTextTrap }
	STATUS     current
	DESCRIPTION 
		"MUX index 14"
	::= { iFDVBTSignalTrapsPrefix 14 }

iFDVBTSignal15Trap  NOTIFICATION-TYPE
	OBJECTS { eventIdTrap, 
		notificationIdTrap, 
		perceivedSeverityTrap, 
		timeStampTrap, 
		additionalTextTrap }
	STATUS     current
	DESCRIPTION 
		"MUX index 15"
	::= { iFDVBTSignalTrapsPrefix 15 }

iFDVBTSignal16Trap  NOTIFICATION-TYPE
	OBJECTS { eventIdTrap, 
		notificationIdTrap, 
		perceivedSeverityTrap, 
		timeStampTrap, 
		additionalTextTrap }
	STATUS     current
	DESCRIPTION 
		"MUX index 16"
	::= { iFDVBTSignalTrapsPrefix 16 }

iFDVBTSignal17Trap  NOTIFICATION-TYPE
	OBJECTS { eventIdTrap, 
		notificationIdTrap, 
		perceivedSeverityTrap, 
		timeStampTrap, 
		additionalTextTrap }
	STATUS     current
	DESCRIPTION 
		"MUX index 17"
	::= { iFDVBTSignalTrapsPrefix 17 }

iFDVBTSignal18Trap  NOTIFICATION-TYPE
	OBJECTS { eventIdTrap, 
		notificationIdTrap, 
		perceivedSeverityTrap, 
		timeStampTrap, 
		additionalTextTrap }
	STATUS     current
	DESCRIPTION 
		"MUX index 18"
	::= { iFDVBTSignalTrapsPrefix 18 }

iFDVBTSignal19Trap  NOTIFICATION-TYPE
	OBJECTS { eventIdTrap, 
		notificationIdTrap, 
		perceivedSeverityTrap, 
		timeStampTrap, 
		additionalTextTrap }
	STATUS     current
	DESCRIPTION 
		"MUX index 19"
	::= { iFDVBTSignalTrapsPrefix 19 }

iFDVBTSignal20Trap  NOTIFICATION-TYPE
	OBJECTS { eventIdTrap, 
		notificationIdTrap, 
		perceivedSeverityTrap, 
		timeStampTrap, 
		additionalTextTrap }
	STATUS     current
	DESCRIPTION 
		"MUX index 20"
	::= { iFDVBTSignalTrapsPrefix 20 }

iFDVBTSignal21Trap  NOTIFICATION-TYPE
	OBJECTS { eventIdTrap, 
		notificationIdTrap, 
		perceivedSeverityTrap, 
		timeStampTrap, 
		additionalTextTrap }
	STATUS     current
	DESCRIPTION 
		"MUX index 21"
	::= { iFDVBTSignalTrapsPrefix 21 }

iFDVBTSignal22Trap  NOTIFICATION-TYPE
	OBJECTS { eventIdTrap, 
		notificationIdTrap, 
		perceivedSeverityTrap, 
		timeStampTrap, 
		additionalTextTrap }
	STATUS     current
	DESCRIPTION 
		"MUX index 22"
	::= { iFDVBTSignalTrapsPrefix 22 }

iFDVBTSignal23Trap  NOTIFICATION-TYPE
	OBJECTS { eventIdTrap, 
		notificationIdTrap, 
		perceivedSeverityTrap, 
		timeStampTrap, 
		additionalTextTrap }
	STATUS     current
	DESCRIPTION 
		"MUX index 23"
	::= { iFDVBTSignalTrapsPrefix 23 }

iFDVBTSignal24Trap  NOTIFICATION-TYPE
	OBJECTS { eventIdTrap, 
		notificationIdTrap, 
		perceivedSeverityTrap, 
		timeStampTrap, 
		additionalTextTrap }
	STATUS     current
	DESCRIPTION 
		"MUX index 24"
	::= { iFDVBTSignalTrapsPrefix 24 }

iFDVBTSignal25Trap  NOTIFICATION-TYPE
	OBJECTS { eventIdTrap, 
		notificationIdTrap, 
		perceivedSeverityTrap, 
		timeStampTrap, 
		additionalTextTrap }
	STATUS     current
	DESCRIPTION 
		"MUX index 25"
	::= { iFDVBTSignalTrapsPrefix 25 }

iFDVBTSignal26Trap  NOTIFICATION-TYPE
	OBJECTS { eventIdTrap, 
		notificationIdTrap, 
		perceivedSeverityTrap, 
		timeStampTrap, 
		additionalTextTrap }
	STATUS     current
	DESCRIPTION 
		"MUX index 26"
	::= { iFDVBTSignalTrapsPrefix 26 }

iFDVBTSignal27Trap  NOTIFICATION-TYPE
	OBJECTS { eventIdTrap, 
		notificationIdTrap, 
		perceivedSeverityTrap, 
		timeStampTrap, 
		additionalTextTrap }
	STATUS     current
	DESCRIPTION 
		"MUX index 27"
	::= { iFDVBTSignalTrapsPrefix 27 }

iFDVBTSignal28Trap  NOTIFICATION-TYPE
	OBJECTS { eventIdTrap, 
		notificationIdTrap, 
		perceivedSeverityTrap, 
		timeStampTrap, 
		additionalTextTrap }
	STATUS     current
	DESCRIPTION 
		"MUX index 28"
	::= { iFDVBTSignalTrapsPrefix 28 }

iFDVBTSignal29Trap  NOTIFICATION-TYPE
	OBJECTS { eventIdTrap, 
		notificationIdTrap, 
		perceivedSeverityTrap, 
		timeStampTrap, 
		additionalTextTrap }
	STATUS     current
	DESCRIPTION 
		"MUX index 29"
	::= { iFDVBTSignalTrapsPrefix 29 }

iFDVBTSignal30Trap  NOTIFICATION-TYPE
	OBJECTS { eventIdTrap, 
		notificationIdTrap, 
		perceivedSeverityTrap, 
		timeStampTrap, 
		additionalTextTrap }
	STATUS     current
	DESCRIPTION 
		"MUX index 30"
	::= { iFDVBTSignalTrapsPrefix 30 }

gps10MHz1Trap  NOTIFICATION-TYPE
	OBJECTS { eventIdTrap, 
		notificationIdTrap, 
		perceivedSeverityTrap, 
		timeStampTrap, 
		additionalTextTrap }
	STATUS     current
	DESCRIPTION 
		"MUX index 1"
	::= { gps10MHzTrapsPrefix 1 }

gps10MHz2Trap  NOTIFICATION-TYPE
	OBJECTS { eventIdTrap, 
		notificationIdTrap, 
		perceivedSeverityTrap, 
		timeStampTrap, 
		additionalTextTrap }
	STATUS     current
	DESCRIPTION 
		"MUX index 2"
	::= { gps10MHzTrapsPrefix 2 }

gps10MHz3Trap  NOTIFICATION-TYPE
	OBJECTS { eventIdTrap, 
		notificationIdTrap, 
		perceivedSeverityTrap, 
		timeStampTrap, 
		additionalTextTrap }
	STATUS     current
	DESCRIPTION 
		"MUX index 3"
	::= { gps10MHzTrapsPrefix 3 }

gps10MHz4Trap  NOTIFICATION-TYPE
	OBJECTS { eventIdTrap, 
		notificationIdTrap, 
		perceivedSeverityTrap, 
		timeStampTrap, 
		additionalTextTrap }
	STATUS     current
	DESCRIPTION 
		"MUX index 4"
	::= { gps10MHzTrapsPrefix 4 }

gps10MHz5Trap  NOTIFICATION-TYPE
	OBJECTS { eventIdTrap, 
		notificationIdTrap, 
		perceivedSeverityTrap, 
		timeStampTrap, 
		additionalTextTrap }
	STATUS     current
	DESCRIPTION 
		"MUX index 5"
	::= { gps10MHzTrapsPrefix 5 }

gps10MHz6Trap  NOTIFICATION-TYPE
	OBJECTS { eventIdTrap, 
		notificationIdTrap, 
		perceivedSeverityTrap, 
		timeStampTrap, 
		additionalTextTrap }
	STATUS     current
	DESCRIPTION 
		"MUX index 6"
	::= { gps10MHzTrapsPrefix 6 }

gps10MHz7Trap  NOTIFICATION-TYPE
	OBJECTS { eventIdTrap, 
		notificationIdTrap, 
		perceivedSeverityTrap, 
		timeStampTrap, 
		additionalTextTrap }
	STATUS     current
	DESCRIPTION 
		"MUX index 7"
	::= { gps10MHzTrapsPrefix 7 }

gps10MHz8Trap  NOTIFICATION-TYPE
	OBJECTS { eventIdTrap, 
		notificationIdTrap, 
		perceivedSeverityTrap, 
		timeStampTrap, 
		additionalTextTrap }
	STATUS     current
	DESCRIPTION 
		"MUX index 8"
	::= { gps10MHzTrapsPrefix 8 }

gps10MHz9Trap  NOTIFICATION-TYPE
	OBJECTS { eventIdTrap, 
		notificationIdTrap, 
		perceivedSeverityTrap, 
		timeStampTrap, 
		additionalTextTrap }
	STATUS     current
	DESCRIPTION 
		"MUX index 9"
	::= { gps10MHzTrapsPrefix 9 }

gps10MHz10Trap  NOTIFICATION-TYPE
	OBJECTS { eventIdTrap, 
		notificationIdTrap, 
		perceivedSeverityTrap, 
		timeStampTrap, 
		additionalTextTrap }
	STATUS     current
	DESCRIPTION 
		"MUX index 10"
	::= { gps10MHzTrapsPrefix 10 }

gps10MHz11Trap  NOTIFICATION-TYPE
	OBJECTS { eventIdTrap, 
		notificationIdTrap, 
		perceivedSeverityTrap, 
		timeStampTrap, 
		additionalTextTrap }
	STATUS     current
	DESCRIPTION 
		"MUX index 11"
	::= { gps10MHzTrapsPrefix 11 }

gps10MHz12Trap  NOTIFICATION-TYPE
	OBJECTS { eventIdTrap, 
		notificationIdTrap, 
		perceivedSeverityTrap, 
		timeStampTrap, 
		additionalTextTrap }
	STATUS     current
	DESCRIPTION 
		"MUX index 12"
	::= { gps10MHzTrapsPrefix 12 }

gps10MHz13Trap  NOTIFICATION-TYPE
	OBJECTS { eventIdTrap, 
		notificationIdTrap, 
		perceivedSeverityTrap, 
		timeStampTrap, 
		additionalTextTrap }
	STATUS     current
	DESCRIPTION 
		"MUX index 13"
	::= { gps10MHzTrapsPrefix 13 }

gps10MHz14Trap  NOTIFICATION-TYPE
	OBJECTS { eventIdTrap, 
		notificationIdTrap, 
		perceivedSeverityTrap, 
		timeStampTrap, 
		additionalTextTrap }
	STATUS     current
	DESCRIPTION 
		"MUX index 14"
	::= { gps10MHzTrapsPrefix 14 }

gps10MHz15Trap  NOTIFICATION-TYPE
	OBJECTS { eventIdTrap, 
		notificationIdTrap, 
		perceivedSeverityTrap, 
		timeStampTrap, 
		additionalTextTrap }
	STATUS     current
	DESCRIPTION 
		"MUX index 15"
	::= { gps10MHzTrapsPrefix 15 }

gps10MHz16Trap  NOTIFICATION-TYPE
	OBJECTS { eventIdTrap, 
		notificationIdTrap, 
		perceivedSeverityTrap, 
		timeStampTrap, 
		additionalTextTrap }
	STATUS     current
	DESCRIPTION 
		"MUX index 16"
	::= { gps10MHzTrapsPrefix 16 }

gps10MHz17Trap  NOTIFICATION-TYPE
	OBJECTS { eventIdTrap, 
		notificationIdTrap, 
		perceivedSeverityTrap, 
		timeStampTrap, 
		additionalTextTrap }
	STATUS     current
	DESCRIPTION 
		"MUX index 17"
	::= { gps10MHzTrapsPrefix 17 }

gps10MHz18Trap  NOTIFICATION-TYPE
	OBJECTS { eventIdTrap, 
		notificationIdTrap, 
		perceivedSeverityTrap, 
		timeStampTrap, 
		additionalTextTrap }
	STATUS     current
	DESCRIPTION 
		"MUX index 18"
	::= { gps10MHzTrapsPrefix 18 }

gps10MHz19Trap  NOTIFICATION-TYPE
	OBJECTS { eventIdTrap, 
		notificationIdTrap, 
		perceivedSeverityTrap, 
		timeStampTrap, 
		additionalTextTrap }
	STATUS     current
	DESCRIPTION 
		"MUX index 19"
	::= { gps10MHzTrapsPrefix 19 }

gps10MHz20Trap  NOTIFICATION-TYPE
	OBJECTS { eventIdTrap, 
		notificationIdTrap, 
		perceivedSeverityTrap, 
		timeStampTrap, 
		additionalTextTrap }
	STATUS     current
	DESCRIPTION 
		"MUX index 20"
	::= { gps10MHzTrapsPrefix 20 }

gps10MHz21Trap  NOTIFICATION-TYPE
	OBJECTS { eventIdTrap, 
		notificationIdTrap, 
		perceivedSeverityTrap, 
		timeStampTrap, 
		additionalTextTrap }
	STATUS     current
	DESCRIPTION 
		"MUX index 21"
	::= { gps10MHzTrapsPrefix 21 }

gps10MHz22Trap  NOTIFICATION-TYPE
	OBJECTS { eventIdTrap, 
		notificationIdTrap, 
		perceivedSeverityTrap, 
		timeStampTrap, 
		additionalTextTrap }
	STATUS     current
	DESCRIPTION 
		"MUX index 22"
	::= { gps10MHzTrapsPrefix 22 }

gps10MHz23Trap  NOTIFICATION-TYPE
	OBJECTS { eventIdTrap, 
		notificationIdTrap, 
		perceivedSeverityTrap, 
		timeStampTrap, 
		additionalTextTrap }
	STATUS     current
	DESCRIPTION 
		"MUX index 23"
	::= { gps10MHzTrapsPrefix 23 }

gps10MHz24Trap  NOTIFICATION-TYPE
	OBJECTS { eventIdTrap, 
		notificationIdTrap, 
		perceivedSeverityTrap, 
		timeStampTrap, 
		additionalTextTrap }
	STATUS     current
	DESCRIPTION 
		"MUX index 24"
	::= { gps10MHzTrapsPrefix 24 }

gps10MHz25Trap  NOTIFICATION-TYPE
	OBJECTS { eventIdTrap, 
		notificationIdTrap, 
		perceivedSeverityTrap, 
		timeStampTrap, 
		additionalTextTrap }
	STATUS     current
	DESCRIPTION 
		"MUX index 25"
	::= { gps10MHzTrapsPrefix 25 }

gps10MHz26Trap  NOTIFICATION-TYPE
	OBJECTS { eventIdTrap, 
		notificationIdTrap, 
		perceivedSeverityTrap, 
		timeStampTrap, 
		additionalTextTrap }
	STATUS     current
	DESCRIPTION 
		"MUX index 26"
	::= { gps10MHzTrapsPrefix 26 }

gps10MHz27Trap  NOTIFICATION-TYPE
	OBJECTS { eventIdTrap, 
		notificationIdTrap, 
		perceivedSeverityTrap, 
		timeStampTrap, 
		additionalTextTrap }
	STATUS     current
	DESCRIPTION 
		"MUX index 27"
	::= { gps10MHzTrapsPrefix 27 }

gps10MHz28Trap  NOTIFICATION-TYPE
	OBJECTS { eventIdTrap, 
		notificationIdTrap, 
		perceivedSeverityTrap, 
		timeStampTrap, 
		additionalTextTrap }
	STATUS     current
	DESCRIPTION 
		"MUX index 28"
	::= { gps10MHzTrapsPrefix 28 }

gps10MHz29Trap  NOTIFICATION-TYPE
	OBJECTS { eventIdTrap, 
		notificationIdTrap, 
		perceivedSeverityTrap, 
		timeStampTrap, 
		additionalTextTrap }
	STATUS     current
	DESCRIPTION 
		"MUX index 29"
	::= { gps10MHzTrapsPrefix 29 }

gps10MHz30Trap  NOTIFICATION-TYPE
	OBJECTS { eventIdTrap, 
		notificationIdTrap, 
		perceivedSeverityTrap, 
		timeStampTrap, 
		additionalTextTrap }
	STATUS     current
	DESCRIPTION 
		"MUX index 30"
	::= { gps10MHzTrapsPrefix 30 }

powerAmplifierCommunic1Trap  NOTIFICATION-TYPE
	OBJECTS { eventIdTrap, 
		notificationIdTrap, 
		perceivedSeverityTrap, 
		timeStampTrap, 
		additionalTextTrap }
	STATUS     current
	DESCRIPTION 
		"MUX index 1"
	::= { powerAmplifierCommunTrapsPrefix 1 }

powerAmplifierCommunic2Trap  NOTIFICATION-TYPE
	OBJECTS { eventIdTrap, 
		notificationIdTrap, 
		perceivedSeverityTrap, 
		timeStampTrap, 
		additionalTextTrap }
	STATUS     current
	DESCRIPTION 
		"MUX index 2"
	::= { powerAmplifierCommunTrapsPrefix 2 }

powerAmplifierCommunic3Trap  NOTIFICATION-TYPE
	OBJECTS { eventIdTrap, 
		notificationIdTrap, 
		perceivedSeverityTrap, 
		timeStampTrap, 
		additionalTextTrap }
	STATUS     current
	DESCRIPTION 
		"MUX index 3"
	::= { powerAmplifierCommunTrapsPrefix 3 }

powerAmplifierCommunic4Trap  NOTIFICATION-TYPE
	OBJECTS { eventIdTrap, 
		notificationIdTrap, 
		perceivedSeverityTrap, 
		timeStampTrap, 
		additionalTextTrap }
	STATUS     current
	DESCRIPTION 
		"MUX index 4"
	::= { powerAmplifierCommunTrapsPrefix 4 }

powerAmplifierCommunic5Trap  NOTIFICATION-TYPE
	OBJECTS { eventIdTrap, 
		notificationIdTrap, 
		perceivedSeverityTrap, 
		timeStampTrap, 
		additionalTextTrap }
	STATUS     current
	DESCRIPTION 
		"MUX index 5"
	::= { powerAmplifierCommunTrapsPrefix 5 }

powerAmplifierCommunic6Trap  NOTIFICATION-TYPE
	OBJECTS { eventIdTrap, 
		notificationIdTrap, 
		perceivedSeverityTrap, 
		timeStampTrap, 
		additionalTextTrap }
	STATUS     current
	DESCRIPTION 
		"MUX index 6"
	::= { powerAmplifierCommunTrapsPrefix 6 }

powerAmplifierCommunic7Trap  NOTIFICATION-TYPE
	OBJECTS { eventIdTrap, 
		notificationIdTrap, 
		perceivedSeverityTrap, 
		timeStampTrap, 
		additionalTextTrap }
	STATUS     current
	DESCRIPTION 
		"MUX index 7"
	::= { powerAmplifierCommunTrapsPrefix 7 }

powerAmplifierCommunic8Trap  NOTIFICATION-TYPE
	OBJECTS { eventIdTrap, 
		notificationIdTrap, 
		perceivedSeverityTrap, 
		timeStampTrap, 
		additionalTextTrap }
	STATUS     current
	DESCRIPTION 
		"MUX index 8"
	::= { powerAmplifierCommunTrapsPrefix 8 }

powerAmplifierCommunic9Trap  NOTIFICATION-TYPE
	OBJECTS { eventIdTrap, 
		notificationIdTrap, 
		perceivedSeverityTrap, 
		timeStampTrap, 
		additionalTextTrap }
	STATUS     current
	DESCRIPTION 
		"MUX index 9"
	::= { powerAmplifierCommunTrapsPrefix 9 }

powerAmplifierCommunic10Trap  NOTIFICATION-TYPE
	OBJECTS { eventIdTrap, 
		notificationIdTrap, 
		perceivedSeverityTrap, 
		timeStampTrap, 
		additionalTextTrap }
	STATUS     current
	DESCRIPTION 
		"MUX index 10"
	::= { powerAmplifierCommunTrapsPrefix 10 }

powerAmplifierCommunic11Trap  NOTIFICATION-TYPE
	OBJECTS { eventIdTrap, 
		notificationIdTrap, 
		perceivedSeverityTrap, 
		timeStampTrap, 
		additionalTextTrap }
	STATUS     current
	DESCRIPTION 
		"MUX index 11"
	::= { powerAmplifierCommunTrapsPrefix 11 }

powerAmplifierCommunic12Trap  NOTIFICATION-TYPE
	OBJECTS { eventIdTrap, 
		notificationIdTrap, 
		perceivedSeverityTrap, 
		timeStampTrap, 
		additionalTextTrap }
	STATUS     current
	DESCRIPTION 
		"MUX index 12"
	::= { powerAmplifierCommunTrapsPrefix 12 }

powerAmplifierCommunic13Trap  NOTIFICATION-TYPE
	OBJECTS { eventIdTrap, 
		notificationIdTrap, 
		perceivedSeverityTrap, 
		timeStampTrap, 
		additionalTextTrap }
	STATUS     current
	DESCRIPTION 
		"MUX index 13"
	::= { powerAmplifierCommunTrapsPrefix 13 }

powerAmplifierCommunic14Trap  NOTIFICATION-TYPE
	OBJECTS { eventIdTrap, 
		notificationIdTrap, 
		perceivedSeverityTrap, 
		timeStampTrap, 
		additionalTextTrap }
	STATUS     current
	DESCRIPTION 
		"MUX index 14"
	::= { powerAmplifierCommunTrapsPrefix 14 }

powerAmplifierCommunic15Trap  NOTIFICATION-TYPE
	OBJECTS { eventIdTrap, 
		notificationIdTrap, 
		perceivedSeverityTrap, 
		timeStampTrap, 
		additionalTextTrap }
	STATUS     current
	DESCRIPTION 
		"MUX index 15"
	::= { powerAmplifierCommunTrapsPrefix 15 }

powerAmplifierCommunic16Trap  NOTIFICATION-TYPE
	OBJECTS { eventIdTrap, 
		notificationIdTrap, 
		perceivedSeverityTrap, 
		timeStampTrap, 
		additionalTextTrap }
	STATUS     current
	DESCRIPTION 
		"MUX index 16"
	::= { powerAmplifierCommunTrapsPrefix 16 }

powerAmplifierCommunic17Trap  NOTIFICATION-TYPE
	OBJECTS { eventIdTrap, 
		notificationIdTrap, 
		perceivedSeverityTrap, 
		timeStampTrap, 
		additionalTextTrap }
	STATUS     current
	DESCRIPTION 
		"MUX index 17"
	::= { powerAmplifierCommunTrapsPrefix 17 }

powerAmplifierCommunic18Trap  NOTIFICATION-TYPE
	OBJECTS { eventIdTrap, 
		notificationIdTrap, 
		perceivedSeverityTrap, 
		timeStampTrap, 
		additionalTextTrap }
	STATUS     current
	DESCRIPTION 
		"MUX index 18"
	::= { powerAmplifierCommunTrapsPrefix 18 }

powerAmplifierCommunic19Trap  NOTIFICATION-TYPE
	OBJECTS { eventIdTrap, 
		notificationIdTrap, 
		perceivedSeverityTrap, 
		timeStampTrap, 
		additionalTextTrap }
	STATUS     current
	DESCRIPTION 
		"MUX index 19"
	::= { powerAmplifierCommunTrapsPrefix 19 }

powerAmplifierCommunic20Trap  NOTIFICATION-TYPE
	OBJECTS { eventIdTrap, 
		notificationIdTrap, 
		perceivedSeverityTrap, 
		timeStampTrap, 
		additionalTextTrap }
	STATUS     current
	DESCRIPTION 
		"MUX index 20"
	::= { powerAmplifierCommunTrapsPrefix 20 }

powerAmplifierCommunic21Trap  NOTIFICATION-TYPE
	OBJECTS { eventIdTrap, 
		notificationIdTrap, 
		perceivedSeverityTrap, 
		timeStampTrap, 
		additionalTextTrap }
	STATUS     current
	DESCRIPTION 
		"MUX index 21"
	::= { powerAmplifierCommunTrapsPrefix 21 }

powerAmplifierCommunic22Trap  NOTIFICATION-TYPE
	OBJECTS { eventIdTrap, 
		notificationIdTrap, 
		perceivedSeverityTrap, 
		timeStampTrap, 
		additionalTextTrap }
	STATUS     current
	DESCRIPTION 
		"MUX index 22"
	::= { powerAmplifierCommunTrapsPrefix 22 }

powerAmplifierCommunic23Trap  NOTIFICATION-TYPE
	OBJECTS { eventIdTrap, 
		notificationIdTrap, 
		perceivedSeverityTrap, 
		timeStampTrap, 
		additionalTextTrap }
	STATUS     current
	DESCRIPTION 
		"MUX index 23"
	::= { powerAmplifierCommunTrapsPrefix 23 }

powerAmplifierCommunic24Trap  NOTIFICATION-TYPE
	OBJECTS { eventIdTrap, 
		notificationIdTrap, 
		perceivedSeverityTrap, 
		timeStampTrap, 
		additionalTextTrap }
	STATUS     current
	DESCRIPTION 
		"MUX index 24"
	::= { powerAmplifierCommunTrapsPrefix 24 }

powerAmplifierCommunic25Trap  NOTIFICATION-TYPE
	OBJECTS { eventIdTrap, 
		notificationIdTrap, 
		perceivedSeverityTrap, 
		timeStampTrap, 
		additionalTextTrap }
	STATUS     current
	DESCRIPTION 
		"MUX index 25"
	::= { powerAmplifierCommunTrapsPrefix 25 }

powerAmplifierCommunic26Trap  NOTIFICATION-TYPE
	OBJECTS { eventIdTrap, 
		notificationIdTrap, 
		perceivedSeverityTrap, 
		timeStampTrap, 
		additionalTextTrap }
	STATUS     current
	DESCRIPTION 
		"MUX index 26"
	::= { powerAmplifierCommunTrapsPrefix 26 }

powerAmplifierCommunic27Trap  NOTIFICATION-TYPE
	OBJECTS { eventIdTrap, 
		notificationIdTrap, 
		perceivedSeverityTrap, 
		timeStampTrap, 
		additionalTextTrap }
	STATUS     current
	DESCRIPTION 
		"MUX index 27"
	::= { powerAmplifierCommunTrapsPrefix 27 }

powerAmplifierCommunic28Trap  NOTIFICATION-TYPE
	OBJECTS { eventIdTrap, 
		notificationIdTrap, 
		perceivedSeverityTrap, 
		timeStampTrap, 
		additionalTextTrap }
	STATUS     current
	DESCRIPTION 
		"MUX index 28"
	::= { powerAmplifierCommunTrapsPrefix 28 }

powerAmplifierCommunic29Trap  NOTIFICATION-TYPE
	OBJECTS { eventIdTrap, 
		notificationIdTrap, 
		perceivedSeverityTrap, 
		timeStampTrap, 
		additionalTextTrap }
	STATUS     current
	DESCRIPTION 
		"MUX index 29"
	::= { powerAmplifierCommunTrapsPrefix 29 }

powerAmplifierCommunic30Trap  NOTIFICATION-TYPE
	OBJECTS { eventIdTrap, 
		notificationIdTrap, 
		perceivedSeverityTrap, 
		timeStampTrap, 
		additionalTextTrap }
	STATUS     current
	DESCRIPTION 
		"MUX index 30"
	::= { powerAmplifierCommunTrapsPrefix 30 }

temperature1Trap  NOTIFICATION-TYPE
	OBJECTS { eventIdTrap, 
		notificationIdTrap, 
		perceivedSeverityTrap, 
		timeStampTrap, 
		additionalTextTrap }
	STATUS     current
	DESCRIPTION 
		"MUX index 1"
	::= { temperatureTrapsPrefix 1 }

temperature2Trap  NOTIFICATION-TYPE
	OBJECTS { eventIdTrap, 
		notificationIdTrap, 
		perceivedSeverityTrap, 
		timeStampTrap, 
		additionalTextTrap }
	STATUS     current
	DESCRIPTION 
		"MUX index 2"
	::= { temperatureTrapsPrefix 2 }

temperature3Trap  NOTIFICATION-TYPE
	OBJECTS { eventIdTrap, 
		notificationIdTrap, 
		perceivedSeverityTrap, 
		timeStampTrap, 
		additionalTextTrap }
	STATUS     current
	DESCRIPTION 
		"MUX index 3"
	::= { temperatureTrapsPrefix 3 }

temperature4Trap  NOTIFICATION-TYPE
	OBJECTS { eventIdTrap, 
		notificationIdTrap, 
		perceivedSeverityTrap, 
		timeStampTrap, 
		additionalTextTrap }
	STATUS     current
	DESCRIPTION 
		"MUX index 4"
	::= { temperatureTrapsPrefix 4 }

temperature5Trap  NOTIFICATION-TYPE
	OBJECTS { eventIdTrap, 
		notificationIdTrap, 
		perceivedSeverityTrap, 
		timeStampTrap, 
		additionalTextTrap }
	STATUS     current
	DESCRIPTION 
		"MUX index 5"
	::= { temperatureTrapsPrefix 5 }

temperature6Trap  NOTIFICATION-TYPE
	OBJECTS { eventIdTrap, 
		notificationIdTrap, 
		perceivedSeverityTrap, 
		timeStampTrap, 
		additionalTextTrap }
	STATUS     current
	DESCRIPTION 
		"MUX index 6"
	::= { temperatureTrapsPrefix 6 }

temperature7Trap  NOTIFICATION-TYPE
	OBJECTS { eventIdTrap, 
		notificationIdTrap, 
		perceivedSeverityTrap, 
		timeStampTrap, 
		additionalTextTrap }
	STATUS     current
	DESCRIPTION 
		"MUX index 7"
	::= { temperatureTrapsPrefix 7 }

temperature8Trap  NOTIFICATION-TYPE
	OBJECTS { eventIdTrap, 
		notificationIdTrap, 
		perceivedSeverityTrap, 
		timeStampTrap, 
		additionalTextTrap }
	STATUS     current
	DESCRIPTION 
		"MUX index 8"
	::= { temperatureTrapsPrefix 8 }

temperature9Trap  NOTIFICATION-TYPE
	OBJECTS { eventIdTrap, 
		notificationIdTrap, 
		perceivedSeverityTrap, 
		timeStampTrap, 
		additionalTextTrap }
	STATUS     current
	DESCRIPTION 
		"MUX index 9"
	::= { temperatureTrapsPrefix 9 }

temperature10Trap  NOTIFICATION-TYPE
	OBJECTS { eventIdTrap, 
		notificationIdTrap, 
		perceivedSeverityTrap, 
		timeStampTrap, 
		additionalTextTrap }
	STATUS     current
	DESCRIPTION 
		"MUX index 10"
	::= { temperatureTrapsPrefix 10 }

temperature11Trap  NOTIFICATION-TYPE
	OBJECTS { eventIdTrap, 
		notificationIdTrap, 
		perceivedSeverityTrap, 
		timeStampTrap, 
		additionalTextTrap }
	STATUS     current
	DESCRIPTION 
		"MUX index 11"
	::= { temperatureTrapsPrefix 11 }

temperature12Trap  NOTIFICATION-TYPE
	OBJECTS { eventIdTrap, 
		notificationIdTrap, 
		perceivedSeverityTrap, 
		timeStampTrap, 
		additionalTextTrap }
	STATUS     current
	DESCRIPTION 
		"MUX index 12"
	::= { temperatureTrapsPrefix 12 }

temperature13Trap  NOTIFICATION-TYPE
	OBJECTS { eventIdTrap, 
		notificationIdTrap, 
		perceivedSeverityTrap, 
		timeStampTrap, 
		additionalTextTrap }
	STATUS     current
	DESCRIPTION 
		"MUX index 13"
	::= { temperatureTrapsPrefix 13 }

temperature14Trap  NOTIFICATION-TYPE
	OBJECTS { eventIdTrap, 
		notificationIdTrap, 
		perceivedSeverityTrap, 
		timeStampTrap, 
		additionalTextTrap }
	STATUS     current
	DESCRIPTION 
		"MUX index 14"
	::= { temperatureTrapsPrefix 14 }

temperature15Trap  NOTIFICATION-TYPE
	OBJECTS { eventIdTrap, 
		notificationIdTrap, 
		perceivedSeverityTrap, 
		timeStampTrap, 
		additionalTextTrap }
	STATUS     current
	DESCRIPTION 
		"MUX index 15"
	::= { temperatureTrapsPrefix 15 }

temperature16Trap  NOTIFICATION-TYPE
	OBJECTS { eventIdTrap, 
		notificationIdTrap, 
		perceivedSeverityTrap, 
		timeStampTrap, 
		additionalTextTrap }
	STATUS     current
	DESCRIPTION 
		"MUX index 16"
	::= { temperatureTrapsPrefix 16 }

temperature17Trap  NOTIFICATION-TYPE
	OBJECTS { eventIdTrap, 
		notificationIdTrap, 
		perceivedSeverityTrap, 
		timeStampTrap, 
		additionalTextTrap }
	STATUS     current
	DESCRIPTION 
		"MUX index 17"
	::= { temperatureTrapsPrefix 17 }

temperature18Trap  NOTIFICATION-TYPE
	OBJECTS { eventIdTrap, 
		notificationIdTrap, 
		perceivedSeverityTrap, 
		timeStampTrap, 
		additionalTextTrap }
	STATUS     current
	DESCRIPTION 
		"MUX index 18"
	::= { temperatureTrapsPrefix 18 }

temperature19Trap  NOTIFICATION-TYPE
	OBJECTS { eventIdTrap, 
		notificationIdTrap, 
		perceivedSeverityTrap, 
		timeStampTrap, 
		additionalTextTrap }
	STATUS     current
	DESCRIPTION 
		"MUX index 19"
	::= { temperatureTrapsPrefix 19 }

temperature20Trap  NOTIFICATION-TYPE
	OBJECTS { eventIdTrap, 
		notificationIdTrap, 
		perceivedSeverityTrap, 
		timeStampTrap, 
		additionalTextTrap }
	STATUS     current
	DESCRIPTION 
		"MUX index 20"
	::= { temperatureTrapsPrefix 20 }

temperature21Trap  NOTIFICATION-TYPE
	OBJECTS { eventIdTrap, 
		notificationIdTrap, 
		perceivedSeverityTrap, 
		timeStampTrap, 
		additionalTextTrap }
	STATUS     current
	DESCRIPTION 
		"MUX index 21"
	::= { temperatureTrapsPrefix 21 }

temperature22Trap  NOTIFICATION-TYPE
	OBJECTS { eventIdTrap, 
		notificationIdTrap, 
		perceivedSeverityTrap, 
		timeStampTrap, 
		additionalTextTrap }
	STATUS     current
	DESCRIPTION 
		"MUX index 22"
	::= { temperatureTrapsPrefix 22 }

temperature23Trap  NOTIFICATION-TYPE
	OBJECTS { eventIdTrap, 
		notificationIdTrap, 
		perceivedSeverityTrap, 
		timeStampTrap, 
		additionalTextTrap }
	STATUS     current
	DESCRIPTION 
		"MUX index 23"
	::= { temperatureTrapsPrefix 23 }

temperature24Trap  NOTIFICATION-TYPE
	OBJECTS { eventIdTrap, 
		notificationIdTrap, 
		perceivedSeverityTrap, 
		timeStampTrap, 
		additionalTextTrap }
	STATUS     current
	DESCRIPTION 
		"MUX index 24"
	::= { temperatureTrapsPrefix 24 }

temperature25Trap  NOTIFICATION-TYPE
	OBJECTS { eventIdTrap, 
		notificationIdTrap, 
		perceivedSeverityTrap, 
		timeStampTrap, 
		additionalTextTrap }
	STATUS     current
	DESCRIPTION 
		"MUX index 25"
	::= { temperatureTrapsPrefix 25 }

temperature26Trap  NOTIFICATION-TYPE
	OBJECTS { eventIdTrap, 
		notificationIdTrap, 
		perceivedSeverityTrap, 
		timeStampTrap, 
		additionalTextTrap }
	STATUS     current
	DESCRIPTION 
		"MUX index 26"
	::= { temperatureTrapsPrefix 26 }

temperature27Trap  NOTIFICATION-TYPE
	OBJECTS { eventIdTrap, 
		notificationIdTrap, 
		perceivedSeverityTrap, 
		timeStampTrap, 
		additionalTextTrap }
	STATUS     current
	DESCRIPTION 
		"MUX index 27"
	::= { temperatureTrapsPrefix 27 }

temperature28Trap  NOTIFICATION-TYPE
	OBJECTS { eventIdTrap, 
		notificationIdTrap, 
		perceivedSeverityTrap, 
		timeStampTrap, 
		additionalTextTrap }
	STATUS     current
	DESCRIPTION 
		"MUX index 28"
	::= { temperatureTrapsPrefix 28 }

temperature29Trap  NOTIFICATION-TYPE
	OBJECTS { eventIdTrap, 
		notificationIdTrap, 
		perceivedSeverityTrap, 
		timeStampTrap, 
		additionalTextTrap }
	STATUS     current
	DESCRIPTION 
		"MUX index 29"
	::= { temperatureTrapsPrefix 29 }

temperature30Trap  NOTIFICATION-TYPE
	OBJECTS { eventIdTrap, 
		notificationIdTrap, 
		perceivedSeverityTrap, 
		timeStampTrap, 
		additionalTextTrap }
	STATUS     current
	DESCRIPTION 
		"MUX index 30"
	::= { temperatureTrapsPrefix 30 }

moduleCommunication1Trap  NOTIFICATION-TYPE
	OBJECTS { eventIdTrap, 
		notificationIdTrap, 
		perceivedSeverityTrap, 
		timeStampTrap, 
		additionalTextTrap }
	STATUS     current
	DESCRIPTION 
		"Index 1"
	::= { moduleCommunicationTrapsPrefix 1 }

moduleCommunication2Trap  NOTIFICATION-TYPE
	OBJECTS { eventIdTrap, 
		notificationIdTrap, 
		perceivedSeverityTrap, 
		timeStampTrap, 
		additionalTextTrap }
	STATUS     current
	DESCRIPTION 
		"Index 2"
	::= { moduleCommunicationTrapsPrefix 2 }

moduleCommunication3Trap  NOTIFICATION-TYPE
	OBJECTS { eventIdTrap, 
		notificationIdTrap, 
		perceivedSeverityTrap, 
		timeStampTrap, 
		additionalTextTrap }
	STATUS     current
	DESCRIPTION 
		"Index 3"
	::= { moduleCommunicationTrapsPrefix 3 }

moduleCommunication4Trap  NOTIFICATION-TYPE
	OBJECTS { eventIdTrap, 
		notificationIdTrap, 
		perceivedSeverityTrap, 
		timeStampTrap, 
		additionalTextTrap }
	STATUS     current
	DESCRIPTION 
		"Index 4"
	::= { moduleCommunicationTrapsPrefix 4 }

moduleCommunication5Trap  NOTIFICATION-TYPE
	OBJECTS { eventIdTrap, 
		notificationIdTrap, 
		perceivedSeverityTrap, 
		timeStampTrap, 
		additionalTextTrap }
	STATUS     current
	DESCRIPTION 
		"Index 5"
	::= { moduleCommunicationTrapsPrefix 5 }

moduleCommunication6Trap  NOTIFICATION-TYPE
	OBJECTS { eventIdTrap, 
		notificationIdTrap, 
		perceivedSeverityTrap, 
		timeStampTrap, 
		additionalTextTrap }
	STATUS     current
	DESCRIPTION 
		"Index 6"
	::= { moduleCommunicationTrapsPrefix 6 }

moduleCommunication7Trap  NOTIFICATION-TYPE
	OBJECTS { eventIdTrap, 
		notificationIdTrap, 
		perceivedSeverityTrap, 
		timeStampTrap, 
		additionalTextTrap }
	STATUS     current
	DESCRIPTION 
		"Index 7"
	::= { moduleCommunicationTrapsPrefix 7 }

moduleCommunication8Trap  NOTIFICATION-TYPE
	OBJECTS { eventIdTrap, 
		notificationIdTrap, 
		perceivedSeverityTrap, 
		timeStampTrap, 
		additionalTextTrap }
	STATUS     current
	DESCRIPTION 
		"Index 8"
	::= { moduleCommunicationTrapsPrefix 8 }

moduleCommunication9Trap  NOTIFICATION-TYPE
	OBJECTS { eventIdTrap, 
		notificationIdTrap, 
		perceivedSeverityTrap, 
		timeStampTrap, 
		additionalTextTrap }
	STATUS     current
	DESCRIPTION 
		"Index 9"
	::= { moduleCommunicationTrapsPrefix 9 }

moduleCommunication10Trap  NOTIFICATION-TYPE
	OBJECTS { eventIdTrap, 
		notificationIdTrap, 
		perceivedSeverityTrap, 
		timeStampTrap, 
		additionalTextTrap }
	STATUS     current
	DESCRIPTION 
		"Index 10"
	::= { moduleCommunicationTrapsPrefix 10 }

moduleCommunication11Trap  NOTIFICATION-TYPE
	OBJECTS { eventIdTrap, 
		notificationIdTrap, 
		perceivedSeverityTrap, 
		timeStampTrap, 
		additionalTextTrap }
	STATUS     current
	DESCRIPTION 
		"Index 11"
	::= { moduleCommunicationTrapsPrefix 11 }

moduleCommunication12Trap  NOTIFICATION-TYPE
	OBJECTS { eventIdTrap, 
		notificationIdTrap, 
		perceivedSeverityTrap, 
		timeStampTrap, 
		additionalTextTrap }
	STATUS     current
	DESCRIPTION 
		"Index 12"
	::= { moduleCommunicationTrapsPrefix 12 }

moduleCommunication13Trap  NOTIFICATION-TYPE
	OBJECTS { eventIdTrap, 
		notificationIdTrap, 
		perceivedSeverityTrap, 
		timeStampTrap, 
		additionalTextTrap }
	STATUS     current
	DESCRIPTION 
		"Index 13"
	::= { moduleCommunicationTrapsPrefix 13 }

moduleCommunication14Trap  NOTIFICATION-TYPE
	OBJECTS { eventIdTrap, 
		notificationIdTrap, 
		perceivedSeverityTrap, 
		timeStampTrap, 
		additionalTextTrap }
	STATUS     current
	DESCRIPTION 
		"Index 14"
	::= { moduleCommunicationTrapsPrefix 14 }

moduleCommunication15Trap  NOTIFICATION-TYPE
	OBJECTS { eventIdTrap, 
		notificationIdTrap, 
		perceivedSeverityTrap, 
		timeStampTrap, 
		additionalTextTrap }
	STATUS     current
	DESCRIPTION 
		"Index 15"
	::= { moduleCommunicationTrapsPrefix 15 }

moduleCommunicationUCASSCCTrap  NOTIFICATION-TYPE
	OBJECTS { eventIdTrap, 
		notificationIdTrap, 
		perceivedSeverityTrap, 
		timeStampTrap, 
		additionalTextTrap }
	STATUS     current
	DESCRIPTION 
		"UCA SS.CC."
	::= { moduleCommunicationTrapsPrefix 20 }

moduleCommunicationUCA1Trap  NOTIFICATION-TYPE
	OBJECTS { eventIdTrap, 
		notificationIdTrap, 
		perceivedSeverityTrap, 
		timeStampTrap, 
		additionalTextTrap }
	STATUS     current
	DESCRIPTION 
		"UCA 1"
	::= { moduleCommunicationTrapsPrefix 21 }

moduleCommunicationUCA2Trap  NOTIFICATION-TYPE
	OBJECTS { eventIdTrap, 
		notificationIdTrap, 
		perceivedSeverityTrap, 
		timeStampTrap, 
		additionalTextTrap }
	STATUS     current
	DESCRIPTION 
		"UCA 2"
	::= { moduleCommunicationTrapsPrefix 22 }

moduleCommunicationUCA3Trap  NOTIFICATION-TYPE
	OBJECTS { eventIdTrap, 
		notificationIdTrap, 
		perceivedSeverityTrap, 
		timeStampTrap, 
		additionalTextTrap }
	STATUS     current
	DESCRIPTION 
		"UCA 3"
	::= { moduleCommunicationTrapsPrefix 23 }

moduleCommunicationUCA4Trap  NOTIFICATION-TYPE
	OBJECTS { eventIdTrap, 
		notificationIdTrap, 
		perceivedSeverityTrap, 
		timeStampTrap, 
		additionalTextTrap }
	STATUS     current
	DESCRIPTION 
		"UCA 3"
	::= { moduleCommunicationTrapsPrefix 24 }

moduleCommunicationUCA5Trap  NOTIFICATION-TYPE
	OBJECTS { eventIdTrap, 
		notificationIdTrap, 
		perceivedSeverityTrap, 
		timeStampTrap, 
		additionalTextTrap }
	STATUS     current
	DESCRIPTION 
		"UCA 3"
	::= { moduleCommunicationTrapsPrefix 25 }

moduleCommunicationGPS1Trap  NOTIFICATION-TYPE
	OBJECTS { eventIdTrap, 
		notificationIdTrap, 
		perceivedSeverityTrap, 
		timeStampTrap, 
		additionalTextTrap }
	STATUS     current
	DESCRIPTION 
		"GPS 1"
	::= { moduleCommunicationTrapsPrefix 50 }

moduleCommunicationGPS2Trap  NOTIFICATION-TYPE
	OBJECTS { eventIdTrap, 
		notificationIdTrap, 
		perceivedSeverityTrap, 
		timeStampTrap, 
		additionalTextTrap }
	STATUS     current
	DESCRIPTION 
		"GPS 2"
	::= { moduleCommunicationTrapsPrefix 51 }

moduleCommunicationCONTACTSTrap  NOTIFICATION-TYPE
	OBJECTS { eventIdTrap, 
		notificationIdTrap, 
		perceivedSeverityTrap, 
		timeStampTrap, 
		additionalTextTrap }
	STATUS     current
	DESCRIPTION 
		"Relays module"
	::= { moduleCommunicationTrapsPrefix 60 }

moduleCommunicationUCA101Trap  NOTIFICATION-TYPE
	OBJECTS { eventIdTrap, 
		notificationIdTrap, 
		perceivedSeverityTrap, 
		timeStampTrap, 
		additionalTextTrap }
	STATUS     current
	DESCRIPTION 
		"UCA 1+1 1"
	::= { moduleCommunicationTrapsPrefix 71 }

moduleCommunicationUCA102Trap  NOTIFICATION-TYPE
	OBJECTS { eventIdTrap, 
		notificationIdTrap, 
		perceivedSeverityTrap, 
		timeStampTrap, 
		additionalTextTrap }
	STATUS     current
	DESCRIPTION 
		"UCA 1+1 2"
	::= { moduleCommunicationTrapsPrefix 72 }

moduleCommunicationUCA103Trap  NOTIFICATION-TYPE
	OBJECTS { eventIdTrap, 
		notificationIdTrap, 
		perceivedSeverityTrap, 
		timeStampTrap, 
		additionalTextTrap }
	STATUS     current
	DESCRIPTION 
		"UCA 1+1 3"
	::= { moduleCommunicationTrapsPrefix 73 }

moduleCommunicationUCA104Trap  NOTIFICATION-TYPE
	OBJECTS { eventIdTrap, 
		notificationIdTrap, 
		perceivedSeverityTrap, 
		timeStampTrap, 
		additionalTextTrap }
	STATUS     current
	DESCRIPTION 
		"UCA 1+1 4"
	::= { moduleCommunicationTrapsPrefix 74 }

moduleCommunicationUCA105Trap  NOTIFICATION-TYPE
	OBJECTS { eventIdTrap, 
		notificationIdTrap, 
		perceivedSeverityTrap, 
		timeStampTrap, 
		additionalTextTrap }
	STATUS     current
	DESCRIPTION 
		"UCA 1+1 5"
	::= { moduleCommunicationTrapsPrefix 75 }

moduleCommunicationUCA106Trap  NOTIFICATION-TYPE
	OBJECTS { eventIdTrap, 
		notificationIdTrap, 
		perceivedSeverityTrap, 
		timeStampTrap, 
		additionalTextTrap }
	STATUS     current
	DESCRIPTION 
		"UCA 1+1 6"
	::= { moduleCommunicationTrapsPrefix 76 }

moduleCommunicationUCA107Trap  NOTIFICATION-TYPE
	OBJECTS { eventIdTrap, 
		notificationIdTrap, 
		perceivedSeverityTrap, 
		timeStampTrap, 
		additionalTextTrap }
	STATUS     current
	DESCRIPTION 
		"UCA 1+1 7"
	::= { moduleCommunicationTrapsPrefix 77 }

moduleCommunicationUCA108Trap  NOTIFICATION-TYPE
	OBJECTS { eventIdTrap, 
		notificationIdTrap, 
		perceivedSeverityTrap, 
		timeStampTrap, 
		additionalTextTrap }
	STATUS     current
	DESCRIPTION 
		"UCA 1+1 8"
	::= { moduleCommunicationTrapsPrefix 78 }

moduleCommunicationUCA109Trap  NOTIFICATION-TYPE
	OBJECTS { eventIdTrap, 
		notificationIdTrap, 
		perceivedSeverityTrap, 
		timeStampTrap, 
		additionalTextTrap }
	STATUS     current
	DESCRIPTION 
		"UCA 1+1 9"
	::= { moduleCommunicationTrapsPrefix 79 }

moduleCommunicationUCA110Trap  NOTIFICATION-TYPE
	OBJECTS { eventIdTrap, 
		notificationIdTrap, 
		perceivedSeverityTrap, 
		timeStampTrap, 
		additionalTextTrap }
	STATUS     current
	DESCRIPTION 
		"UCA 1+1 10"
	::= { moduleCommunicationTrapsPrefix 80 }

moduleCommunicationUCA111Trap  NOTIFICATION-TYPE
	OBJECTS { eventIdTrap, 
		notificationIdTrap, 
		perceivedSeverityTrap, 
		timeStampTrap, 
		additionalTextTrap }
	STATUS     current
	DESCRIPTION 
		"UCA 1+1 11"
	::= { moduleCommunicationTrapsPrefix 81 }

moduleCommunicationUCA112Trap  NOTIFICATION-TYPE
	OBJECTS { eventIdTrap, 
		notificationIdTrap, 
		perceivedSeverityTrap, 
		timeStampTrap, 
		additionalTextTrap }
	STATUS     current
	DESCRIPTION 
		"UCA 1+1 12"
	::= { moduleCommunicationTrapsPrefix 82 }

moduleCommunicationUCA113Trap  NOTIFICATION-TYPE
	OBJECTS { eventIdTrap, 
		notificationIdTrap, 
		perceivedSeverityTrap, 
		timeStampTrap, 
		additionalTextTrap }
	STATUS     current
	DESCRIPTION 
		"UCA 1+1 13"
	::= { moduleCommunicationTrapsPrefix 83 }

moduleCommunicationUCA114Trap  NOTIFICATION-TYPE
	OBJECTS { eventIdTrap, 
		notificationIdTrap, 
		perceivedSeverityTrap, 
		timeStampTrap, 
		additionalTextTrap }
	STATUS     current
	DESCRIPTION 
		"UCA 1+1 14"
	::= { moduleCommunicationTrapsPrefix 84 }

moduleCommunicationUCA115Trap  NOTIFICATION-TYPE
	OBJECTS { eventIdTrap, 
		notificationIdTrap, 
		perceivedSeverityTrap, 
		timeStampTrap, 
		additionalTextTrap }
	STATUS     current
	DESCRIPTION 
		"UCA 1+1 15"
	::= { moduleCommunicationTrapsPrefix 85 }

moduleCommunication1BTrap  NOTIFICATION-TYPE
	OBJECTS { eventIdTrap, 
		notificationIdTrap, 
		perceivedSeverityTrap, 
		timeStampTrap, 
		additionalTextTrap }
	STATUS     current
	DESCRIPTION 
		"MUX index 16"
	::= { moduleCommunicationTrapsPrefix 101 }

moduleCommunication2BTrap  NOTIFICATION-TYPE
	OBJECTS { eventIdTrap, 
		notificationIdTrap, 
		perceivedSeverityTrap, 
		timeStampTrap, 
		additionalTextTrap }
	STATUS     current
	DESCRIPTION 
		"MUX index 17"
	::= { moduleCommunicationTrapsPrefix 102 }

moduleCommunication3BTrap  NOTIFICATION-TYPE
	OBJECTS { eventIdTrap, 
		notificationIdTrap, 
		perceivedSeverityTrap, 
		timeStampTrap, 
		additionalTextTrap }
	STATUS     current
	DESCRIPTION 
		"MUX index 18"
	::= { moduleCommunicationTrapsPrefix 103 }

moduleCommunication4BTrap  NOTIFICATION-TYPE
	OBJECTS { eventIdTrap, 
		notificationIdTrap, 
		perceivedSeverityTrap, 
		timeStampTrap, 
		additionalTextTrap }
	STATUS     current
	DESCRIPTION 
		"MUX index 19"
	::= { moduleCommunicationTrapsPrefix 104 }

moduleCommunication5BTrap  NOTIFICATION-TYPE
	OBJECTS { eventIdTrap, 
		notificationIdTrap, 
		perceivedSeverityTrap, 
		timeStampTrap, 
		additionalTextTrap }
	STATUS     current
	DESCRIPTION 
		"MUX index 20"
	::= { moduleCommunicationTrapsPrefix 105 }

moduleCommunication6BTrap  NOTIFICATION-TYPE
	OBJECTS { eventIdTrap, 
		notificationIdTrap, 
		perceivedSeverityTrap, 
		timeStampTrap, 
		additionalTextTrap }
	STATUS     current
	DESCRIPTION 
		"MUX index 21"
	::= { moduleCommunicationTrapsPrefix 106 }

moduleCommunication7BTrap  NOTIFICATION-TYPE
	OBJECTS { eventIdTrap, 
		notificationIdTrap, 
		perceivedSeverityTrap, 
		timeStampTrap, 
		additionalTextTrap }
	STATUS     current
	DESCRIPTION 
		"MUX index 22"
	::= { moduleCommunicationTrapsPrefix 107 }

moduleCommunication8BTrap  NOTIFICATION-TYPE
	OBJECTS { eventIdTrap, 
		notificationIdTrap, 
		perceivedSeverityTrap, 
		timeStampTrap, 
		additionalTextTrap }
	STATUS     current
	DESCRIPTION 
		"MUX index 23"
	::= { moduleCommunicationTrapsPrefix 108 }

moduleCommunication9BTrap  NOTIFICATION-TYPE
	OBJECTS { eventIdTrap, 
		notificationIdTrap, 
		perceivedSeverityTrap, 
		timeStampTrap, 
		additionalTextTrap }
	STATUS     current
	DESCRIPTION 
		"MUX index 24"
	::= { moduleCommunicationTrapsPrefix 109 }

moduleCommunication10BTrap  NOTIFICATION-TYPE
	OBJECTS { eventIdTrap, 
		notificationIdTrap, 
		perceivedSeverityTrap, 
		timeStampTrap, 
		additionalTextTrap }
	STATUS     current
	DESCRIPTION 
		"MUX index 25"
	::= { moduleCommunicationTrapsPrefix 110 }

moduleCommunication11BTrap  NOTIFICATION-TYPE
	OBJECTS { eventIdTrap, 
		notificationIdTrap, 
		perceivedSeverityTrap, 
		timeStampTrap, 
		additionalTextTrap }
	STATUS     current
	DESCRIPTION 
		"MUX index 26"
	::= { moduleCommunicationTrapsPrefix 111 }

moduleCommunication12BTrap  NOTIFICATION-TYPE
	OBJECTS { eventIdTrap, 
		notificationIdTrap, 
		perceivedSeverityTrap, 
		timeStampTrap, 
		additionalTextTrap }
	STATUS     current
	DESCRIPTION 
		"MUX index 27"
	::= { moduleCommunicationTrapsPrefix 112 }

moduleCommunication13BTrap  NOTIFICATION-TYPE
	OBJECTS { eventIdTrap, 
		notificationIdTrap, 
		perceivedSeverityTrap, 
		timeStampTrap, 
		additionalTextTrap }
	STATUS     current
	DESCRIPTION 
		"MUX index 28"
	::= { moduleCommunicationTrapsPrefix 113 }

moduleCommunication14BTrap  NOTIFICATION-TYPE
	OBJECTS { eventIdTrap, 
		notificationIdTrap, 
		perceivedSeverityTrap, 
		timeStampTrap, 
		additionalTextTrap }
	STATUS     current
	DESCRIPTION 
		"MUX index 29"
	::= { moduleCommunicationTrapsPrefix 114 }

moduleCommunication15BTrap  NOTIFICATION-TYPE
	OBJECTS { eventIdTrap, 
		notificationIdTrap, 
		perceivedSeverityTrap, 
		timeStampTrap, 
		additionalTextTrap }
	STATUS     current
	DESCRIPTION 
		"MUX index 30"
	::= { moduleCommunicationTrapsPrefix 115 }

powerSupply1UCASSCCTrap  NOTIFICATION-TYPE
	OBJECTS { eventIdTrap, 
		notificationIdTrap, 
		perceivedSeverityTrap, 
		timeStampTrap, 
		additionalTextTrap }
	STATUS     current
	DESCRIPTION 
		"UCA SSCC"
	::= { powerSupply1TrapsPrefix 1 }

powerSupply1UCA1Trap  NOTIFICATION-TYPE
	OBJECTS { eventIdTrap, 
		notificationIdTrap, 
		perceivedSeverityTrap, 
		timeStampTrap, 
		additionalTextTrap }
	STATUS     current
	DESCRIPTION 
		"UCA 1"
	::= { powerSupply1TrapsPrefix 2 }

powerSupply1UCA2Trap  NOTIFICATION-TYPE
	OBJECTS { eventIdTrap, 
		notificationIdTrap, 
		perceivedSeverityTrap, 
		timeStampTrap, 
		additionalTextTrap }
	STATUS     current
	DESCRIPTION 
		"UCA 2"
	::= { powerSupply1TrapsPrefix 3 }

powerSupply1UCA3Trap  NOTIFICATION-TYPE
	OBJECTS { eventIdTrap, 
		notificationIdTrap, 
		perceivedSeverityTrap, 
		timeStampTrap, 
		additionalTextTrap }
	STATUS     current
	DESCRIPTION 
		"UCA 3"
	::= { powerSupply1TrapsPrefix 4 }

powerSupply1UC4Trap  NOTIFICATION-TYPE
	OBJECTS { eventIdTrap, 
		notificationIdTrap, 
		perceivedSeverityTrap, 
		timeStampTrap, 
		additionalTextTrap }
	STATUS     current
	DESCRIPTION 
		"UCA 3"
	::= { powerSupply1TrapsPrefix 5 }

powerSupply1UCA5Trap  NOTIFICATION-TYPE
	OBJECTS { eventIdTrap, 
		notificationIdTrap, 
		perceivedSeverityTrap, 
		timeStampTrap, 
		additionalTextTrap }
	STATUS     current
	DESCRIPTION 
		"UCA 3"
	::= { powerSupply1TrapsPrefix 6 }

powerSupply2UCASSCCTrap  NOTIFICATION-TYPE
	OBJECTS { eventIdTrap, 
		notificationIdTrap, 
		perceivedSeverityTrap, 
		timeStampTrap, 
		additionalTextTrap }
	STATUS     current
	DESCRIPTION 
		"UCA SSCC"
	::= { powerSupply2TrapsPrefix 1 }

powerSupply2UCA1Trap  NOTIFICATION-TYPE
	OBJECTS { eventIdTrap, 
		notificationIdTrap, 
		perceivedSeverityTrap, 
		timeStampTrap, 
		additionalTextTrap }
	STATUS     current
	DESCRIPTION 
		"UCA 1"
	::= { powerSupply2TrapsPrefix 2 }

powerSupply2UCA2Trap  NOTIFICATION-TYPE
	OBJECTS { eventIdTrap, 
		notificationIdTrap, 
		perceivedSeverityTrap, 
		timeStampTrap, 
		additionalTextTrap }
	STATUS     current
	DESCRIPTION 
		"UCA 2"
	::= { powerSupply2TrapsPrefix 3 }

powerSupply2UCA3Trap  NOTIFICATION-TYPE
	OBJECTS { eventIdTrap, 
		notificationIdTrap, 
		perceivedSeverityTrap, 
		timeStampTrap, 
		additionalTextTrap }
	STATUS     current
	DESCRIPTION 
		"UCA 3"
	::= { powerSupply2TrapsPrefix 4 }

powerSupply2UCA4Trap  NOTIFICATION-TYPE
	OBJECTS { eventIdTrap, 
		notificationIdTrap, 
		perceivedSeverityTrap, 
		timeStampTrap, 
		additionalTextTrap }
	STATUS     current
	DESCRIPTION 
		"UCA 3"
	::= { powerSupply2TrapsPrefix 5 }

powerSupply2UCA5Trap  NOTIFICATION-TYPE
	OBJECTS { eventIdTrap, 
		notificationIdTrap, 
		perceivedSeverityTrap, 
		timeStampTrap, 
		additionalTextTrap }
	STATUS     current
	DESCRIPTION 
		"UCA 3"
	::= { powerSupply2TrapsPrefix 6 }

gpsHoldoverGPS1Trap  NOTIFICATION-TYPE
	OBJECTS { eventIdTrap, 
		notificationIdTrap, 
		perceivedSeverityTrap, 
		timeStampTrap, 
		additionalTextTrap }
	STATUS     current
	DESCRIPTION 
		"GPS 1"
	::= { gpsHoldoverTrapsPrefix 1 }

gpsHoldoverGPS2Trap  NOTIFICATION-TYPE
	OBJECTS { eventIdTrap, 
		notificationIdTrap, 
		perceivedSeverityTrap, 
		timeStampTrap, 
		additionalTextTrap }
	STATUS     current
	DESCRIPTION 
		"GPS 2"
	::= { gpsHoldoverTrapsPrefix 2 }

gpsAntennaGPS1Trap  NOTIFICATION-TYPE
	OBJECTS { eventIdTrap, 
		notificationIdTrap, 
		perceivedSeverityTrap, 
		timeStampTrap, 
		additionalTextTrap }
	STATUS     current
	DESCRIPTION 
		"GPS 1"
	::= { gpsAntennaTrapsPrefix 1 }

gpsAntennaGPS2Trap  NOTIFICATION-TYPE
	OBJECTS { eventIdTrap, 
		notificationIdTrap, 
		perceivedSeverityTrap, 
		timeStampTrap, 
		additionalTextTrap }
	STATUS     current
	DESCRIPTION 
		"GPS 2"
	::= { gpsAntennaTrapsPrefix 2 }

relay1Trap  NOTIFICATION-TYPE
	OBJECTS { eventIdTrap, 
		notificationIdTrap, 
		perceivedSeverityTrap, 
		timeStampTrap, 
		additionalTextTrap }
	STATUS     current
	DESCRIPTION 
		"Relay 1"
	::= { relayTrapsPrefix 1 }

relay2Trap  NOTIFICATION-TYPE
	OBJECTS { eventIdTrap, 
		notificationIdTrap, 
		perceivedSeverityTrap, 
		timeStampTrap, 
		additionalTextTrap }
	STATUS     current
	DESCRIPTION 
		"Relay 2"
	::= { relayTrapsPrefix 2 }

relay3Trap  NOTIFICATION-TYPE
	OBJECTS { eventIdTrap, 
		notificationIdTrap, 
		perceivedSeverityTrap, 
		timeStampTrap, 
		additionalTextTrap }
	STATUS     current
	DESCRIPTION 
		"Relay 3"
	::= { relayTrapsPrefix 3 }

relay4Trap  NOTIFICATION-TYPE
	OBJECTS { eventIdTrap, 
		notificationIdTrap, 
		perceivedSeverityTrap, 
		timeStampTrap, 
		additionalTextTrap }
	STATUS     current
	DESCRIPTION 
		"Relay 4"
	::= { relayTrapsPrefix 4 }

relay5Trap  NOTIFICATION-TYPE
	OBJECTS { eventIdTrap, 
		notificationIdTrap, 
		perceivedSeverityTrap, 
		timeStampTrap, 
		additionalTextTrap }
	STATUS     current
	DESCRIPTION 
		"Relay 5"
	::= { relayTrapsPrefix 5 }

relay6Trap  NOTIFICATION-TYPE
	OBJECTS { eventIdTrap, 
		notificationIdTrap, 
		perceivedSeverityTrap, 
		timeStampTrap, 
		additionalTextTrap }
	STATUS     current
	DESCRIPTION 
		"Relay 6"
	::= { relayTrapsPrefix 6 }

relay7Trap  NOTIFICATION-TYPE
	OBJECTS { eventIdTrap, 
		notificationIdTrap, 
		perceivedSeverityTrap, 
		timeStampTrap, 
		additionalTextTrap }
	STATUS     current
	DESCRIPTION 
		"Relay 7"
	::= { relayTrapsPrefix 7 }

relay8Trap  NOTIFICATION-TYPE
	OBJECTS { eventIdTrap, 
		notificationIdTrap, 
		perceivedSeverityTrap, 
		timeStampTrap, 
		additionalTextTrap }
	STATUS     current
	DESCRIPTION 
		"Relay 8"
	::= { relayTrapsPrefix 8 }

relay9Trap  NOTIFICATION-TYPE
	OBJECTS { eventIdTrap, 
		notificationIdTrap, 
		perceivedSeverityTrap, 
		timeStampTrap, 
		additionalTextTrap }
	STATUS     current
	DESCRIPTION 
		"Relay 9"
	::= { relayTrapsPrefix 9 }

relay10Trap  NOTIFICATION-TYPE
	OBJECTS { eventIdTrap, 
		notificationIdTrap, 
		perceivedSeverityTrap, 
		timeStampTrap, 
		additionalTextTrap }
	STATUS     current
	DESCRIPTION 
		"Relay 10"
	::= { relayTrapsPrefix 10 }

relay11Trap  NOTIFICATION-TYPE
	OBJECTS { eventIdTrap, 
		notificationIdTrap, 
		perceivedSeverityTrap, 
		timeStampTrap, 
		additionalTextTrap }
	STATUS     current
	DESCRIPTION 
		"Relay 11"
	::= { relayTrapsPrefix 11 }

relay12Trap  NOTIFICATION-TYPE
	OBJECTS { eventIdTrap, 
		notificationIdTrap, 
		perceivedSeverityTrap, 
		timeStampTrap, 
		additionalTextTrap }
	STATUS     current
	DESCRIPTION 
		"Relay 12"
	::= { relayTrapsPrefix 12 }

relay13Trap  NOTIFICATION-TYPE
	OBJECTS { eventIdTrap, 
		notificationIdTrap, 
		perceivedSeverityTrap, 
		timeStampTrap, 
		additionalTextTrap }
	STATUS     current
	DESCRIPTION 
		"Relay 13"
	::= { relayTrapsPrefix 13 }

relay14Trap  NOTIFICATION-TYPE
	OBJECTS { eventIdTrap, 
		notificationIdTrap, 
		perceivedSeverityTrap, 
		timeStampTrap, 
		additionalTextTrap }
	STATUS     current
	DESCRIPTION 
		"Relay 14"
	::= { relayTrapsPrefix 14 }

relay15Trap  NOTIFICATION-TYPE
	OBJECTS { eventIdTrap, 
		notificationIdTrap, 
		perceivedSeverityTrap, 
		timeStampTrap, 
		additionalTextTrap }
	STATUS     current
	DESCRIPTION 
		"Relay 15"
	::= { relayTrapsPrefix 15 }

channelBer1Trap  NOTIFICATION-TYPE
	OBJECTS { eventIdTrap, 
		notificationIdTrap, 
		perceivedSeverityTrap, 
		timeStampTrap, 
		additionalTextTrap }
	STATUS     current
	DESCRIPTION 
		"MUX index 1"
	::= { channelBerTrapsPrefix 1 }

channelBer2Trap  NOTIFICATION-TYPE
	OBJECTS { eventIdTrap, 
		notificationIdTrap, 
		perceivedSeverityTrap, 
		timeStampTrap, 
		additionalTextTrap }
	STATUS     current
	DESCRIPTION 
		"MUX index 2"
	::= { channelBerTrapsPrefix 2 }

channelBer3Trap  NOTIFICATION-TYPE
	OBJECTS { eventIdTrap, 
		notificationIdTrap, 
		perceivedSeverityTrap, 
		timeStampTrap, 
		additionalTextTrap }
	STATUS     current
	DESCRIPTION 
		"MUX index 3"
	::= { channelBerTrapsPrefix 3 }

channelBer4Trap  NOTIFICATION-TYPE
	OBJECTS { eventIdTrap, 
		notificationIdTrap, 
		perceivedSeverityTrap, 
		timeStampTrap, 
		additionalTextTrap }
	STATUS     current
	DESCRIPTION 
		"MUX index 4"
	::= { channelBerTrapsPrefix 4 }

channelBer5Trap  NOTIFICATION-TYPE
	OBJECTS { eventIdTrap, 
		notificationIdTrap, 
		perceivedSeverityTrap, 
		timeStampTrap, 
		additionalTextTrap }
	STATUS     current
	DESCRIPTION 
		"MUX index 5"
	::= { channelBerTrapsPrefix 5 }

channelBer6Trap  NOTIFICATION-TYPE
	OBJECTS { eventIdTrap, 
		notificationIdTrap, 
		perceivedSeverityTrap, 
		timeStampTrap, 
		additionalTextTrap }
	STATUS     current
	DESCRIPTION 
		"MUX index 6"
	::= { channelBerTrapsPrefix 6 }

channelBer7Trap  NOTIFICATION-TYPE
	OBJECTS { eventIdTrap, 
		notificationIdTrap, 
		perceivedSeverityTrap, 
		timeStampTrap, 
		additionalTextTrap }
	STATUS     current
	DESCRIPTION 
		"MUX index 7"
	::= { channelBerTrapsPrefix 7 }

channelBer8Trap  NOTIFICATION-TYPE
	OBJECTS { eventIdTrap, 
		notificationIdTrap, 
		perceivedSeverityTrap, 
		timeStampTrap, 
		additionalTextTrap }
	STATUS     current
	DESCRIPTION 
		"MUX index 8"
	::= { channelBerTrapsPrefix 8 }

channelBer9Trap  NOTIFICATION-TYPE
	OBJECTS { eventIdTrap, 
		notificationIdTrap, 
		perceivedSeverityTrap, 
		timeStampTrap, 
		additionalTextTrap }
	STATUS     current
	DESCRIPTION 
		"MUX index 9"
	::= { channelBerTrapsPrefix 9 }

channelBer10Trap  NOTIFICATION-TYPE
	OBJECTS { eventIdTrap, 
		notificationIdTrap, 
		perceivedSeverityTrap, 
		timeStampTrap, 
		additionalTextTrap }
	STATUS     current
	DESCRIPTION 
		"MUX index 10"
	::= { channelBerTrapsPrefix 10 }

channelBer11Trap  NOTIFICATION-TYPE
	OBJECTS { eventIdTrap, 
		notificationIdTrap, 
		perceivedSeverityTrap, 
		timeStampTrap, 
		additionalTextTrap }
	STATUS     current
	DESCRIPTION 
		"MUX index 11"
	::= { channelBerTrapsPrefix 11 }

channelBer12Trap  NOTIFICATION-TYPE
	OBJECTS { eventIdTrap, 
		notificationIdTrap, 
		perceivedSeverityTrap, 
		timeStampTrap, 
		additionalTextTrap }
	STATUS     current
	DESCRIPTION 
		"MUX index 12"
	::= { channelBerTrapsPrefix 12 }

channelBer13Trap  NOTIFICATION-TYPE
	OBJECTS { eventIdTrap, 
		notificationIdTrap, 
		perceivedSeverityTrap, 
		timeStampTrap, 
		additionalTextTrap }
	STATUS     current
	DESCRIPTION 
		"MUX index 13"
	::= { channelBerTrapsPrefix 13 }

channelBer14Trap  NOTIFICATION-TYPE
	OBJECTS { eventIdTrap, 
		notificationIdTrap, 
		perceivedSeverityTrap, 
		timeStampTrap, 
		additionalTextTrap }
	STATUS     current
	DESCRIPTION 
		"MUX index 14"
	::= { channelBerTrapsPrefix 14 }

channelBer15Trap  NOTIFICATION-TYPE
	OBJECTS { eventIdTrap, 
		notificationIdTrap, 
		perceivedSeverityTrap, 
		timeStampTrap, 
		additionalTextTrap }
	STATUS     current
	DESCRIPTION 
		"MUX index 15"
	::= { channelBerTrapsPrefix 15 }

channelBer16Trap  NOTIFICATION-TYPE
	OBJECTS { eventIdTrap, 
		notificationIdTrap, 
		perceivedSeverityTrap, 
		timeStampTrap, 
		additionalTextTrap }
	STATUS     current
	DESCRIPTION 
		"MUX index 16"
	::= { channelBerTrapsPrefix 16 }

channelBer17Trap  NOTIFICATION-TYPE
	OBJECTS { eventIdTrap, 
		notificationIdTrap, 
		perceivedSeverityTrap, 
		timeStampTrap, 
		additionalTextTrap }
	STATUS     current
	DESCRIPTION 
		"MUX index 17"
	::= { channelBerTrapsPrefix 17 }

channelBer18Trap  NOTIFICATION-TYPE
	OBJECTS { eventIdTrap, 
		notificationIdTrap, 
		perceivedSeverityTrap, 
		timeStampTrap, 
		additionalTextTrap }
	STATUS     current
	DESCRIPTION 
		"MUX index 18"
	::= { channelBerTrapsPrefix 18 }

channelBer19Trap  NOTIFICATION-TYPE
	OBJECTS { eventIdTrap, 
		notificationIdTrap, 
		perceivedSeverityTrap, 
		timeStampTrap, 
		additionalTextTrap }
	STATUS     current
	DESCRIPTION 
		"MUX index 19"
	::= { channelBerTrapsPrefix 19 }

channelBer20Trap  NOTIFICATION-TYPE
	OBJECTS { eventIdTrap, 
		notificationIdTrap, 
		perceivedSeverityTrap, 
		timeStampTrap, 
		additionalTextTrap }
	STATUS     current
	DESCRIPTION 
		"MUX index 20"
	::= { channelBerTrapsPrefix 20 }

channelBer21Trap  NOTIFICATION-TYPE
	OBJECTS { eventIdTrap, 
		notificationIdTrap, 
		perceivedSeverityTrap, 
		timeStampTrap, 
		additionalTextTrap }
	STATUS     current
	DESCRIPTION 
		"MUX index 21"
	::= { channelBerTrapsPrefix 21 }

channelBer22Trap  NOTIFICATION-TYPE
	OBJECTS { eventIdTrap, 
		notificationIdTrap, 
		perceivedSeverityTrap, 
		timeStampTrap, 
		additionalTextTrap }
	STATUS     current
	DESCRIPTION 
		"MUX index 22"
	::= { channelBerTrapsPrefix 22 }

channelBer23Trap  NOTIFICATION-TYPE
	OBJECTS { eventIdTrap, 
		notificationIdTrap, 
		perceivedSeverityTrap, 
		timeStampTrap, 
		additionalTextTrap }
	STATUS     current
	DESCRIPTION 
		"MUX index 23"
	::= { channelBerTrapsPrefix 23 }

channelBer24Trap  NOTIFICATION-TYPE
	OBJECTS { eventIdTrap, 
		notificationIdTrap, 
		perceivedSeverityTrap, 
		timeStampTrap, 
		additionalTextTrap }
	STATUS     current
	DESCRIPTION 
		"MUX index 24"
	::= { channelBerTrapsPrefix 24 }

channelBer25Trap  NOTIFICATION-TYPE
	OBJECTS { eventIdTrap, 
		notificationIdTrap, 
		perceivedSeverityTrap, 
		timeStampTrap, 
		additionalTextTrap }
	STATUS     current
	DESCRIPTION 
		"MUX index 25"
	::= { channelBerTrapsPrefix 25 }

channelBer26Trap  NOTIFICATION-TYPE
	OBJECTS { eventIdTrap, 
		notificationIdTrap, 
		perceivedSeverityTrap, 
		timeStampTrap, 
		additionalTextTrap }
	STATUS     current
	DESCRIPTION 
		"MUX index 26"
	::= { channelBerTrapsPrefix 26 }

channelBer27Trap  NOTIFICATION-TYPE
	OBJECTS { eventIdTrap, 
		notificationIdTrap, 
		perceivedSeverityTrap, 
		timeStampTrap, 
		additionalTextTrap }
	STATUS     current
	DESCRIPTION 
		"MUX index 27"
	::= { channelBerTrapsPrefix 27 }

channelBer28Trap  NOTIFICATION-TYPE
	OBJECTS { eventIdTrap, 
		notificationIdTrap, 
		perceivedSeverityTrap, 
		timeStampTrap, 
		additionalTextTrap }
	STATUS     current
	DESCRIPTION 
		"MUX index 28"
	::= { channelBerTrapsPrefix 28 }

channelBer29Trap  NOTIFICATION-TYPE
	OBJECTS { eventIdTrap, 
		notificationIdTrap, 
		perceivedSeverityTrap, 
		timeStampTrap, 
		additionalTextTrap }
	STATUS     current
	DESCRIPTION 
		"MUX index 29"
	::= { channelBerTrapsPrefix 29 }

channelBer30Trap  NOTIFICATION-TYPE
	OBJECTS { eventIdTrap, 
		notificationIdTrap, 
		perceivedSeverityTrap, 
		timeStampTrap, 
		additionalTextTrap }
	STATUS     current
	DESCRIPTION 
		"MUX index 30"
	::= { channelBerTrapsPrefix 30 }

minorMUX1Traps  NOTIFICATION-TYPE
	OBJECTS { eventIdTrap, 
		notificationIdTrap, 
		perceivedSeverityTrap, 
		timeStampTrap, 
		additionalTextTrap }
	STATUS     current
	DESCRIPTION 
		"MUX minor OR. Index 1"
	::= { minorTrapsPrefix 1 }

minorMUX2Traps  NOTIFICATION-TYPE
	OBJECTS { eventIdTrap, 
		notificationIdTrap, 
		perceivedSeverityTrap, 
		timeStampTrap, 
		additionalTextTrap }
	STATUS     current
	DESCRIPTION 
		"MUX minor OR. Index 2"
	::= { minorTrapsPrefix 2 }

minorMUX3Traps  NOTIFICATION-TYPE
	OBJECTS { eventIdTrap, 
		notificationIdTrap, 
		perceivedSeverityTrap, 
		timeStampTrap, 
		additionalTextTrap }
	STATUS     current
	DESCRIPTION 
		"MUX minor OR. Index 3"
	::= { minorTrapsPrefix 3 }

minorMUX4Traps  NOTIFICATION-TYPE
	OBJECTS { eventIdTrap, 
		notificationIdTrap, 
		perceivedSeverityTrap, 
		timeStampTrap, 
		additionalTextTrap }
	STATUS     current
	DESCRIPTION 
		"MUX minor OR. Index 4"
	::= { minorTrapsPrefix 4 }

minorMUX5Traps  NOTIFICATION-TYPE
	OBJECTS { eventIdTrap, 
		notificationIdTrap, 
		perceivedSeverityTrap, 
		timeStampTrap, 
		additionalTextTrap }
	STATUS     current
	DESCRIPTION 
		"MUX minor OR. Index 5"
	::= { minorTrapsPrefix 5 }

minorMUX6Traps  NOTIFICATION-TYPE
	OBJECTS { eventIdTrap, 
		notificationIdTrap, 
		perceivedSeverityTrap, 
		timeStampTrap, 
		additionalTextTrap }
	STATUS     current
	DESCRIPTION 
		"MUX minor OR. Index 6"
	::= { minorTrapsPrefix 6 }

minorMUX7Traps  NOTIFICATION-TYPE
	OBJECTS { eventIdTrap, 
		notificationIdTrap, 
		perceivedSeverityTrap, 
		timeStampTrap, 
		additionalTextTrap }
	STATUS     current
	DESCRIPTION 
		"MUX minor OR. Index 7"
	::= { minorTrapsPrefix 7 }

minorMUX8Traps  NOTIFICATION-TYPE
	OBJECTS { eventIdTrap, 
		notificationIdTrap, 
		perceivedSeverityTrap, 
		timeStampTrap, 
		additionalTextTrap }
	STATUS     current
	DESCRIPTION 
		"MUX minor OR. Index 8"
	::= { minorTrapsPrefix 8 }

minorMUX9Traps  NOTIFICATION-TYPE
	OBJECTS { eventIdTrap, 
		notificationIdTrap, 
		perceivedSeverityTrap, 
		timeStampTrap, 
		additionalTextTrap }
	STATUS     current
	DESCRIPTION 
		"MUX minor OR. Index 9"
	::= { minorTrapsPrefix 9 }

minorMUX10Traps  NOTIFICATION-TYPE
	OBJECTS { eventIdTrap, 
		notificationIdTrap, 
		perceivedSeverityTrap, 
		timeStampTrap, 
		additionalTextTrap }
	STATUS     current
	DESCRIPTION 
		"MUX minor OR. Index 10"
	::= { minorTrapsPrefix 10 }

minorMUX11Traps  NOTIFICATION-TYPE
	OBJECTS { eventIdTrap, 
		notificationIdTrap, 
		perceivedSeverityTrap, 
		timeStampTrap, 
		additionalTextTrap }
	STATUS     current
	DESCRIPTION 
		"MUX minor OR. Index 11"
	::= { minorTrapsPrefix 11 }

minorMUX12Traps  NOTIFICATION-TYPE
	OBJECTS { eventIdTrap, 
		notificationIdTrap, 
		perceivedSeverityTrap, 
		timeStampTrap, 
		additionalTextTrap }
	STATUS     current
	DESCRIPTION 
		"MUX minor OR. Index 12"
	::= { minorTrapsPrefix 12 }

minorMUX13Traps  NOTIFICATION-TYPE
	OBJECTS { eventIdTrap, 
		notificationIdTrap, 
		perceivedSeverityTrap, 
		timeStampTrap, 
		additionalTextTrap }
	STATUS     current
	DESCRIPTION 
		"MUX minor OR. Index 13"
	::= { minorTrapsPrefix 13 }

minorMUX14Traps  NOTIFICATION-TYPE
	OBJECTS { eventIdTrap, 
		notificationIdTrap, 
		perceivedSeverityTrap, 
		timeStampTrap, 
		additionalTextTrap }
	STATUS     current
	DESCRIPTION 
		"MUX minor OR. Index 14"
	::= { minorTrapsPrefix 14 }

minorMUX15Traps  NOTIFICATION-TYPE
	OBJECTS { eventIdTrap, 
		notificationIdTrap, 
		perceivedSeverityTrap, 
		timeStampTrap, 
		additionalTextTrap }
	STATUS     current
	DESCRIPTION 
		"MUX minor OR. Index 15"
	::= { minorTrapsPrefix 15 }

minorUCAsTraps  NOTIFICATION-TYPE
	OBJECTS { eventIdTrap, 
		notificationIdTrap, 
		perceivedSeverityTrap, 
		timeStampTrap, 
		additionalTextTrap }
	STATUS     current
	DESCRIPTION 
		"UCAs minor OR"
	::= { minorTrapsPrefix 16 }

minorGPSTraps  NOTIFICATION-TYPE
	OBJECTS { eventIdTrap, 
		notificationIdTrap, 
		perceivedSeverityTrap, 
		timeStampTrap, 
		additionalTextTrap }
	STATUS     current
	DESCRIPTION 
		"GPS minor RR"
	::= { minorTrapsPrefix 17 }

minorMUX16Traps  NOTIFICATION-TYPE
	OBJECTS { eventIdTrap, 
		notificationIdTrap, 
		perceivedSeverityTrap, 
		timeStampTrap, 
		additionalTextTrap }
	STATUS     current
	DESCRIPTION 
		"MUX minor OR. Index 16"
	::= { minorTrapsPrefix 18 }

minorMUX17Traps  NOTIFICATION-TYPE
	OBJECTS { eventIdTrap, 
		notificationIdTrap, 
		perceivedSeverityTrap, 
		timeStampTrap, 
		additionalTextTrap }
	STATUS     current
	DESCRIPTION 
		"MUX minor OR. Index 17"
	::= { minorTrapsPrefix 19 }

minorMUX18Traps  NOTIFICATION-TYPE
	OBJECTS { eventIdTrap, 
		notificationIdTrap, 
		perceivedSeverityTrap, 
		timeStampTrap, 
		additionalTextTrap }
	STATUS     current
	DESCRIPTION 
		"MUX minor OR. Index 18"
	::= { minorTrapsPrefix 20 }

minorMUX19Traps  NOTIFICATION-TYPE
	OBJECTS { eventIdTrap, 
		notificationIdTrap, 
		perceivedSeverityTrap, 
		timeStampTrap, 
		additionalTextTrap }
	STATUS     current
	DESCRIPTION 
		"MUX minor OR. Index 19"
	::= { minorTrapsPrefix 21 }

minorMUX20Traps  NOTIFICATION-TYPE
	OBJECTS { eventIdTrap, 
		notificationIdTrap, 
		perceivedSeverityTrap, 
		timeStampTrap, 
		additionalTextTrap }
	STATUS     current
	DESCRIPTION 
		"MUX minor OR. Index 20"
	::= { minorTrapsPrefix 22 }

minorMUX21Traps  NOTIFICATION-TYPE
	OBJECTS { eventIdTrap, 
		notificationIdTrap, 
		perceivedSeverityTrap, 
		timeStampTrap, 
		additionalTextTrap }
	STATUS     current
	DESCRIPTION 
		"MUX minor OR. Index 21"
	::= { minorTrapsPrefix 23 }

minorMUX22Traps  NOTIFICATION-TYPE
	OBJECTS { eventIdTrap, 
		notificationIdTrap, 
		perceivedSeverityTrap, 
		timeStampTrap, 
		additionalTextTrap }
	STATUS     current
	DESCRIPTION 
		"MUX minor OR. Index 22"
	::= { minorTrapsPrefix 24 }

minorMUX23Traps  NOTIFICATION-TYPE
	OBJECTS { eventIdTrap, 
		notificationIdTrap, 
		perceivedSeverityTrap, 
		timeStampTrap, 
		additionalTextTrap }
	STATUS     current
	DESCRIPTION 
		"MUX minor OR. Index 23"
	::= { minorTrapsPrefix 25 }

minorMUX24Traps  NOTIFICATION-TYPE
	OBJECTS { eventIdTrap, 
		notificationIdTrap, 
		perceivedSeverityTrap, 
		timeStampTrap, 
		additionalTextTrap }
	STATUS     current
	DESCRIPTION 
		"MUX minor OR. Index 24"
	::= { minorTrapsPrefix 26 }

minorMUX25Traps  NOTIFICATION-TYPE
	OBJECTS { eventIdTrap, 
		notificationIdTrap, 
		perceivedSeverityTrap, 
		timeStampTrap, 
		additionalTextTrap }
	STATUS     current
	DESCRIPTION 
		"MUX minor OR. Index 25"
	::= { minorTrapsPrefix 27 }

minorMUX26Traps  NOTIFICATION-TYPE
	OBJECTS { eventIdTrap, 
		notificationIdTrap, 
		perceivedSeverityTrap, 
		timeStampTrap, 
		additionalTextTrap }
	STATUS     current
	DESCRIPTION 
		"MUX minor OR. Index 26"
	::= { minorTrapsPrefix 28 }

minorMUX27Traps  NOTIFICATION-TYPE
	OBJECTS { eventIdTrap, 
		notificationIdTrap, 
		perceivedSeverityTrap, 
		timeStampTrap, 
		additionalTextTrap }
	STATUS     current
	DESCRIPTION 
		"MUX minor OR. Index 27"
	::= { minorTrapsPrefix 29 }

minorMUX28Traps  NOTIFICATION-TYPE
	OBJECTS { eventIdTrap, 
		notificationIdTrap, 
		perceivedSeverityTrap, 
		timeStampTrap, 
		additionalTextTrap }
	STATUS     current
	DESCRIPTION 
		"MUX minor OR. Index 28"
	::= { minorTrapsPrefix 30 }

minorMUX29Traps  NOTIFICATION-TYPE
	OBJECTS { eventIdTrap, 
		notificationIdTrap, 
		perceivedSeverityTrap, 
		timeStampTrap, 
		additionalTextTrap }
	STATUS     current
	DESCRIPTION 
		"MUX minor OR. Index 29"
	::= { minorTrapsPrefix 31 }

minorMUX30Traps  NOTIFICATION-TYPE
	OBJECTS { eventIdTrap, 
		notificationIdTrap, 
		perceivedSeverityTrap, 
		timeStampTrap, 
		additionalTextTrap }
	STATUS     current
	DESCRIPTION 
		"MUX minor OR. Index 30"
	::= { minorTrapsPrefix 32 }

majorMUX1Traps  NOTIFICATION-TYPE
	OBJECTS { eventIdTrap, 
		notificationIdTrap, 
		perceivedSeverityTrap, 
		timeStampTrap, 
		additionalTextTrap }
	STATUS     current
	DESCRIPTION 
		"MUX major OR. Index 1"
	::= { majorTrapsPrefix 1 }

majorMUX2Traps  NOTIFICATION-TYPE
	OBJECTS { eventIdTrap, 
		notificationIdTrap, 
		perceivedSeverityTrap, 
		timeStampTrap, 
		additionalTextTrap }
	STATUS     current
	DESCRIPTION 
		"MUX major OR. Index 2"
	::= { majorTrapsPrefix 2 }

majorMUX3Traps  NOTIFICATION-TYPE
	OBJECTS { eventIdTrap, 
		notificationIdTrap, 
		perceivedSeverityTrap, 
		timeStampTrap, 
		additionalTextTrap }
	STATUS     current
	DESCRIPTION 
		"MUX major OR. Index 3"
	::= { majorTrapsPrefix 3 }

majorMUX4Traps  NOTIFICATION-TYPE
	OBJECTS { eventIdTrap, 
		notificationIdTrap, 
		perceivedSeverityTrap, 
		timeStampTrap, 
		additionalTextTrap }
	STATUS     current
	DESCRIPTION 
		"MUX major OR. Index 4"
	::= { majorTrapsPrefix 4 }

majorMUX5Traps  NOTIFICATION-TYPE
	OBJECTS { eventIdTrap, 
		notificationIdTrap, 
		perceivedSeverityTrap, 
		timeStampTrap, 
		additionalTextTrap }
	STATUS     current
	DESCRIPTION 
		"MUX major OR. Index 5"
	::= { majorTrapsPrefix 5 }

majorMUX6Traps  NOTIFICATION-TYPE
	OBJECTS { eventIdTrap, 
		notificationIdTrap, 
		perceivedSeverityTrap, 
		timeStampTrap, 
		additionalTextTrap }
	STATUS     current
	DESCRIPTION 
		"MUX major OR. Index 6"
	::= { majorTrapsPrefix 6 }

majorMUX7Traps  NOTIFICATION-TYPE
	OBJECTS { eventIdTrap, 
		notificationIdTrap, 
		perceivedSeverityTrap, 
		timeStampTrap, 
		additionalTextTrap }
	STATUS     current
	DESCRIPTION 
		"MUX major OR. Index 7"
	::= { majorTrapsPrefix 7 }

majorMUX8Traps  NOTIFICATION-TYPE
	OBJECTS { eventIdTrap, 
		notificationIdTrap, 
		perceivedSeverityTrap, 
		timeStampTrap, 
		additionalTextTrap }
	STATUS     current
	DESCRIPTION 
		"MUX major OR. Index 8"
	::= { majorTrapsPrefix 8 }

majorMUX9Traps  NOTIFICATION-TYPE
	OBJECTS { eventIdTrap, 
		notificationIdTrap, 
		perceivedSeverityTrap, 
		timeStampTrap, 
		additionalTextTrap }
	STATUS     current
	DESCRIPTION 
		"MUX major OR. Index 9"
	::= { majorTrapsPrefix 9 }

majorMUX10Traps  NOTIFICATION-TYPE
	OBJECTS { eventIdTrap, 
		notificationIdTrap, 
		perceivedSeverityTrap, 
		timeStampTrap, 
		additionalTextTrap }
	STATUS     current
	DESCRIPTION 
		"MUX major OR. Index 10"
	::= { majorTrapsPrefix 10 }

majorMUX11Traps  NOTIFICATION-TYPE
	OBJECTS { eventIdTrap, 
		notificationIdTrap, 
		perceivedSeverityTrap, 
		timeStampTrap, 
		additionalTextTrap }
	STATUS     current
	DESCRIPTION 
		"MUX major OR. Index 11"
	::= { majorTrapsPrefix 11 }

majorMUX12Traps  NOTIFICATION-TYPE
	OBJECTS { eventIdTrap, 
		notificationIdTrap, 
		perceivedSeverityTrap, 
		timeStampTrap, 
		additionalTextTrap }
	STATUS     current
	DESCRIPTION 
		"MUX major OR. Index 12"
	::= { majorTrapsPrefix 12 }

majorMUX13Traps  NOTIFICATION-TYPE
	OBJECTS { eventIdTrap, 
		notificationIdTrap, 
		perceivedSeverityTrap, 
		timeStampTrap, 
		additionalTextTrap }
	STATUS     current
	DESCRIPTION 
		"MUX major OR. Index 13"
	::= { majorTrapsPrefix 13 }

majorMUX14Traps  NOTIFICATION-TYPE
	OBJECTS { eventIdTrap, 
		notificationIdTrap, 
		perceivedSeverityTrap, 
		timeStampTrap, 
		additionalTextTrap }
	STATUS     current
	DESCRIPTION 
		"MUX major OR. Index 14"
	::= { majorTrapsPrefix 14 }

majorMUX15Traps  NOTIFICATION-TYPE
	OBJECTS { eventIdTrap, 
		notificationIdTrap, 
		perceivedSeverityTrap, 
		timeStampTrap, 
		additionalTextTrap }
	STATUS     current
	DESCRIPTION 
		"MUX major OR. Index 15"
	::= { majorTrapsPrefix 15 }

majorUCAsTraps  NOTIFICATION-TYPE
	OBJECTS { eventIdTrap, 
		notificationIdTrap, 
		perceivedSeverityTrap, 
		timeStampTrap, 
		additionalTextTrap }
	STATUS     current
	DESCRIPTION 
		"UCAs major OR"
	::= { majorTrapsPrefix 16 }

majorGPSsTraps  NOTIFICATION-TYPE
	OBJECTS { eventIdTrap, 
		notificationIdTrap, 
		perceivedSeverityTrap, 
		timeStampTrap, 
		additionalTextTrap }
	STATUS     current
	DESCRIPTION 
		"GPSs major OR"
	::= { majorTrapsPrefix 17 }

majorMUX16Traps  NOTIFICATION-TYPE
	OBJECTS { eventIdTrap, 
		notificationIdTrap, 
		perceivedSeverityTrap, 
		timeStampTrap, 
		additionalTextTrap }
	STATUS     current
	DESCRIPTION 
		"MUX major OR. Index 16"
	::= { majorTrapsPrefix 18 }

majorMUX17Traps  NOTIFICATION-TYPE
	OBJECTS { eventIdTrap, 
		notificationIdTrap, 
		perceivedSeverityTrap, 
		timeStampTrap, 
		additionalTextTrap }
	STATUS     current
	DESCRIPTION 
		"MUX major OR. Index 17"
	::= { majorTrapsPrefix 19 }

majorMUX18Traps  NOTIFICATION-TYPE
	OBJECTS { eventIdTrap, 
		notificationIdTrap, 
		perceivedSeverityTrap, 
		timeStampTrap, 
		additionalTextTrap }
	STATUS     current
	DESCRIPTION 
		"MUX major OR. Index 18"
	::= { majorTrapsPrefix 20 }

majorMUX19Traps  NOTIFICATION-TYPE
	OBJECTS { eventIdTrap, 
		notificationIdTrap, 
		perceivedSeverityTrap, 
		timeStampTrap, 
		additionalTextTrap }
	STATUS     current
	DESCRIPTION 
		"MUX major OR. Index 19"
	::= { majorTrapsPrefix 21 }

majorMUX20Traps  NOTIFICATION-TYPE
	OBJECTS { eventIdTrap, 
		notificationIdTrap, 
		perceivedSeverityTrap, 
		timeStampTrap, 
		additionalTextTrap }
	STATUS     current
	DESCRIPTION 
		"MUX major OR. Index 20"
	::= { majorTrapsPrefix 22 }

majorMUX21Traps  NOTIFICATION-TYPE
	OBJECTS { eventIdTrap, 
		notificationIdTrap, 
		perceivedSeverityTrap, 
		timeStampTrap, 
		additionalTextTrap }
	STATUS     current
	DESCRIPTION 
		"MUX major OR. Index 21"
	::= { majorTrapsPrefix 23 }

majorMUX22Traps  NOTIFICATION-TYPE
	OBJECTS { eventIdTrap, 
		notificationIdTrap, 
		perceivedSeverityTrap, 
		timeStampTrap, 
		additionalTextTrap }
	STATUS     current
	DESCRIPTION 
		"MUX major OR. Index 22"
	::= { majorTrapsPrefix 24 }

majorMUX23Traps  NOTIFICATION-TYPE
	OBJECTS { eventIdTrap, 
		notificationIdTrap, 
		perceivedSeverityTrap, 
		timeStampTrap, 
		additionalTextTrap }
	STATUS     current
	DESCRIPTION 
		"MUX major OR. Index 23"
	::= { majorTrapsPrefix 25 }

majorMUX24Traps  NOTIFICATION-TYPE
	OBJECTS { eventIdTrap, 
		notificationIdTrap, 
		perceivedSeverityTrap, 
		timeStampTrap, 
		additionalTextTrap }
	STATUS     current
	DESCRIPTION 
		"MUX major OR. Index 24"
	::= { majorTrapsPrefix 26 }

majorMUX25Traps  NOTIFICATION-TYPE
	OBJECTS { eventIdTrap, 
		notificationIdTrap, 
		perceivedSeverityTrap, 
		timeStampTrap, 
		additionalTextTrap }
	STATUS     current
	DESCRIPTION 
		"MUX major OR. Index 25"
	::= { majorTrapsPrefix 27 }

majorMUX26Traps  NOTIFICATION-TYPE
	OBJECTS { eventIdTrap, 
		notificationIdTrap, 
		perceivedSeverityTrap, 
		timeStampTrap, 
		additionalTextTrap }
	STATUS     current
	DESCRIPTION 
		"MUX major OR. Index 26"
	::= { majorTrapsPrefix 28 }

majorMUX27Traps  NOTIFICATION-TYPE
	OBJECTS { eventIdTrap, 
		notificationIdTrap, 
		perceivedSeverityTrap, 
		timeStampTrap, 
		additionalTextTrap }
	STATUS     current
	DESCRIPTION 
		"MUX major OR. Index 27"
	::= { majorTrapsPrefix 29 }

majorMUX28Traps  NOTIFICATION-TYPE
	OBJECTS { eventIdTrap, 
		notificationIdTrap, 
		perceivedSeverityTrap, 
		timeStampTrap, 
		additionalTextTrap }
	STATUS     current
	DESCRIPTION 
		"MUX major OR. Index 28"
	::= { majorTrapsPrefix 30 }

majorMUX29Traps  NOTIFICATION-TYPE
	OBJECTS { eventIdTrap, 
		notificationIdTrap, 
		perceivedSeverityTrap, 
		timeStampTrap, 
		additionalTextTrap }
	STATUS     current
	DESCRIPTION 
		"MUX major OR. Index 29"
	::= { majorTrapsPrefix 31 }

majorMUX30Traps  NOTIFICATION-TYPE
	OBJECTS { eventIdTrap, 
		notificationIdTrap, 
		perceivedSeverityTrap, 
		timeStampTrap, 
		additionalTextTrap }
	STATUS     current
	DESCRIPTION 
		"MUX major OR. Index 30"
	::= { majorTrapsPrefix 32 }

periodicTrap  NOTIFICATION-TYPE
	OBJECTS { eventIdTrap, 
		notificationIdTrap, 
		perceivedSeverityTrap, 
		timeStampTrap, 
		additionalTextTrap }
	STATUS     current
	DESCRIPTION 
		"Severity Minor (3): external relay is close
		Severity Cleared (5): external relay is open"
	::= { generalTrapsPrefix 1 }

externalSupplyTrap  NOTIFICATION-TYPE
	OBJECTS { eventIdTrap, 
		notificationIdTrap, 
		perceivedSeverityTrap, 
		timeStampTrap, 
		additionalTextTrap }
	STATUS     current
	DESCRIPTION 
		"External supply alarm"
	::= { generalTrapsPrefix 2 }

coldStartTrap  NOTIFICATION-TYPE
	OBJECTS { eventIdTrap, 
		notificationIdTrap, 
		perceivedSeverityTrap, 
		timeStampTrap, 
		additionalTextTrap }
	STATUS     current
	DESCRIPTION 
		"ColdStart traps is send it when the system up."
	::= { generalTrapsPrefix 3 }

newConfigurationFileTrap  NOTIFICATION-TYPE
	OBJECTS { eventIdTrap, 
		notificationIdTrap, 
		perceivedSeverityTrap, 
		timeStampTrap, 
		additionalTextTrap }
	STATUS     current
	DESCRIPTION 
		"New configuration file was generated."
	::= { generalTrapsPrefix 4 }

input1Traps  NOTIFICATION-TYPE
	OBJECTS { eventIdTrap, 
		notificationIdTrap, 
		perceivedSeverityTrap, 
		timeStampTrap, 
		additionalTextTrap, 
		contactsInputState }
	STATUS     current
	DESCRIPTION 
		"Input 1"
	::= { inputsContactsTrapsPrefix 1 }

input2Traps  NOTIFICATION-TYPE
	OBJECTS { eventIdTrap, 
		notificationIdTrap, 
		perceivedSeverityTrap, 
		timeStampTrap, 
		additionalTextTrap, 
		contactsInputState }
	STATUS     current
	DESCRIPTION 
		"Input 2"
	::= { inputsContactsTrapsPrefix 2 }

input3Traps  NOTIFICATION-TYPE
	OBJECTS { eventIdTrap, 
		notificationIdTrap, 
		perceivedSeverityTrap, 
		timeStampTrap, 
		additionalTextTrap, 
		contactsInputState }
	STATUS     current
	DESCRIPTION 
		"Input 3"
	::= { inputsContactsTrapsPrefix 3 }

input4Traps  NOTIFICATION-TYPE
	OBJECTS { eventIdTrap, 
		notificationIdTrap, 
		perceivedSeverityTrap, 
		timeStampTrap, 
		additionalTextTrap, 
		contactsInputState }
	STATUS     current
	DESCRIPTION 
		"Input 4"
	::= { inputsContactsTrapsPrefix 4 }

input5Traps  NOTIFICATION-TYPE
	OBJECTS { eventIdTrap, 
		notificationIdTrap, 
		perceivedSeverityTrap, 
		timeStampTrap, 
		additionalTextTrap, 
		contactsInputState }
	STATUS     current
	DESCRIPTION 
		"Input 5"
	::= { inputsContactsTrapsPrefix 5 }

input6Traps  NOTIFICATION-TYPE
	OBJECTS { eventIdTrap, 
		notificationIdTrap, 
		perceivedSeverityTrap, 
		timeStampTrap, 
		additionalTextTrap, 
		contactsInputState }
	STATUS     current
	DESCRIPTION 
		"Input 6"
	::= { inputsContactsTrapsPrefix 6 }

input7Traps  NOTIFICATION-TYPE
	OBJECTS { eventIdTrap, 
		notificationIdTrap, 
		perceivedSeverityTrap, 
		timeStampTrap, 
		additionalTextTrap, 
		contactsInputState }
	STATUS     current
	DESCRIPTION 
		"Input 7"
	::= { inputsContactsTrapsPrefix 7 }

input8Traps  NOTIFICATION-TYPE
	OBJECTS { eventIdTrap, 
		notificationIdTrap, 
		perceivedSeverityTrap, 
		timeStampTrap, 
		additionalTextTrap, 
		contactsInputState }
	STATUS     current
	DESCRIPTION 
		"Input 8"
	::= { inputsContactsTrapsPrefix 8 }

input9Traps  NOTIFICATION-TYPE
	OBJECTS { eventIdTrap, 
		notificationIdTrap, 
		perceivedSeverityTrap, 
		timeStampTrap, 
		additionalTextTrap, 
		contactsInputState }
	STATUS     current
	DESCRIPTION 
		"Input 9"
	::= { inputsContactsTrapsPrefix 9 }

input10Traps  NOTIFICATION-TYPE
	OBJECTS { eventIdTrap, 
		notificationIdTrap, 
		perceivedSeverityTrap, 
		timeStampTrap, 
		additionalTextTrap, 
		contactsInputState }
	STATUS     current
	DESCRIPTION 
		"Input 10"
	::= { inputsContactsTrapsPrefix 10 }

input11Traps  NOTIFICATION-TYPE
	OBJECTS { eventIdTrap, 
		notificationIdTrap, 
		perceivedSeverityTrap, 
		timeStampTrap, 
		additionalTextTrap, 
		contactsInputState }
	STATUS     current
	DESCRIPTION 
		"Input 11"
	::= { inputsContactsTrapsPrefix 11 }

input12Traps  NOTIFICATION-TYPE
	OBJECTS { eventIdTrap, 
		notificationIdTrap, 
		perceivedSeverityTrap, 
		timeStampTrap, 
		additionalTextTrap, 
		contactsInputState }
	STATUS     current
	DESCRIPTION 
		"Input 12"
	::= { inputsContactsTrapsPrefix 12 }

input13Traps  NOTIFICATION-TYPE
	OBJECTS { eventIdTrap, 
		notificationIdTrap, 
		perceivedSeverityTrap, 
		timeStampTrap, 
		additionalTextTrap, 
		contactsInputState }
	STATUS     current
	DESCRIPTION 
		"Input 13"
	::= { inputsContactsTrapsPrefix 13 }

input14Traps  NOTIFICATION-TYPE
	OBJECTS { eventIdTrap, 
		notificationIdTrap, 
		perceivedSeverityTrap, 
		timeStampTrap, 
		additionalTextTrap, 
		contactsInputState }
	STATUS     current
	DESCRIPTION 
		"Input 14"
	::= { inputsContactsTrapsPrefix 14 }

input15Traps  NOTIFICATION-TYPE
	OBJECTS { eventIdTrap, 
		notificationIdTrap, 
		perceivedSeverityTrap, 
		timeStampTrap, 
		additionalTextTrap, 
		contactsInputState }
	STATUS     current
	DESCRIPTION 
		"Input 15"
	::= { inputsContactsTrapsPrefix 15 }

viterbiBer1Trap  NOTIFICATION-TYPE
	OBJECTS { eventIdTrap, 
		notificationIdTrap, 
		perceivedSeverityTrap, 
		timeStampTrap, 
		additionalTextTrap }
	STATUS     current
	DESCRIPTION 
		"MUX index 1"
	::= { viterbiBerTrapsPrefix 1 }

viterbiBer2Trap  NOTIFICATION-TYPE
	OBJECTS { eventIdTrap, 
		notificationIdTrap, 
		perceivedSeverityTrap, 
		timeStampTrap, 
		additionalTextTrap }
	STATUS     current
	DESCRIPTION 
		"MUX index 2"
	::= { viterbiBerTrapsPrefix 2 }

viterbiBer3Trap  NOTIFICATION-TYPE
	OBJECTS { eventIdTrap, 
		notificationIdTrap, 
		perceivedSeverityTrap, 
		timeStampTrap, 
		additionalTextTrap }
	STATUS     current
	DESCRIPTION 
		"MUX index 3"
	::= { viterbiBerTrapsPrefix 3 }

viterbiBer4Trap  NOTIFICATION-TYPE
	OBJECTS { eventIdTrap, 
		notificationIdTrap, 
		perceivedSeverityTrap, 
		timeStampTrap, 
		additionalTextTrap }
	STATUS     current
	DESCRIPTION 
		"MUX index 4"
	::= { viterbiBerTrapsPrefix 4 }

viterbiBer5Trap  NOTIFICATION-TYPE
	OBJECTS { eventIdTrap, 
		notificationIdTrap, 
		perceivedSeverityTrap, 
		timeStampTrap, 
		additionalTextTrap }
	STATUS     current
	DESCRIPTION 
		"MUX index 5"
	::= { viterbiBerTrapsPrefix 5 }

viterbiBer6Trap  NOTIFICATION-TYPE
	OBJECTS { eventIdTrap, 
		notificationIdTrap, 
		perceivedSeverityTrap, 
		timeStampTrap, 
		additionalTextTrap }
	STATUS     current
	DESCRIPTION 
		"MUX index 6"
	::= { viterbiBerTrapsPrefix 6 }

viterbiBer7Trap  NOTIFICATION-TYPE
	OBJECTS { eventIdTrap, 
		notificationIdTrap, 
		perceivedSeverityTrap, 
		timeStampTrap, 
		additionalTextTrap }
	STATUS     current
	DESCRIPTION 
		"MUX index 7"
	::= { viterbiBerTrapsPrefix 7 }

viterbiBer8Trap  NOTIFICATION-TYPE
	OBJECTS { eventIdTrap, 
		notificationIdTrap, 
		perceivedSeverityTrap, 
		timeStampTrap, 
		additionalTextTrap }
	STATUS     current
	DESCRIPTION 
		"MUX index 8"
	::= { viterbiBerTrapsPrefix 8 }

viterbiBer9Trap  NOTIFICATION-TYPE
	OBJECTS { eventIdTrap, 
		notificationIdTrap, 
		perceivedSeverityTrap, 
		timeStampTrap, 
		additionalTextTrap }
	STATUS     current
	DESCRIPTION 
		"MUX index 9"
	::= { viterbiBerTrapsPrefix 9 }

viterbiBer10Trap  NOTIFICATION-TYPE
	OBJECTS { eventIdTrap, 
		notificationIdTrap, 
		perceivedSeverityTrap, 
		timeStampTrap, 
		additionalTextTrap }
	STATUS     current
	DESCRIPTION 
		"MUX index 10"
	::= { viterbiBerTrapsPrefix 10 }

viterbiBer11Trap  NOTIFICATION-TYPE
	OBJECTS { eventIdTrap, 
		notificationIdTrap, 
		perceivedSeverityTrap, 
		timeStampTrap, 
		additionalTextTrap }
	STATUS     current
	DESCRIPTION 
		"MUX index 11"
	::= { viterbiBerTrapsPrefix 11 }

viterbiBer12Trap  NOTIFICATION-TYPE
	OBJECTS { eventIdTrap, 
		notificationIdTrap, 
		perceivedSeverityTrap, 
		timeStampTrap, 
		additionalTextTrap }
	STATUS     current
	DESCRIPTION 
		"MUX index 12"
	::= { viterbiBerTrapsPrefix 12 }

viterbiBer13Trap  NOTIFICATION-TYPE
	OBJECTS { eventIdTrap, 
		notificationIdTrap, 
		perceivedSeverityTrap, 
		timeStampTrap, 
		additionalTextTrap }
	STATUS     current
	DESCRIPTION 
		"MUX index 13"
	::= { viterbiBerTrapsPrefix 13 }

viterbiBer14Trap  NOTIFICATION-TYPE
	OBJECTS { eventIdTrap, 
		notificationIdTrap, 
		perceivedSeverityTrap, 
		timeStampTrap, 
		additionalTextTrap }
	STATUS     current
	DESCRIPTION 
		"MUX index 14"
	::= { viterbiBerTrapsPrefix 14 }

viterbiBer15Trap  NOTIFICATION-TYPE
	OBJECTS { eventIdTrap, 
		notificationIdTrap, 
		perceivedSeverityTrap, 
		timeStampTrap, 
		additionalTextTrap }
	STATUS     current
	DESCRIPTION 
		"MUX index 15"
	::= { viterbiBerTrapsPrefix 15 }

viterbiBer16Trap  NOTIFICATION-TYPE
	OBJECTS { eventIdTrap, 
		notificationIdTrap, 
		perceivedSeverityTrap, 
		timeStampTrap, 
		additionalTextTrap }
	STATUS     current
	DESCRIPTION 
		"MUX index 16"
	::= { viterbiBerTrapsPrefix 16 }

viterbiBer17Trap  NOTIFICATION-TYPE
	OBJECTS { eventIdTrap, 
		notificationIdTrap, 
		perceivedSeverityTrap, 
		timeStampTrap, 
		additionalTextTrap }
	STATUS     current
	DESCRIPTION 
		"MUX index 17"
	::= { viterbiBerTrapsPrefix 17 }

viterbiBer18Trap  NOTIFICATION-TYPE
	OBJECTS { eventIdTrap, 
		notificationIdTrap, 
		perceivedSeverityTrap, 
		timeStampTrap, 
		additionalTextTrap }
	STATUS     current
	DESCRIPTION 
		"MUX index 18"
	::= { viterbiBerTrapsPrefix 18 }

viterbiBer19Trap  NOTIFICATION-TYPE
	OBJECTS { eventIdTrap, 
		notificationIdTrap, 
		perceivedSeverityTrap, 
		timeStampTrap, 
		additionalTextTrap }
	STATUS     current
	DESCRIPTION 
		"MUX index 19"
	::= { viterbiBerTrapsPrefix 19 }

viterbiBer20Trap  NOTIFICATION-TYPE
	OBJECTS { eventIdTrap, 
		notificationIdTrap, 
		perceivedSeverityTrap, 
		timeStampTrap, 
		additionalTextTrap }
	STATUS     current
	DESCRIPTION 
		"MUX index 20"
	::= { viterbiBerTrapsPrefix 20 }

viterbiBer21Trap  NOTIFICATION-TYPE
	OBJECTS { eventIdTrap, 
		notificationIdTrap, 
		perceivedSeverityTrap, 
		timeStampTrap, 
		additionalTextTrap }
	STATUS     current
	DESCRIPTION 
		"MUX index 21"
	::= { viterbiBerTrapsPrefix 21 }

viterbiBer22Trap  NOTIFICATION-TYPE
	OBJECTS { eventIdTrap, 
		notificationIdTrap, 
		perceivedSeverityTrap, 
		timeStampTrap, 
		additionalTextTrap }
	STATUS     current
	DESCRIPTION 
		"MUX index 22"
	::= { viterbiBerTrapsPrefix 22 }

viterbiBer23Trap  NOTIFICATION-TYPE
	OBJECTS { eventIdTrap, 
		notificationIdTrap, 
		perceivedSeverityTrap, 
		timeStampTrap, 
		additionalTextTrap }
	STATUS     current
	DESCRIPTION 
		"MUX index 23"
	::= { viterbiBerTrapsPrefix 23 }

viterbiBer24Trap  NOTIFICATION-TYPE
	OBJECTS { eventIdTrap, 
		notificationIdTrap, 
		perceivedSeverityTrap, 
		timeStampTrap, 
		additionalTextTrap }
	STATUS     current
	DESCRIPTION 
		"MUX index 24"
	::= { viterbiBerTrapsPrefix 24 }

viterbiBer25Trap  NOTIFICATION-TYPE
	OBJECTS { eventIdTrap, 
		notificationIdTrap, 
		perceivedSeverityTrap, 
		timeStampTrap, 
		additionalTextTrap }
	STATUS     current
	DESCRIPTION 
		"MUX index 25"
	::= { viterbiBerTrapsPrefix 25 }

viterbiBer26Trap  NOTIFICATION-TYPE
	OBJECTS { eventIdTrap, 
		notificationIdTrap, 
		perceivedSeverityTrap, 
		timeStampTrap, 
		additionalTextTrap }
	STATUS     current
	DESCRIPTION 
		"MUX index 26"
	::= { viterbiBerTrapsPrefix 26 }

viterbiBer27Trap  NOTIFICATION-TYPE
	OBJECTS { eventIdTrap, 
		notificationIdTrap, 
		perceivedSeverityTrap, 
		timeStampTrap, 
		additionalTextTrap }
	STATUS     current
	DESCRIPTION 
		"MUX index 27"
	::= { viterbiBerTrapsPrefix 27 }

viterbiBer28Trap  NOTIFICATION-TYPE
	OBJECTS { eventIdTrap, 
		notificationIdTrap, 
		perceivedSeverityTrap, 
		timeStampTrap, 
		additionalTextTrap }
	STATUS     current
	DESCRIPTION 
		"MUX index 28"
	::= { viterbiBerTrapsPrefix 28 }

viterbiBer29Trap  NOTIFICATION-TYPE
	OBJECTS { eventIdTrap, 
		notificationIdTrap, 
		perceivedSeverityTrap, 
		timeStampTrap, 
		additionalTextTrap }
	STATUS     current
	DESCRIPTION 
		"MUX index 29"
	::= { viterbiBerTrapsPrefix 29 }

viterbiBer30Trap  NOTIFICATION-TYPE
	OBJECTS { eventIdTrap, 
		notificationIdTrap, 
		perceivedSeverityTrap, 
		timeStampTrap, 
		additionalTextTrap }
	STATUS     current
	DESCRIPTION 
		"MUX index 30"
	::= { viterbiBerTrapsPrefix 30 }

alternativeAsi1Trap  NOTIFICATION-TYPE
	OBJECTS { eventIdTrap, 
		notificationIdTrap, 
		perceivedSeverityTrap, 
		timeStampTrap, 
		additionalTextTrap }
	STATUS     deprecated
	DESCRIPTION 
		"MUX index 1"
	::= { alternativeAsiTrapsPrefix 1 }

alternativeAsi2Trap  NOTIFICATION-TYPE
	OBJECTS { eventIdTrap, 
		notificationIdTrap, 
		perceivedSeverityTrap, 
		timeStampTrap, 
		additionalTextTrap }
	STATUS     deprecated
	DESCRIPTION 
		"MUX index 2"
	::= { alternativeAsiTrapsPrefix 2 }

alternativeAsi3Trap  NOTIFICATION-TYPE
	OBJECTS { eventIdTrap, 
		notificationIdTrap, 
		perceivedSeverityTrap, 
		timeStampTrap, 
		additionalTextTrap }
	STATUS     deprecated
	DESCRIPTION 
		"MUX index 3"
	::= { alternativeAsiTrapsPrefix 3 }

alternativeAsi4Trap  NOTIFICATION-TYPE
	OBJECTS { eventIdTrap, 
		notificationIdTrap, 
		perceivedSeverityTrap, 
		timeStampTrap, 
		additionalTextTrap }
	STATUS     deprecated
	DESCRIPTION 
		"MUX index 4"
	::= { alternativeAsiTrapsPrefix 4 }

alternativeAsi5Trap  NOTIFICATION-TYPE
	OBJECTS { eventIdTrap, 
		notificationIdTrap, 
		perceivedSeverityTrap, 
		timeStampTrap, 
		additionalTextTrap }
	STATUS     deprecated
	DESCRIPTION 
		"MUX index 5"
	::= { alternativeAsiTrapsPrefix 5 }

alternativeAsi6Trap  NOTIFICATION-TYPE
	OBJECTS { eventIdTrap, 
		notificationIdTrap, 
		perceivedSeverityTrap, 
		timeStampTrap, 
		additionalTextTrap }
	STATUS     deprecated
	DESCRIPTION 
		"MUX index 6"
	::= { alternativeAsiTrapsPrefix 6 }

alternativeAsi7Trap  NOTIFICATION-TYPE
	OBJECTS { eventIdTrap, 
		notificationIdTrap, 
		perceivedSeverityTrap, 
		timeStampTrap, 
		additionalTextTrap }
	STATUS     deprecated
	DESCRIPTION 
		"MUX index 7"
	::= { alternativeAsiTrapsPrefix 7 }

alternativeAsi8Trap  NOTIFICATION-TYPE
	OBJECTS { eventIdTrap, 
		notificationIdTrap, 
		perceivedSeverityTrap, 
		timeStampTrap, 
		additionalTextTrap }
	STATUS     deprecated
	DESCRIPTION 
		"MUX index 8"
	::= { alternativeAsiTrapsPrefix 8 }

alternativeAsi9Trap  NOTIFICATION-TYPE
	OBJECTS { eventIdTrap, 
		notificationIdTrap, 
		perceivedSeverityTrap, 
		timeStampTrap, 
		additionalTextTrap }
	STATUS     deprecated
	DESCRIPTION 
		"MUX index 9"
	::= { alternativeAsiTrapsPrefix 9 }

alternativeAsi10Trap  NOTIFICATION-TYPE
	OBJECTS { eventIdTrap, 
		notificationIdTrap, 
		perceivedSeverityTrap, 
		timeStampTrap, 
		additionalTextTrap }
	STATUS     deprecated
	DESCRIPTION 
		"MUX index 10"
	::= { alternativeAsiTrapsPrefix 10 }

alternativeAsi11Trap  NOTIFICATION-TYPE
	OBJECTS { eventIdTrap, 
		notificationIdTrap, 
		perceivedSeverityTrap, 
		timeStampTrap, 
		additionalTextTrap }
	STATUS     deprecated
	DESCRIPTION 
		"MUX index 11"
	::= { alternativeAsiTrapsPrefix 11 }

alternativeAsi12Trap  NOTIFICATION-TYPE
	OBJECTS { eventIdTrap, 
		notificationIdTrap, 
		perceivedSeverityTrap, 
		timeStampTrap, 
		additionalTextTrap }
	STATUS     deprecated
	DESCRIPTION 
		"MUX index 12"
	::= { alternativeAsiTrapsPrefix 12 }

alternativeAsi13Trap  NOTIFICATION-TYPE
	OBJECTS { eventIdTrap, 
		notificationIdTrap, 
		perceivedSeverityTrap, 
		timeStampTrap, 
		additionalTextTrap }
	STATUS     deprecated
	DESCRIPTION 
		"MUX index 13"
	::= { alternativeAsiTrapsPrefix 13 }

alternativeAsi14Trap  NOTIFICATION-TYPE
	OBJECTS { eventIdTrap, 
		notificationIdTrap, 
		perceivedSeverityTrap, 
		timeStampTrap, 
		additionalTextTrap }
	STATUS     deprecated
	DESCRIPTION 
		"MUX index 14"
	::= { alternativeAsiTrapsPrefix 14 }

alternativeAsi15Trap  NOTIFICATION-TYPE
	OBJECTS { eventIdTrap, 
		notificationIdTrap, 
		perceivedSeverityTrap, 
		timeStampTrap, 
		additionalTextTrap }
	STATUS     deprecated
	DESCRIPTION 
		"MUX index 15"
	::= { alternativeAsiTrapsPrefix 15 }

alternativeAsi16Trap  NOTIFICATION-TYPE
	OBJECTS { eventIdTrap, 
		notificationIdTrap, 
		perceivedSeverityTrap, 
		timeStampTrap, 
		additionalTextTrap }
	STATUS     deprecated
	DESCRIPTION 
		"MUX index 16"
	::= { alternativeAsiTrapsPrefix 16 }

alternativeAsi17Trap  NOTIFICATION-TYPE
	OBJECTS { eventIdTrap, 
		notificationIdTrap, 
		perceivedSeverityTrap, 
		timeStampTrap, 
		additionalTextTrap }
	STATUS     deprecated
	DESCRIPTION 
		"MUX index 17"
	::= { alternativeAsiTrapsPrefix 17 }

alternativeAsi18Trap  NOTIFICATION-TYPE
	OBJECTS { eventIdTrap, 
		notificationIdTrap, 
		perceivedSeverityTrap, 
		timeStampTrap, 
		additionalTextTrap }
	STATUS     deprecated
	DESCRIPTION 
		"MUX index 18"
	::= { alternativeAsiTrapsPrefix 18 }

alternativeAsi19Trap  NOTIFICATION-TYPE
	OBJECTS { eventIdTrap, 
		notificationIdTrap, 
		perceivedSeverityTrap, 
		timeStampTrap, 
		additionalTextTrap }
	STATUS     deprecated
	DESCRIPTION 
		"MUX index 19"
	::= { alternativeAsiTrapsPrefix 19 }

alternativeAsi20Trap  NOTIFICATION-TYPE
	OBJECTS { eventIdTrap, 
		notificationIdTrap, 
		perceivedSeverityTrap, 
		timeStampTrap, 
		additionalTextTrap }
	STATUS     deprecated
	DESCRIPTION 
		"MUX index 20"
	::= { alternativeAsiTrapsPrefix 20 }

alternativeAsi21Trap  NOTIFICATION-TYPE
	OBJECTS { eventIdTrap, 
		notificationIdTrap, 
		perceivedSeverityTrap, 
		timeStampTrap, 
		additionalTextTrap }
	STATUS     deprecated
	DESCRIPTION 
		"MUX index 21"
	::= { alternativeAsiTrapsPrefix 21 }

alternativeAsi22Trap  NOTIFICATION-TYPE
	OBJECTS { eventIdTrap, 
		notificationIdTrap, 
		perceivedSeverityTrap, 
		timeStampTrap, 
		additionalTextTrap }
	STATUS     deprecated
	DESCRIPTION 
		"MUX index 22"
	::= { alternativeAsiTrapsPrefix 22 }

alternativeAsi23Trap  NOTIFICATION-TYPE
	OBJECTS { eventIdTrap, 
		notificationIdTrap, 
		perceivedSeverityTrap, 
		timeStampTrap, 
		additionalTextTrap }
	STATUS     deprecated
	DESCRIPTION 
		"MUX index 23"
	::= { alternativeAsiTrapsPrefix 23 }

alternativeAsi24Trap  NOTIFICATION-TYPE
	OBJECTS { eventIdTrap, 
		notificationIdTrap, 
		perceivedSeverityTrap, 
		timeStampTrap, 
		additionalTextTrap }
	STATUS     deprecated
	DESCRIPTION 
		"MUX index 24"
	::= { alternativeAsiTrapsPrefix 24 }

alternativeAsi25Trap  NOTIFICATION-TYPE
	OBJECTS { eventIdTrap, 
		notificationIdTrap, 
		perceivedSeverityTrap, 
		timeStampTrap, 
		additionalTextTrap }
	STATUS     deprecated
	DESCRIPTION 
		"MUX index 25"
	::= { alternativeAsiTrapsPrefix 25 }

alternativeAsi26Trap  NOTIFICATION-TYPE
	OBJECTS { eventIdTrap, 
		notificationIdTrap, 
		perceivedSeverityTrap, 
		timeStampTrap, 
		additionalTextTrap }
	STATUS     deprecated
	DESCRIPTION 
		"MUX index 26"
	::= { alternativeAsiTrapsPrefix 26 }

alternativeAsi27Trap  NOTIFICATION-TYPE
	OBJECTS { eventIdTrap, 
		notificationIdTrap, 
		perceivedSeverityTrap, 
		timeStampTrap, 
		additionalTextTrap }
	STATUS     deprecated
	DESCRIPTION 
		"MUX index 27"
	::= { alternativeAsiTrapsPrefix 27 }

alternativeAsi28Trap  NOTIFICATION-TYPE
	OBJECTS { eventIdTrap, 
		notificationIdTrap, 
		perceivedSeverityTrap, 
		timeStampTrap, 
		additionalTextTrap }
	STATUS     deprecated
	DESCRIPTION 
		"MUX index 28"
	::= { alternativeAsiTrapsPrefix 28 }

alternativeAsi29Trap  NOTIFICATION-TYPE
	OBJECTS { eventIdTrap, 
		notificationIdTrap, 
		perceivedSeverityTrap, 
		timeStampTrap, 
		additionalTextTrap }
	STATUS     deprecated
	DESCRIPTION 
		"MUX index 29"
	::= { alternativeAsiTrapsPrefix 29 }

alternativeAsi30Trap  NOTIFICATION-TYPE
	OBJECTS { eventIdTrap, 
		notificationIdTrap, 
		perceivedSeverityTrap, 
		timeStampTrap, 
		additionalTextTrap }
	STATUS     deprecated
	DESCRIPTION 
		"MUX index 30"
	::= { alternativeAsiTrapsPrefix 30 }

adaptativeEcho1Trap  NOTIFICATION-TYPE
	OBJECTS { eventIdTrap, 
		notificationIdTrap, 
		perceivedSeverityTrap, 
		timeStampTrap, 
		additionalTextTrap }
	STATUS     current
	DESCRIPTION 
		"MUX index 1"
	::= { adaptativeEchoTrapsPrefix 1 }

adaptativeEcho2Trap  NOTIFICATION-TYPE
	OBJECTS { eventIdTrap, 
		notificationIdTrap, 
		perceivedSeverityTrap, 
		timeStampTrap, 
		additionalTextTrap }
	STATUS     current
	DESCRIPTION 
		"MUX index 2"
	::= { adaptativeEchoTrapsPrefix 2 }

adaptativeEcho3Trap  NOTIFICATION-TYPE
	OBJECTS { eventIdTrap, 
		notificationIdTrap, 
		perceivedSeverityTrap, 
		timeStampTrap, 
		additionalTextTrap }
	STATUS     current
	DESCRIPTION 
		"MUX index 3"
	::= { adaptativeEchoTrapsPrefix 3 }

adaptativeEcho4Trap  NOTIFICATION-TYPE
	OBJECTS { eventIdTrap, 
		notificationIdTrap, 
		perceivedSeverityTrap, 
		timeStampTrap, 
		additionalTextTrap }
	STATUS     current
	DESCRIPTION 
		"MUX index 4"
	::= { adaptativeEchoTrapsPrefix 4 }

adaptativeEcho5Trap  NOTIFICATION-TYPE
	OBJECTS { eventIdTrap, 
		notificationIdTrap, 
		perceivedSeverityTrap, 
		timeStampTrap, 
		additionalTextTrap }
	STATUS     current
	DESCRIPTION 
		"MUX index 5"
	::= { adaptativeEchoTrapsPrefix 5 }

adaptativeEcho6Trap  NOTIFICATION-TYPE
	OBJECTS { eventIdTrap, 
		notificationIdTrap, 
		perceivedSeverityTrap, 
		timeStampTrap, 
		additionalTextTrap }
	STATUS     current
	DESCRIPTION 
		"MUX index 6"
	::= { adaptativeEchoTrapsPrefix 6 }

adaptativeEcho7Trap  NOTIFICATION-TYPE
	OBJECTS { eventIdTrap, 
		notificationIdTrap, 
		perceivedSeverityTrap, 
		timeStampTrap, 
		additionalTextTrap }
	STATUS     current
	DESCRIPTION 
		"MUX index 7"
	::= { adaptativeEchoTrapsPrefix 7 }

adaptativeEcho8Trap  NOTIFICATION-TYPE
	OBJECTS { eventIdTrap, 
		notificationIdTrap, 
		perceivedSeverityTrap, 
		timeStampTrap, 
		additionalTextTrap }
	STATUS     current
	DESCRIPTION 
		"MUX index 8"
	::= { adaptativeEchoTrapsPrefix 8 }

adaptativeEcho9Trap  NOTIFICATION-TYPE
	OBJECTS { eventIdTrap, 
		notificationIdTrap, 
		perceivedSeverityTrap, 
		timeStampTrap, 
		additionalTextTrap }
	STATUS     current
	DESCRIPTION 
		"MUX index 9"
	::= { adaptativeEchoTrapsPrefix 9 }

adaptativeEcho10Trap  NOTIFICATION-TYPE
	OBJECTS { eventIdTrap, 
		notificationIdTrap, 
		perceivedSeverityTrap, 
		timeStampTrap, 
		additionalTextTrap }
	STATUS     current
	DESCRIPTION 
		"MUX index 10"
	::= { adaptativeEchoTrapsPrefix 10 }

adaptativeEcho11Trap  NOTIFICATION-TYPE
	OBJECTS { eventIdTrap, 
		notificationIdTrap, 
		perceivedSeverityTrap, 
		timeStampTrap, 
		additionalTextTrap }
	STATUS     current
	DESCRIPTION 
		"MUX index 11"
	::= { adaptativeEchoTrapsPrefix 11 }

adaptativeEcho12Trap  NOTIFICATION-TYPE
	OBJECTS { eventIdTrap, 
		notificationIdTrap, 
		perceivedSeverityTrap, 
		timeStampTrap, 
		additionalTextTrap }
	STATUS     current
	DESCRIPTION 
		"MUX index 12"
	::= { adaptativeEchoTrapsPrefix 12 }

adaptativeEcho13Trap  NOTIFICATION-TYPE
	OBJECTS { eventIdTrap, 
		notificationIdTrap, 
		perceivedSeverityTrap, 
		timeStampTrap, 
		additionalTextTrap }
	STATUS     current
	DESCRIPTION 
		"MUX index 13"
	::= { adaptativeEchoTrapsPrefix 13 }

adaptativeEcho14Trap  NOTIFICATION-TYPE
	OBJECTS { eventIdTrap, 
		notificationIdTrap, 
		perceivedSeverityTrap, 
		timeStampTrap, 
		additionalTextTrap }
	STATUS     current
	DESCRIPTION 
		"MUX index 14"
	::= { adaptativeEchoTrapsPrefix 14 }

adaptativeEcho15Trap  NOTIFICATION-TYPE
	OBJECTS { eventIdTrap, 
		notificationIdTrap, 
		perceivedSeverityTrap, 
		timeStampTrap, 
		additionalTextTrap }
	STATUS     current
	DESCRIPTION 
		"MUX index 15"
	::= { adaptativeEchoTrapsPrefix 15 }

adaptativeEcho16Trap  NOTIFICATION-TYPE
	OBJECTS { eventIdTrap, 
		notificationIdTrap, 
		perceivedSeverityTrap, 
		timeStampTrap, 
		additionalTextTrap }
	STATUS     current
	DESCRIPTION 
		"MUX index 16"
	::= { adaptativeEchoTrapsPrefix 16 }

adaptativeEcho17Trap  NOTIFICATION-TYPE
	OBJECTS { eventIdTrap, 
		notificationIdTrap, 
		perceivedSeverityTrap, 
		timeStampTrap, 
		additionalTextTrap }
	STATUS     current
	DESCRIPTION 
		"MUX index 17"
	::= { adaptativeEchoTrapsPrefix 17 }

adaptativeEcho18Trap  NOTIFICATION-TYPE
	OBJECTS { eventIdTrap, 
		notificationIdTrap, 
		perceivedSeverityTrap, 
		timeStampTrap, 
		additionalTextTrap }
	STATUS     current
	DESCRIPTION 
		"MUX index 18"
	::= { adaptativeEchoTrapsPrefix 18 }

adaptativeEcho19Trap  NOTIFICATION-TYPE
	OBJECTS { eventIdTrap, 
		notificationIdTrap, 
		perceivedSeverityTrap, 
		timeStampTrap, 
		additionalTextTrap }
	STATUS     current
	DESCRIPTION 
		"MUX index 19"
	::= { adaptativeEchoTrapsPrefix 19 }

adaptativeEcho20Trap  NOTIFICATION-TYPE
	OBJECTS { eventIdTrap, 
		notificationIdTrap, 
		perceivedSeverityTrap, 
		timeStampTrap, 
		additionalTextTrap }
	STATUS     current
	DESCRIPTION 
		"MUX index 20"
	::= { adaptativeEchoTrapsPrefix 20 }

adaptativeEcho21Trap  NOTIFICATION-TYPE
	OBJECTS { eventIdTrap, 
		notificationIdTrap, 
		perceivedSeverityTrap, 
		timeStampTrap, 
		additionalTextTrap }
	STATUS     current
	DESCRIPTION 
		"MUX index 21"
	::= { adaptativeEchoTrapsPrefix 21 }

adaptativeEcho22Trap  NOTIFICATION-TYPE
	OBJECTS { eventIdTrap, 
		notificationIdTrap, 
		perceivedSeverityTrap, 
		timeStampTrap, 
		additionalTextTrap }
	STATUS     current
	DESCRIPTION 
		"MUX index 22"
	::= { adaptativeEchoTrapsPrefix 22 }

adaptativeEcho23Trap  NOTIFICATION-TYPE
	OBJECTS { eventIdTrap, 
		notificationIdTrap, 
		perceivedSeverityTrap, 
		timeStampTrap, 
		additionalTextTrap }
	STATUS     current
	DESCRIPTION 
		"MUX index 23"
	::= { adaptativeEchoTrapsPrefix 23 }

adaptativeEcho24Trap  NOTIFICATION-TYPE
	OBJECTS { eventIdTrap, 
		notificationIdTrap, 
		perceivedSeverityTrap, 
		timeStampTrap, 
		additionalTextTrap }
	STATUS     current
	DESCRIPTION 
		"MUX index 24"
	::= { adaptativeEchoTrapsPrefix 24 }

adaptativeEcho25Trap  NOTIFICATION-TYPE
	OBJECTS { eventIdTrap, 
		notificationIdTrap, 
		perceivedSeverityTrap, 
		timeStampTrap, 
		additionalTextTrap }
	STATUS     current
	DESCRIPTION 
		"MUX index 25"
	::= { adaptativeEchoTrapsPrefix 25 }

adaptativeEcho26Trap  NOTIFICATION-TYPE
	OBJECTS { eventIdTrap, 
		notificationIdTrap, 
		perceivedSeverityTrap, 
		timeStampTrap, 
		additionalTextTrap }
	STATUS     current
	DESCRIPTION 
		"MUX index 26"
	::= { adaptativeEchoTrapsPrefix 26 }

adaptativeEcho27Trap  NOTIFICATION-TYPE
	OBJECTS { eventIdTrap, 
		notificationIdTrap, 
		perceivedSeverityTrap, 
		timeStampTrap, 
		additionalTextTrap }
	STATUS     current
	DESCRIPTION 
		"MUX index 27"
	::= { adaptativeEchoTrapsPrefix 27 }

adaptativeEcho28Trap  NOTIFICATION-TYPE
	OBJECTS { eventIdTrap, 
		notificationIdTrap, 
		perceivedSeverityTrap, 
		timeStampTrap, 
		additionalTextTrap }
	STATUS     current
	DESCRIPTION 
		"MUX index 28"
	::= { adaptativeEchoTrapsPrefix 28 }

adaptativeEcho29Trap  NOTIFICATION-TYPE
	OBJECTS { eventIdTrap, 
		notificationIdTrap, 
		perceivedSeverityTrap, 
		timeStampTrap, 
		additionalTextTrap }
	STATUS     current
	DESCRIPTION 
		"MUX index 29"
	::= { adaptativeEchoTrapsPrefix 29 }

adaptativeEcho30Trap  NOTIFICATION-TYPE
	OBJECTS { eventIdTrap, 
		notificationIdTrap, 
		perceivedSeverityTrap, 
		timeStampTrap, 
		additionalTextTrap }
	STATUS     current
	DESCRIPTION 
		"MUX index 30"
	::= { adaptativeEchoTrapsPrefix 30 }

n1conmutation1Trap  NOTIFICATION-TYPE
	OBJECTS { eventIdTrap, 
		notificationIdTrap, 
		perceivedSeverityTrap, 
		timeStampTrap, 
		additionalTextTrap }
	STATUS     current
	DESCRIPTION 
		"Relay 1 conmutation"
	::= { n1conmutationTrapsPrefix 1 }

n1conmutation2Trap  NOTIFICATION-TYPE
	OBJECTS { eventIdTrap, 
		notificationIdTrap, 
		perceivedSeverityTrap, 
		timeStampTrap, 
		additionalTextTrap }
	STATUS     current
	DESCRIPTION 
		"Relay 2 conmutation"
	::= { n1conmutationTrapsPrefix 2 }

n1conmutation3Trap  NOTIFICATION-TYPE
	OBJECTS { eventIdTrap, 
		notificationIdTrap, 
		perceivedSeverityTrap, 
		timeStampTrap, 
		additionalTextTrap }
	STATUS     current
	DESCRIPTION 
		"Relay 3 conmutation"
	::= { n1conmutationTrapsPrefix 3 }

n1conmutation4Trap  NOTIFICATION-TYPE
	OBJECTS { eventIdTrap, 
		notificationIdTrap, 
		perceivedSeverityTrap, 
		timeStampTrap, 
		additionalTextTrap }
	STATUS     current
	DESCRIPTION 
		"Relay 4 conmutation"
	::= { n1conmutationTrapsPrefix 4 }

n1conmutation5Trap  NOTIFICATION-TYPE
	OBJECTS { eventIdTrap, 
		notificationIdTrap, 
		perceivedSeverityTrap, 
		timeStampTrap, 
		additionalTextTrap }
	STATUS     current
	DESCRIPTION 
		"Relay 5 conmutation"
	::= { n1conmutationTrapsPrefix 5 }

n1conmutation6Trap  NOTIFICATION-TYPE
	OBJECTS { eventIdTrap, 
		notificationIdTrap, 
		perceivedSeverityTrap, 
		timeStampTrap, 
		additionalTextTrap }
	STATUS     current
	DESCRIPTION 
		"Relay 6 conmutation"
	::= { n1conmutationTrapsPrefix 6 }

localTrap  NOTIFICATION-TYPE
	OBJECTS { eventIdTrap, 
		notificationIdTrap, 
		perceivedSeverityTrap, 
		timeStampTrap, 
		additionalTextTrap }
	STATUS     deprecated
	DESCRIPTION 
		"UCA n+1 is in local mode"
	::= { ucaN1TrapsPrefix 1 }

generalAlarmTrap  NOTIFICATION-TYPE
	OBJECTS { eventIdTrap, 
		notificationIdTrap, 
		perceivedSeverityTrap, 
		timeStampTrap, 
		additionalTextTrap }
	STATUS     deprecated
	DESCRIPTION 
		"General alarm in the conmutation system"
	::= { ucaN1TrapsPrefix 2 }

manualTrap  NOTIFICATION-TYPE
	OBJECTS { eventIdTrap, 
		notificationIdTrap, 
		perceivedSeverityTrap, 
		timeStampTrap, 
		additionalTextTrap }
	STATUS     deprecated
	DESCRIPTION 
		"UCA n+1 is in manual mode"
	::= { ucaN1TrapsPrefix 3 }

noPriorityTrap  NOTIFICATION-TYPE
	OBJECTS { eventIdTrap, 
		notificationIdTrap, 
		perceivedSeverityTrap, 
		timeStampTrap, 
		additionalTextTrap }
	STATUS     deprecated
	DESCRIPTION 
		"UCA n+1 is working without priorities"
	::= { ucaN1TrapsPrefix 4 }

ucanCommunicationTrap  NOTIFICATION-TYPE
	OBJECTS { eventIdTrap, 
		notificationIdTrap, 
		perceivedSeverityTrap, 
		timeStampTrap, 
		additionalTextTrap }
	STATUS     deprecated
	DESCRIPTION 
		"There are communication problems with UCA n+1"
	::= { ucaN1TrapsPrefix 5 }

reservationModuleTrap  NOTIFICATION-TYPE
	OBJECTS { eventIdTrap, 
		notificationIdTrap, 
		perceivedSeverityTrap, 
		timeStampTrap, 
		additionalTextTrap }
	STATUS     deprecated
	DESCRIPTION 
		"There are problems with reservation module during conmutation."
	::= { ucaN1TrapsPrefix 6 }

uca101BlockedATrap  NOTIFICATION-TYPE
	OBJECTS { eventIdTrap, 
		notificationIdTrap, 
		perceivedSeverityTrap, 
		timeStampTrap, 
		additionalTextTrap }
	STATUS     current
	DESCRIPTION 
		"Relay is blocked in A position. Index 1."
	::= { uca101TrapsPrefix 1 }

uca101BlockedBTrap  NOTIFICATION-TYPE
	OBJECTS { eventIdTrap, 
		notificationIdTrap, 
		perceivedSeverityTrap, 
		timeStampTrap, 
		additionalTextTrap }
	STATUS     current
	DESCRIPTION 
		"Relay is blocked in B position. Index 1."
	::= { uca101TrapsPrefix 2 }

uca101UndeterminatedPositionTrap  NOTIFICATION-TYPE
	OBJECTS { eventIdTrap, 
		notificationIdTrap, 
		perceivedSeverityTrap, 
		timeStampTrap, 
		additionalTextTrap }
	STATUS     current
	DESCRIPTION 
		"Relay position is unknown.  Index 1."
	::= { uca101TrapsPrefix 3 }

uca101IncorrectConfigurationTrap  NOTIFICATION-TYPE
	OBJECTS { eventIdTrap, 
		notificationIdTrap, 
		perceivedSeverityTrap, 
		timeStampTrap, 
		additionalTextTrap }
	STATUS     current
	DESCRIPTION 
		"The MUX A type is not the same that MUX B type. Index 1."
	::= { uca101TrapsPrefix 4 }

uca101ConmutationErrorTrap  NOTIFICATION-TYPE
	OBJECTS { eventIdTrap, 
		notificationIdTrap, 
		perceivedSeverityTrap, 
		timeStampTrap, 
		additionalTextTrap }
	STATUS     current
	DESCRIPTION 
		"UCA 1+1 conmutation error. It was impossible to finish all conmutation process. Index 1."
	::= { uca101TrapsPrefix 5 }

uca101MuxATrap  NOTIFICATION-TYPE
	OBJECTS { eventIdTrap, 
		notificationIdTrap, 
		perceivedSeverityTrap, 
		timeStampTrap, 
		additionalTextTrap }
	STATUS     current
	DESCRIPTION 
		"During conmutation process, it was not possible configure MUX A.
		There are not communication with MUX A. Index 1."
	::= { uca101TrapsPrefix 6 }

uca101MuxBTrap  NOTIFICATION-TYPE
	OBJECTS { eventIdTrap, 
		notificationIdTrap, 
		perceivedSeverityTrap, 
		timeStampTrap, 
		additionalTextTrap }
	STATUS     current
	DESCRIPTION 
		"During conmutation process, it was not possible configure MUX B.
		There are not communication with MUX B. Index 1."
	::= { uca101TrapsPrefix 7 }

uca101ConmutationTrap  NOTIFICATION-TYPE
	OBJECTS { eventIdTrap, 
		notificationIdTrap, 
		perceivedSeverityTrap, 
		timeStampTrap, 
		additionalTextTrap }
	STATUS     current
	DESCRIPTION 
		"Conmutation event. Index 1."
	::= { uca101TrapsPrefix 8 }

uca102BlockedATrap  NOTIFICATION-TYPE
	OBJECTS { eventIdTrap, 
		notificationIdTrap, 
		perceivedSeverityTrap, 
		timeStampTrap, 
		additionalTextTrap }
	STATUS     current
	DESCRIPTION 
		"Relay is blocked in A position. Index 2."
	::= { uca102TrapsPrefix 1 }

uca102BlockedBTrap  NOTIFICATION-TYPE
	OBJECTS { eventIdTrap, 
		notificationIdTrap, 
		perceivedSeverityTrap, 
		timeStampTrap, 
		additionalTextTrap }
	STATUS     current
	DESCRIPTION 
		"Relay is blocked in B position. Index 2."
	::= { uca102TrapsPrefix 2 }

uca102UndeterminatedPositionTrap  NOTIFICATION-TYPE
	OBJECTS { eventIdTrap, 
		notificationIdTrap, 
		perceivedSeverityTrap, 
		timeStampTrap, 
		additionalTextTrap }
	STATUS     current
	DESCRIPTION 
		"Relay position is unknown.  Index 2."
	::= { uca102TrapsPrefix 3 }

uca102IncorrectConfigurationTrap  NOTIFICATION-TYPE
	OBJECTS { eventIdTrap, 
		notificationIdTrap, 
		perceivedSeverityTrap, 
		timeStampTrap, 
		additionalTextTrap }
	STATUS     current
	DESCRIPTION 
		"The MUX A type is not the same that MUX B type. Index 2."
	::= { uca102TrapsPrefix 4 }

uca102ConmutationErrorTrap  NOTIFICATION-TYPE
	OBJECTS { eventIdTrap, 
		notificationIdTrap, 
		perceivedSeverityTrap, 
		timeStampTrap, 
		additionalTextTrap }
	STATUS     current
	DESCRIPTION 
		"UCA 1+1 conmutation error. It was impossible to finish all conmutation process. Index 2."
	::= { uca102TrapsPrefix 5 }

uca102MuxATrap  NOTIFICATION-TYPE
	OBJECTS { eventIdTrap, 
		notificationIdTrap, 
		perceivedSeverityTrap, 
		timeStampTrap, 
		additionalTextTrap }
	STATUS     current
	DESCRIPTION 
		"During conmutation process, it was not possible configure MUX A.
		There are not communication with MUX A. Index 2."
	::= { uca102TrapsPrefix 6 }

uca102MuxBTrap  NOTIFICATION-TYPE
	OBJECTS { eventIdTrap, 
		notificationIdTrap, 
		perceivedSeverityTrap, 
		timeStampTrap, 
		additionalTextTrap }
	STATUS     current
	DESCRIPTION 
		"During conmutation process, it was not possible configure MUX B.
		There are not communication with MUX B. Index 2."
	::= { uca102TrapsPrefix 7 }

uca102ConmutationTrap  NOTIFICATION-TYPE
	OBJECTS { eventIdTrap, 
		notificationIdTrap, 
		perceivedSeverityTrap, 
		timeStampTrap, 
		additionalTextTrap }
	STATUS     current
	DESCRIPTION 
		"Conmutation event. Index 2."
	::= { uca102TrapsPrefix 8 }

uca103BlockedATrap  NOTIFICATION-TYPE
	OBJECTS { eventIdTrap, 
		notificationIdTrap, 
		perceivedSeverityTrap, 
		timeStampTrap, 
		additionalTextTrap }
	STATUS     current
	DESCRIPTION 
		"Relay is blocked in A position. Index 3."
	::= { uca103TrapsPrefix 1 }

uca103BlockedBTrap  NOTIFICATION-TYPE
	OBJECTS { eventIdTrap, 
		notificationIdTrap, 
		perceivedSeverityTrap, 
		timeStampTrap, 
		additionalTextTrap }
	STATUS     current
	DESCRIPTION 
		"Relay is blocked in B position. Index 3."
	::= { uca103TrapsPrefix 2 }

uca103UndeterminatedPositionTrap  NOTIFICATION-TYPE
	OBJECTS { eventIdTrap, 
		notificationIdTrap, 
		perceivedSeverityTrap, 
		timeStampTrap, 
		additionalTextTrap }
	STATUS     current
	DESCRIPTION 
		"Relay position is unknown.  Index 3."
	::= { uca103TrapsPrefix 3 }

uca103IncorrectConfigurationTrap  NOTIFICATION-TYPE
	OBJECTS { eventIdTrap, 
		notificationIdTrap, 
		perceivedSeverityTrap, 
		timeStampTrap, 
		additionalTextTrap }
	STATUS     current
	DESCRIPTION 
		"The MUX A type is not the same that MUX B type. Index 3."
	::= { uca103TrapsPrefix 4 }

uca103ConmutationErrorTrap  NOTIFICATION-TYPE
	OBJECTS { eventIdTrap, 
		notificationIdTrap, 
		perceivedSeverityTrap, 
		timeStampTrap, 
		additionalTextTrap }
	STATUS     current
	DESCRIPTION 
		"UCA 1+1 conmutation error. It was impossible to finish all conmutation process. Index 3."
	::= { uca103TrapsPrefix 5 }

uca103MuxATrap  NOTIFICATION-TYPE
	OBJECTS { eventIdTrap, 
		notificationIdTrap, 
		perceivedSeverityTrap, 
		timeStampTrap, 
		additionalTextTrap }
	STATUS     current
	DESCRIPTION 
		"During conmutation process, it was not possible configure MUX A.
		There are not communication with MUX A. Index 3."
	::= { uca103TrapsPrefix 6 }

uca103MuxBTrap  NOTIFICATION-TYPE
	OBJECTS { eventIdTrap, 
		notificationIdTrap, 
		perceivedSeverityTrap, 
		timeStampTrap, 
		additionalTextTrap }
	STATUS     current
	DESCRIPTION 
		"During conmutation process, it was not possible configure MUX B.
		There are not communication with MUX B. Index 3."
	::= { uca103TrapsPrefix 7 }

uca103ConmutationTrap  NOTIFICATION-TYPE
	OBJECTS { eventIdTrap, 
		notificationIdTrap, 
		perceivedSeverityTrap, 
		timeStampTrap, 
		additionalTextTrap }
	STATUS     current
	DESCRIPTION 
		"Conmutation event. Index 3."
	::= { uca103TrapsPrefix 8 }

uca104BlockedATrap  NOTIFICATION-TYPE
	OBJECTS { eventIdTrap, 
		notificationIdTrap, 
		perceivedSeverityTrap, 
		timeStampTrap, 
		additionalTextTrap }
	STATUS     current
	DESCRIPTION 
		"Relay is blocked in A position. Index 4."
	::= { uca104TrapsPrefix 1 }

uca104BlockedBTrap  NOTIFICATION-TYPE
	OBJECTS { eventIdTrap, 
		notificationIdTrap, 
		perceivedSeverityTrap, 
		timeStampTrap, 
		additionalTextTrap }
	STATUS     current
	DESCRIPTION 
		"Relay is blocked in B position. Index 4."
	::= { uca104TrapsPrefix 2 }

uca104UndeterminatedPositionTrap  NOTIFICATION-TYPE
	OBJECTS { eventIdTrap, 
		notificationIdTrap, 
		perceivedSeverityTrap, 
		timeStampTrap, 
		additionalTextTrap }
	STATUS     current
	DESCRIPTION 
		"Relay position is unknown.  Index 4."
	::= { uca104TrapsPrefix 3 }

uca104IncorrectConfigurationTrap  NOTIFICATION-TYPE
	OBJECTS { eventIdTrap, 
		notificationIdTrap, 
		perceivedSeverityTrap, 
		timeStampTrap, 
		additionalTextTrap }
	STATUS     current
	DESCRIPTION 
		"The MUX A type is not the same that MUX B type. Index 4."
	::= { uca104TrapsPrefix 4 }

uca104ConmutationErrorTrap  NOTIFICATION-TYPE
	OBJECTS { eventIdTrap, 
		notificationIdTrap, 
		perceivedSeverityTrap, 
		timeStampTrap, 
		additionalTextTrap }
	STATUS     current
	DESCRIPTION 
		"UCA 1+1 conmutation error. It was impossible to finish all conmutation process. Index 4."
	::= { uca104TrapsPrefix 5 }

uca104MuxATrap  NOTIFICATION-TYPE
	OBJECTS { eventIdTrap, 
		notificationIdTrap, 
		perceivedSeverityTrap, 
		timeStampTrap, 
		additionalTextTrap }
	STATUS     current
	DESCRIPTION 
		"During conmutation process, it was not possible configure MUX A.
		There are not communication with MUX A. Index 4."
	::= { uca104TrapsPrefix 6 }

uca104MuxBTrap  NOTIFICATION-TYPE
	OBJECTS { eventIdTrap, 
		notificationIdTrap, 
		perceivedSeverityTrap, 
		timeStampTrap, 
		additionalTextTrap }
	STATUS     current
	DESCRIPTION 
		"During conmutation process, it was not possible configure MUX B.
		There are not communication with MUX B. Index 4."
	::= { uca104TrapsPrefix 7 }

uca104ConmutationTrap  NOTIFICATION-TYPE
	OBJECTS { eventIdTrap, 
		notificationIdTrap, 
		perceivedSeverityTrap, 
		timeStampTrap, 
		additionalTextTrap }
	STATUS     current
	DESCRIPTION 
		"Conmutation event. Index 4."
	::= { uca104TrapsPrefix 8 }

uca105BlockedATrap  NOTIFICATION-TYPE
	OBJECTS { eventIdTrap, 
		notificationIdTrap, 
		perceivedSeverityTrap, 
		timeStampTrap, 
		additionalTextTrap }
	STATUS     current
	DESCRIPTION 
		"Relay is blocked in A position. Index 5."
	::= { uca105TrapsPrefix 1 }

uca105BlockedBTrap  NOTIFICATION-TYPE
	OBJECTS { eventIdTrap, 
		notificationIdTrap, 
		perceivedSeverityTrap, 
		timeStampTrap, 
		additionalTextTrap }
	STATUS     current
	DESCRIPTION 
		"Relay is blocked in B position. Index 5."
	::= { uca105TrapsPrefix 2 }

uca105UndeterminatedPositionTrap  NOTIFICATION-TYPE
	OBJECTS { eventIdTrap, 
		notificationIdTrap, 
		perceivedSeverityTrap, 
		timeStampTrap, 
		additionalTextTrap }
	STATUS     current
	DESCRIPTION 
		"Relay position is unknown.  Index 5."
	::= { uca105TrapsPrefix 3 }

uca105IncorrectConfigurationTrap  NOTIFICATION-TYPE
	OBJECTS { eventIdTrap, 
		notificationIdTrap, 
		perceivedSeverityTrap, 
		timeStampTrap, 
		additionalTextTrap }
	STATUS     current
	DESCRIPTION 
		"The MUX A type is not the same that MUX B type. Index 5."
	::= { uca105TrapsPrefix 4 }

uca105ConmutationErrorTrap  NOTIFICATION-TYPE
	OBJECTS { eventIdTrap, 
		notificationIdTrap, 
		perceivedSeverityTrap, 
		timeStampTrap, 
		additionalTextTrap }
	STATUS     current
	DESCRIPTION 
		"UCA 1+1 conmutation error. It was impossible to finish all conmutation process. Index 5."
	::= { uca105TrapsPrefix 5 }

uca105MuxATrap  NOTIFICATION-TYPE
	OBJECTS { eventIdTrap, 
		notificationIdTrap, 
		perceivedSeverityTrap, 
		timeStampTrap, 
		additionalTextTrap }
	STATUS     current
	DESCRIPTION 
		"During conmutation process, it was not possible configure MUX A.
		There are not communication with MUX A. Index 5."
	::= { uca105TrapsPrefix 6 }

uca105MuxBTrap  NOTIFICATION-TYPE
	OBJECTS { eventIdTrap, 
		notificationIdTrap, 
		perceivedSeverityTrap, 
		timeStampTrap, 
		additionalTextTrap }
	STATUS     current
	DESCRIPTION 
		"During conmutation process, it was not possible configure MUX B.
		There are not communication with MUX B. Index 5."
	::= { uca105TrapsPrefix 7 }

uca105ConmutationTrap  NOTIFICATION-TYPE
	OBJECTS { eventIdTrap, 
		notificationIdTrap, 
		perceivedSeverityTrap, 
		timeStampTrap, 
		additionalTextTrap }
	STATUS     current
	DESCRIPTION 
		"Conmutation event. Index 5."
	::= { uca105TrapsPrefix 8 }

uca106BlockedATrap  NOTIFICATION-TYPE
	OBJECTS { eventIdTrap, 
		notificationIdTrap, 
		perceivedSeverityTrap, 
		timeStampTrap, 
		additionalTextTrap }
	STATUS     current
	DESCRIPTION 
		"Relay is blocked in A position. Index 6."
	::= { uca106TrapsPrefix 1 }

uca106BlockedBTrap  NOTIFICATION-TYPE
	OBJECTS { eventIdTrap, 
		notificationIdTrap, 
		perceivedSeverityTrap, 
		timeStampTrap, 
		additionalTextTrap }
	STATUS     current
	DESCRIPTION 
		"Relay is blocked in B position. Index 6."
	::= { uca106TrapsPrefix 2 }

uca106UndeterminatedPositionTrap  NOTIFICATION-TYPE
	OBJECTS { eventIdTrap, 
		notificationIdTrap, 
		perceivedSeverityTrap, 
		timeStampTrap, 
		additionalTextTrap }
	STATUS     current
	DESCRIPTION 
		"Relay position is unknown.  Index 6."
	::= { uca106TrapsPrefix 3 }

uca106IncorrectConfigurationTrap  NOTIFICATION-TYPE
	OBJECTS { eventIdTrap, 
		notificationIdTrap, 
		perceivedSeverityTrap, 
		timeStampTrap, 
		additionalTextTrap }
	STATUS     current
	DESCRIPTION 
		"The MUX A type is not the same that MUX B type. Index 6."
	::= { uca106TrapsPrefix 4 }

uca106ConmutationErrorTrap  NOTIFICATION-TYPE
	OBJECTS { eventIdTrap, 
		notificationIdTrap, 
		perceivedSeverityTrap, 
		timeStampTrap, 
		additionalTextTrap }
	STATUS     current
	DESCRIPTION 
		"UCA 1+1 conmutation error. It was impossible to finish all conmutation process. Index 6."
	::= { uca106TrapsPrefix 5 }

uca106MuxATrap  NOTIFICATION-TYPE
	OBJECTS { eventIdTrap, 
		notificationIdTrap, 
		perceivedSeverityTrap, 
		timeStampTrap, 
		additionalTextTrap }
	STATUS     current
	DESCRIPTION 
		"During conmutation process, it was not possible configure MUX A.
		There are not communication with MUX A. Index 6."
	::= { uca106TrapsPrefix 6 }

uca106MuxBTrap  NOTIFICATION-TYPE
	OBJECTS { eventIdTrap, 
		notificationIdTrap, 
		perceivedSeverityTrap, 
		timeStampTrap, 
		additionalTextTrap }
	STATUS     current
	DESCRIPTION 
		"During conmutation process, it was not possible configure MUX B.
		There are not communication with MUX B. Index 6."
	::= { uca106TrapsPrefix 7 }

uca106ConmutationTrap  NOTIFICATION-TYPE
	OBJECTS { eventIdTrap, 
		notificationIdTrap, 
		perceivedSeverityTrap, 
		timeStampTrap, 
		additionalTextTrap }
	STATUS     current
	DESCRIPTION 
		"Conmutation event. Index 6."
	::= { uca106TrapsPrefix 8 }

uca107BlockedATrap  NOTIFICATION-TYPE
	OBJECTS { eventIdTrap, 
		notificationIdTrap, 
		perceivedSeverityTrap, 
		timeStampTrap, 
		additionalTextTrap }
	STATUS     current
	DESCRIPTION 
		"Relay is blocked in A position. Index 7."
	::= { uca107TrapsPrefix 1 }

uca107BlockedBTrap  NOTIFICATION-TYPE
	OBJECTS { eventIdTrap, 
		notificationIdTrap, 
		perceivedSeverityTrap, 
		timeStampTrap, 
		additionalTextTrap }
	STATUS     current
	DESCRIPTION 
		"Relay is blocked in B position. Index 7."
	::= { uca107TrapsPrefix 2 }

uca107UndeterminatedPositionTrap  NOTIFICATION-TYPE
	OBJECTS { eventIdTrap, 
		notificationIdTrap, 
		perceivedSeverityTrap, 
		timeStampTrap, 
		additionalTextTrap }
	STATUS     current
	DESCRIPTION 
		"Relay position is unknown.  Index 7."
	::= { uca107TrapsPrefix 3 }

uca107IncorrectConfigurationTrap  NOTIFICATION-TYPE
	OBJECTS { eventIdTrap, 
		notificationIdTrap, 
		perceivedSeverityTrap, 
		timeStampTrap, 
		additionalTextTrap }
	STATUS     current
	DESCRIPTION 
		"The MUX A type is not the same that MUX B type. Index 7."
	::= { uca107TrapsPrefix 4 }

uca107ConmutationErrorTrap  NOTIFICATION-TYPE
	OBJECTS { eventIdTrap, 
		notificationIdTrap, 
		perceivedSeverityTrap, 
		timeStampTrap, 
		additionalTextTrap }
	STATUS     current
	DESCRIPTION 
		"UCA 1+1 conmutation error. It was impossible to finish all conmutation process. Index 7."
	::= { uca107TrapsPrefix 5 }

uca107MuxATrap  NOTIFICATION-TYPE
	OBJECTS { eventIdTrap, 
		notificationIdTrap, 
		perceivedSeverityTrap, 
		timeStampTrap, 
		additionalTextTrap }
	STATUS     current
	DESCRIPTION 
		"During conmutation process, it was not possible configure MUX A.
		There are not communication with MUX A. Index 7."
	::= { uca107TrapsPrefix 6 }

uca107MuxBTrap  NOTIFICATION-TYPE
	OBJECTS { eventIdTrap, 
		notificationIdTrap, 
		perceivedSeverityTrap, 
		timeStampTrap, 
		additionalTextTrap }
	STATUS     current
	DESCRIPTION 
		"During conmutation process, it was not possible configure MUX B.
		There are not communication with MUX B. Index 7."
	::= { uca107TrapsPrefix 7 }

uca107ConmutationTrap  NOTIFICATION-TYPE
	OBJECTS { eventIdTrap, 
		notificationIdTrap, 
		perceivedSeverityTrap, 
		timeStampTrap, 
		additionalTextTrap }
	STATUS     current
	DESCRIPTION 
		"Conmutation event. Index 7."
	::= { uca107TrapsPrefix 8 }

uca108BlockedATrap  NOTIFICATION-TYPE
	OBJECTS { eventIdTrap, 
		notificationIdTrap, 
		perceivedSeverityTrap, 
		timeStampTrap, 
		additionalTextTrap }
	STATUS     current
	DESCRIPTION 
		"Relay is blocked in A position. Index 8."
	::= { uca108TrapsPrefix 1 }

uca108BlockedBTrap  NOTIFICATION-TYPE
	OBJECTS { eventIdTrap, 
		notificationIdTrap, 
		perceivedSeverityTrap, 
		timeStampTrap, 
		additionalTextTrap }
	STATUS     current
	DESCRIPTION 
		"Relay is blocked in B position. Index 8."
	::= { uca108TrapsPrefix 2 }

uca108UndeterminatedPositionTrap  NOTIFICATION-TYPE
	OBJECTS { eventIdTrap, 
		notificationIdTrap, 
		perceivedSeverityTrap, 
		timeStampTrap, 
		additionalTextTrap }
	STATUS     current
	DESCRIPTION 
		"Relay position is unknown.  Index 8."
	::= { uca108TrapsPrefix 3 }

uca108IncorrectConfigurationTrap  NOTIFICATION-TYPE
	OBJECTS { eventIdTrap, 
		notificationIdTrap, 
		perceivedSeverityTrap, 
		timeStampTrap, 
		additionalTextTrap }
	STATUS     current
	DESCRIPTION 
		"The MUX A type is not the same that MUX B type. Index 8."
	::= { uca108TrapsPrefix 4 }

uca108ConmutationErrorTrap  NOTIFICATION-TYPE
	OBJECTS { eventIdTrap, 
		notificationIdTrap, 
		perceivedSeverityTrap, 
		timeStampTrap, 
		additionalTextTrap }
	STATUS     current
	DESCRIPTION 
		"UCA 1+1 conmutation error. It was impossible to finish all conmutation process. Index 8."
	::= { uca108TrapsPrefix 5 }

uca108MuxATrap  NOTIFICATION-TYPE
	OBJECTS { eventIdTrap, 
		notificationIdTrap, 
		perceivedSeverityTrap, 
		timeStampTrap, 
		additionalTextTrap }
	STATUS     current
	DESCRIPTION 
		"During conmutation process, it was not possible configure MUX A.
		There are not communication with MUX A. Index 8."
	::= { uca108TrapsPrefix 6 }

uca108MuxBTrap  NOTIFICATION-TYPE
	OBJECTS { eventIdTrap, 
		notificationIdTrap, 
		perceivedSeverityTrap, 
		timeStampTrap, 
		additionalTextTrap }
	STATUS     current
	DESCRIPTION 
		"During conmutation process, it was not possible configure MUX B.
		There are not communication with MUX B. Index 8."
	::= { uca108TrapsPrefix 7 }

uca108ConmutationTrap  NOTIFICATION-TYPE
	OBJECTS { eventIdTrap, 
		notificationIdTrap, 
		perceivedSeverityTrap, 
		timeStampTrap, 
		additionalTextTrap }
	STATUS     current
	DESCRIPTION 
		"Conmutation event. Index 8."
	::= { uca108TrapsPrefix 8 }

uca109BlockedATrap  NOTIFICATION-TYPE
	OBJECTS { eventIdTrap, 
		notificationIdTrap, 
		perceivedSeverityTrap, 
		timeStampTrap, 
		additionalTextTrap }
	STATUS     current
	DESCRIPTION 
		"Relay is blocked in A position. Index 9."
	::= { uca109TrapsPrefix 1 }

uca109BlockedBTrap  NOTIFICATION-TYPE
	OBJECTS { eventIdTrap, 
		notificationIdTrap, 
		perceivedSeverityTrap, 
		timeStampTrap, 
		additionalTextTrap }
	STATUS     current
	DESCRIPTION 
		"Relay is blocked in B position. Index 9."
	::= { uca109TrapsPrefix 2 }

uca109UndeterminatedPositionTrap  NOTIFICATION-TYPE
	OBJECTS { eventIdTrap, 
		notificationIdTrap, 
		perceivedSeverityTrap, 
		timeStampTrap, 
		additionalTextTrap }
	STATUS     current
	DESCRIPTION 
		"Relay position is unknown.  Index 9."
	::= { uca109TrapsPrefix 3 }

uca109IncorrectConfigurationTrap  NOTIFICATION-TYPE
	OBJECTS { eventIdTrap, 
		notificationIdTrap, 
		perceivedSeverityTrap, 
		timeStampTrap, 
		additionalTextTrap }
	STATUS     current
	DESCRIPTION 
		"The MUX A type is not the same that MUX B type. Index 9."
	::= { uca109TrapsPrefix 4 }

uca109ConmutationErrorTrap  NOTIFICATION-TYPE
	OBJECTS { eventIdTrap, 
		notificationIdTrap, 
		perceivedSeverityTrap, 
		timeStampTrap, 
		additionalTextTrap }
	STATUS     current
	DESCRIPTION 
		"UCA 1+1 conmutation error. It was impossible to finish all conmutation process. Index 9."
	::= { uca109TrapsPrefix 5 }

uca109MuxATrap  NOTIFICATION-TYPE
	OBJECTS { eventIdTrap, 
		notificationIdTrap, 
		perceivedSeverityTrap, 
		timeStampTrap, 
		additionalTextTrap }
	STATUS     current
	DESCRIPTION 
		"During conmutation process, it was not possible configure MUX A.
		There are not communication with MUX A. Index 9."
	::= { uca109TrapsPrefix 6 }

uca109MuxBTrap  NOTIFICATION-TYPE
	OBJECTS { eventIdTrap, 
		notificationIdTrap, 
		perceivedSeverityTrap, 
		timeStampTrap, 
		additionalTextTrap }
	STATUS     current
	DESCRIPTION 
		"During conmutation process, it was not possible configure MUX B.
		There are not communication with MUX B. Index 9."
	::= { uca109TrapsPrefix 7 }

uca109ConmutationTrap  NOTIFICATION-TYPE
	OBJECTS { eventIdTrap, 
		notificationIdTrap, 
		perceivedSeverityTrap, 
		timeStampTrap, 
		additionalTextTrap }
	STATUS     current
	DESCRIPTION 
		"Conmutation event. Index 9."
	::= { uca109TrapsPrefix 8 }

uca110BlockedATrap  NOTIFICATION-TYPE
	OBJECTS { eventIdTrap, 
		notificationIdTrap, 
		perceivedSeverityTrap, 
		timeStampTrap, 
		additionalTextTrap }
	STATUS     current
	DESCRIPTION 
		"Relay is blocked in A position. Index 10."
	::= { uca110TrapsPrefix 1 }

uca110BlockedBTrap  NOTIFICATION-TYPE
	OBJECTS { eventIdTrap, 
		notificationIdTrap, 
		perceivedSeverityTrap, 
		timeStampTrap, 
		additionalTextTrap }
	STATUS     current
	DESCRIPTION 
		"Relay is blocked in B position. Index 10."
	::= { uca110TrapsPrefix 2 }

uca110UndeterminatedPositionTrap  NOTIFICATION-TYPE
	OBJECTS { eventIdTrap, 
		notificationIdTrap, 
		perceivedSeverityTrap, 
		timeStampTrap, 
		additionalTextTrap }
	STATUS     current
	DESCRIPTION 
		"Relay position is unknown.  Index 10."
	::= { uca110TrapsPrefix 3 }

uca110IncorrectConfigurationTrap  NOTIFICATION-TYPE
	OBJECTS { eventIdTrap, 
		notificationIdTrap, 
		perceivedSeverityTrap, 
		timeStampTrap, 
		additionalTextTrap }
	STATUS     current
	DESCRIPTION 
		"The MUX A type is not the same that MUX B type. Index 10."
	::= { uca110TrapsPrefix 4 }

uca110ConmutationErrorTrap  NOTIFICATION-TYPE
	OBJECTS { eventIdTrap, 
		notificationIdTrap, 
		perceivedSeverityTrap, 
		timeStampTrap, 
		additionalTextTrap }
	STATUS     current
	DESCRIPTION 
		"UCA 1+1 conmutation error. It was impossible to finish all conmutation process. Index 10."
	::= { uca110TrapsPrefix 5 }

uca110MuxATrap  NOTIFICATION-TYPE
	OBJECTS { eventIdTrap, 
		notificationIdTrap, 
		perceivedSeverityTrap, 
		timeStampTrap, 
		additionalTextTrap }
	STATUS     current
	DESCRIPTION 
		"During conmutation process, it was not possible configure MUX A.
		There are not communication with MUX A. Index 10."
	::= { uca110TrapsPrefix 6 }

uca110MuxBTrap  NOTIFICATION-TYPE
	OBJECTS { eventIdTrap, 
		notificationIdTrap, 
		perceivedSeverityTrap, 
		timeStampTrap, 
		additionalTextTrap }
	STATUS     current
	DESCRIPTION 
		"During conmutation process, it was not possible configure MUX B.
		There are not communication with MUX B. Index 10."
	::= { uca110TrapsPrefix 7 }

uca110ConmutationTrap  NOTIFICATION-TYPE
	OBJECTS { eventIdTrap, 
		notificationIdTrap, 
		perceivedSeverityTrap, 
		timeStampTrap, 
		additionalTextTrap }
	STATUS     current
	DESCRIPTION 
		"Conmutation event. Index 10."
	::= { uca110TrapsPrefix 8 }

uca111BlockedATrap  NOTIFICATION-TYPE
	OBJECTS { eventIdTrap, 
		notificationIdTrap, 
		perceivedSeverityTrap, 
		timeStampTrap, 
		additionalTextTrap }
	STATUS     current
	DESCRIPTION 
		"Relay is blocked in A position. Index 11."
	::= { uca111TrapsPrefix 1 }

uca111BlockedBTrap  NOTIFICATION-TYPE
	OBJECTS { eventIdTrap, 
		notificationIdTrap, 
		perceivedSeverityTrap, 
		timeStampTrap, 
		additionalTextTrap }
	STATUS     current
	DESCRIPTION 
		"Relay is blocked in B position. Index 11."
	::= { uca111TrapsPrefix 2 }

uca111UndeterminatedPositionTrap  NOTIFICATION-TYPE
	OBJECTS { eventIdTrap, 
		notificationIdTrap, 
		perceivedSeverityTrap, 
		timeStampTrap, 
		additionalTextTrap }
	STATUS     current
	DESCRIPTION 
		"Relay position is unknown.  Index 11."
	::= { uca111TrapsPrefix 3 }

uca111IncorrectConfigurationTrap  NOTIFICATION-TYPE
	OBJECTS { eventIdTrap, 
		notificationIdTrap, 
		perceivedSeverityTrap, 
		timeStampTrap, 
		additionalTextTrap }
	STATUS     current
	DESCRIPTION 
		"The MUX A type is not the same that MUX B type. Index 11."
	::= { uca111TrapsPrefix 4 }

uca111ConmutationErrorTrap  NOTIFICATION-TYPE
	OBJECTS { eventIdTrap, 
		notificationIdTrap, 
		perceivedSeverityTrap, 
		timeStampTrap, 
		additionalTextTrap }
	STATUS     current
	DESCRIPTION 
		"UCA 1+1 conmutation error. It was impossible to finish all conmutation process. Index 11."
	::= { uca111TrapsPrefix 5 }

uca111MuxATrap  NOTIFICATION-TYPE
	OBJECTS { eventIdTrap, 
		notificationIdTrap, 
		perceivedSeverityTrap, 
		timeStampTrap, 
		additionalTextTrap }
	STATUS     current
	DESCRIPTION 
		"During conmutation process, it was not possible configure MUX A.
		There are not communication with MUX A. Index 11."
	::= { uca111TrapsPrefix 6 }

uca111MuxBTrap  NOTIFICATION-TYPE
	OBJECTS { eventIdTrap, 
		notificationIdTrap, 
		perceivedSeverityTrap, 
		timeStampTrap, 
		additionalTextTrap }
	STATUS     current
	DESCRIPTION 
		"During conmutation process, it was not possible configure MUX B.
		There are not communication with MUX B. Index 11."
	::= { uca111TrapsPrefix 7 }

uca111ConmutationTrap  NOTIFICATION-TYPE
	OBJECTS { eventIdTrap, 
		notificationIdTrap, 
		perceivedSeverityTrap, 
		timeStampTrap, 
		additionalTextTrap }
	STATUS     current
	DESCRIPTION 
		"Conmutation event. Index 11."
	::= { uca111TrapsPrefix 8 }

uca112BlockedATrap  NOTIFICATION-TYPE
	OBJECTS { eventIdTrap, 
		notificationIdTrap, 
		perceivedSeverityTrap, 
		timeStampTrap, 
		additionalTextTrap }
	STATUS     current
	DESCRIPTION 
		"Relay is blocked in A position. Index 12."
	::= { uca112TrapsPrefix 1 }

uca112BlockedBTrap  NOTIFICATION-TYPE
	OBJECTS { eventIdTrap, 
		notificationIdTrap, 
		perceivedSeverityTrap, 
		timeStampTrap, 
		additionalTextTrap }
	STATUS     current
	DESCRIPTION 
		"Relay is blocked in B position. Index 12."
	::= { uca112TrapsPrefix 2 }

uca112UndeterminatedPositionTrap  NOTIFICATION-TYPE
	OBJECTS { eventIdTrap, 
		notificationIdTrap, 
		perceivedSeverityTrap, 
		timeStampTrap, 
		additionalTextTrap }
	STATUS     current
	DESCRIPTION 
		"Relay position is unknown.  Index 12."
	::= { uca112TrapsPrefix 3 }

uca112IncorrectConfigurationTrap  NOTIFICATION-TYPE
	OBJECTS { eventIdTrap, 
		notificationIdTrap, 
		perceivedSeverityTrap, 
		timeStampTrap, 
		additionalTextTrap }
	STATUS     current
	DESCRIPTION 
		"The MUX A type is not the same that MUX B type. Index 12."
	::= { uca112TrapsPrefix 4 }

uca112ConmutationErrorTrap  NOTIFICATION-TYPE
	OBJECTS { eventIdTrap, 
		notificationIdTrap, 
		perceivedSeverityTrap, 
		timeStampTrap, 
		additionalTextTrap }
	STATUS     current
	DESCRIPTION 
		"UCA 1+1 conmutation error. It was impossible to finish all conmutation process. Index 12."
	::= { uca112TrapsPrefix 5 }

uca112MuxATrap  NOTIFICATION-TYPE
	OBJECTS { eventIdTrap, 
		notificationIdTrap, 
		perceivedSeverityTrap, 
		timeStampTrap, 
		additionalTextTrap }
	STATUS     current
	DESCRIPTION 
		"During conmutation process, it was not possible configure MUX A.
		There are not communication with MUX A. Index 12."
	::= { uca112TrapsPrefix 6 }

uca112MuxBTrap  NOTIFICATION-TYPE
	OBJECTS { eventIdTrap, 
		notificationIdTrap, 
		perceivedSeverityTrap, 
		timeStampTrap, 
		additionalTextTrap }
	STATUS     current
	DESCRIPTION 
		"During conmutation process, it was not possible configure MUX B.
		There are not communication with MUX B. Index 12."
	::= { uca112TrapsPrefix 7 }

uca112ConmutationTrap  NOTIFICATION-TYPE
	OBJECTS { eventIdTrap, 
		notificationIdTrap, 
		perceivedSeverityTrap, 
		timeStampTrap, 
		additionalTextTrap }
	STATUS     current
	DESCRIPTION 
		"Conmutation event. Index 12."
	::= { uca112TrapsPrefix 8 }

uca113BlockedATrap  NOTIFICATION-TYPE
	OBJECTS { eventIdTrap, 
		notificationIdTrap, 
		perceivedSeverityTrap, 
		timeStampTrap, 
		additionalTextTrap }
	STATUS     current
	DESCRIPTION 
		"Relay is blocked in A position. Index 13."
	::= { uca113TrapsPrefix 1 }

uca113BlockedBTrap  NOTIFICATION-TYPE
	OBJECTS { eventIdTrap, 
		notificationIdTrap, 
		perceivedSeverityTrap, 
		timeStampTrap, 
		additionalTextTrap }
	STATUS     current
	DESCRIPTION 
		"Relay is blocked in B position. Index 13."
	::= { uca113TrapsPrefix 2 }

uca113UndeterminatedPositionTrap  NOTIFICATION-TYPE
	OBJECTS { eventIdTrap, 
		notificationIdTrap, 
		perceivedSeverityTrap, 
		timeStampTrap, 
		additionalTextTrap }
	STATUS     current
	DESCRIPTION 
		"Relay position is unknown.  Index 13."
	::= { uca113TrapsPrefix 3 }

uca113IncorrectConfigurationTrap  NOTIFICATION-TYPE
	OBJECTS { eventIdTrap, 
		notificationIdTrap, 
		perceivedSeverityTrap, 
		timeStampTrap, 
		additionalTextTrap }
	STATUS     current
	DESCRIPTION 
		"The MUX A type is not the same that MUX B type. Index 13."
	::= { uca113TrapsPrefix 4 }

uca113ConmutationErrorTrap  NOTIFICATION-TYPE
	OBJECTS { eventIdTrap, 
		notificationIdTrap, 
		perceivedSeverityTrap, 
		timeStampTrap, 
		additionalTextTrap }
	STATUS     current
	DESCRIPTION 
		"UCA 1+1 conmutation error. It was impossible to finish all conmutation process. Index 13."
	::= { uca113TrapsPrefix 5 }

uca113MuxATrap  NOTIFICATION-TYPE
	OBJECTS { eventIdTrap, 
		notificationIdTrap, 
		perceivedSeverityTrap, 
		timeStampTrap, 
		additionalTextTrap }
	STATUS     current
	DESCRIPTION 
		"During conmutation process, it was not possible configure MUX A.
		There are not communication with MUX A. Index 13."
	::= { uca113TrapsPrefix 6 }

uca113MuxBTrap  NOTIFICATION-TYPE
	OBJECTS { eventIdTrap, 
		notificationIdTrap, 
		perceivedSeverityTrap, 
		timeStampTrap, 
		additionalTextTrap }
	STATUS     current
	DESCRIPTION 
		"During conmutation process, it was not possible configure MUX B.
		There are not communication with MUX B. Index 13."
	::= { uca113TrapsPrefix 7 }

uca113ConmutationTrap  NOTIFICATION-TYPE
	OBJECTS { eventIdTrap, 
		notificationIdTrap, 
		perceivedSeverityTrap, 
		timeStampTrap, 
		additionalTextTrap }
	STATUS     current
	DESCRIPTION 
		"Conmutation event. Index 13."
	::= { uca113TrapsPrefix 8 }

uca114BlockedATrap  NOTIFICATION-TYPE
	OBJECTS { eventIdTrap, 
		notificationIdTrap, 
		perceivedSeverityTrap, 
		timeStampTrap, 
		additionalTextTrap }
	STATUS     current
	DESCRIPTION 
		"Relay is blocked in A position. Index 14."
	::= { uca114TrapsPrefix 1 }

uca114BlockedBTrap  NOTIFICATION-TYPE
	OBJECTS { eventIdTrap, 
		notificationIdTrap, 
		perceivedSeverityTrap, 
		timeStampTrap, 
		additionalTextTrap }
	STATUS     current
	DESCRIPTION 
		"Relay is blocked in B position. Index 14."
	::= { uca114TrapsPrefix 2 }

uca114UndeterminatedPositionTrap  NOTIFICATION-TYPE
	OBJECTS { eventIdTrap, 
		notificationIdTrap, 
		perceivedSeverityTrap, 
		timeStampTrap, 
		additionalTextTrap }
	STATUS     current
	DESCRIPTION 
		"Relay position is unknown.  Index 14."
	::= { uca114TrapsPrefix 3 }

uca114IncorrectConfigurationTrap  NOTIFICATION-TYPE
	OBJECTS { eventIdTrap, 
		notificationIdTrap, 
		perceivedSeverityTrap, 
		timeStampTrap, 
		additionalTextTrap }
	STATUS     current
	DESCRIPTION 
		"The MUX A type is not the same that MUX B type. Index 14."
	::= { uca114TrapsPrefix 4 }

uca114ConmutationErrorTrap  NOTIFICATION-TYPE
	OBJECTS { eventIdTrap, 
		notificationIdTrap, 
		perceivedSeverityTrap, 
		timeStampTrap, 
		additionalTextTrap }
	STATUS     current
	DESCRIPTION 
		"UCA 1+1 conmutation error. It was impossible to finish all conmutation process. Index 14."
	::= { uca114TrapsPrefix 5 }

uca114MuxATrap  NOTIFICATION-TYPE
	OBJECTS { eventIdTrap, 
		notificationIdTrap, 
		perceivedSeverityTrap, 
		timeStampTrap, 
		additionalTextTrap }
	STATUS     current
	DESCRIPTION 
		"During conmutation process, it was not possible configure MUX A.
		There are not communication with MUX A. Index 14."
	::= { uca114TrapsPrefix 6 }

uca114MuxBTrap  NOTIFICATION-TYPE
	OBJECTS { eventIdTrap, 
		notificationIdTrap, 
		perceivedSeverityTrap, 
		timeStampTrap, 
		additionalTextTrap }
	STATUS     current
	DESCRIPTION 
		"During conmutation process, it was not possible configure MUX B.
		There are not communication with MUX B. Index 14."
	::= { uca114TrapsPrefix 7 }

uca114ConmutationTrap  NOTIFICATION-TYPE
	OBJECTS { eventIdTrap, 
		notificationIdTrap, 
		perceivedSeverityTrap, 
		timeStampTrap, 
		additionalTextTrap }
	STATUS     current
	DESCRIPTION 
		"Conmutation event. Index 14."
	::= { uca114TrapsPrefix 8 }

uca115BlockedATrap  NOTIFICATION-TYPE
	OBJECTS { eventIdTrap, 
		notificationIdTrap, 
		perceivedSeverityTrap, 
		timeStampTrap, 
		additionalTextTrap }
	STATUS     current
	DESCRIPTION 
		"Relay is blocked in A position. Index 15."
	::= { uca115TrapsPrefix 1 }

uca115BlockedBTrap  NOTIFICATION-TYPE
	OBJECTS { eventIdTrap, 
		notificationIdTrap, 
		perceivedSeverityTrap, 
		timeStampTrap, 
		additionalTextTrap }
	STATUS     current
	DESCRIPTION 
		"Relay is blocked in B position. Index 15."
	::= { uca115TrapsPrefix 2 }

uca115UndeterminatedPositionTrap  NOTIFICATION-TYPE
	OBJECTS { eventIdTrap, 
		notificationIdTrap, 
		perceivedSeverityTrap, 
		timeStampTrap, 
		additionalTextTrap }
	STATUS     current
	DESCRIPTION 
		"Relay position is unknown.  Index 15."
	::= { uca115TrapsPrefix 3 }

uca115IncorrectConfigurationTrap  NOTIFICATION-TYPE
	OBJECTS { eventIdTrap, 
		notificationIdTrap, 
		perceivedSeverityTrap, 
		timeStampTrap, 
		additionalTextTrap }
	STATUS     current
	DESCRIPTION 
		"The MUX A type is not the same that MUX B type. Index 15."
	::= { uca115TrapsPrefix 4 }

uca115ConmutationErrorTrap  NOTIFICATION-TYPE
	OBJECTS { eventIdTrap, 
		notificationIdTrap, 
		perceivedSeverityTrap, 
		timeStampTrap, 
		additionalTextTrap }
	STATUS     current
	DESCRIPTION 
		"UCA 1+1 conmutation error. It was impossible to finish all conmutation process. Index 15."
	::= { uca115TrapsPrefix 5 }

uca115MuxATrap  NOTIFICATION-TYPE
	OBJECTS { eventIdTrap, 
		notificationIdTrap, 
		perceivedSeverityTrap, 
		timeStampTrap, 
		additionalTextTrap }
	STATUS     current
	DESCRIPTION 
		"During conmutation process, it was not possible configure MUX A.
		There are not communication with MUX A. Index 15."
	::= { uca115TrapsPrefix 6 }

uca115MuxBTrap  NOTIFICATION-TYPE
	OBJECTS { eventIdTrap, 
		notificationIdTrap, 
		perceivedSeverityTrap, 
		timeStampTrap, 
		additionalTextTrap }
	STATUS     current
	DESCRIPTION 
		"During conmutation process, it was not possible configure MUX B.
		There are not communication with MUX B. Index 15."
	::= { uca115TrapsPrefix 7 }

uca115ConmutationTrap  NOTIFICATION-TYPE
	OBJECTS { eventIdTrap, 
		notificationIdTrap, 
		perceivedSeverityTrap, 
		timeStampTrap, 
		additionalTextTrap }
	STATUS     current
	DESCRIPTION 
		"Conmutation event. Index 15."
	::= { uca115TrapsPrefix 8 }

dvbtAlarmTrapTable  OBJECT-TYPE
	SYNTAX SEQUENCE OF DvbtAlarmTrapEntry
	MAX-ACCESS not-accessible
	STATUS     current
	DESCRIPTION 
		"This table holds the last 100 traps sent to managing stations."
	::= { dvbtBroadcastAlarm 30 }

dvbtAlarmTrapEntry  OBJECT-TYPE
	SYNTAX 	DvbtAlarmTrapEntry
	MAX-ACCESS not-accessible
	STATUS     current
	DESCRIPTION 
		"An entry in the alarmTrapTable."
	INDEX { alarmTrapIndex }
	::= { dvbtAlarmTrapTable 1 }

DvbtAlarmTrapEntry ::= SEQUENCE {
	alarmTrapIndex
		Integer32,
	eventIdTrap
		Integer32,
	notificationIdTrap
		Integer32,
	perceivedSeverityTrap
		INTEGER,
	timeStampTrap
		OCTET STRING,
	additionalTextTrap
		OCTET STRING
}

alarmTrapIndex  OBJECT-TYPE
	SYNTAX     Integer32 (1..100)
	MAX-ACCESS not-accessible
	STATUS     current
	DESCRIPTION 
		"Index in the alarmTrapTable."
	::= { dvbtAlarmTrapEntry 1 }

eventIdTrap  OBJECT-TYPE
	SYNTAX     Integer32 (1..6)
	MAX-ACCESS read-only
	STATUS     current
	DESCRIPTION 
		"This is an integer uniquely identifying the notification and an indication 
		of the order in which the notifications were generated by the agent.
		
		Note that the agent does not guarantee that its sequencing reflects 
		the order of the underlying events from which the notifications were generated."
	::= { dvbtAlarmTrapEntry 2 }

notificationIdTrap  OBJECT-TYPE
	SYNTAX     Integer32
	MAX-ACCESS read-only
	STATUS     current
	DESCRIPTION 
		"This is a number identifying the trap (enventID) which has being ceased."
	::= { dvbtAlarmTrapEntry 3 }

perceivedSeverityTrap  OBJECT-TYPE
	SYNTAX     INTEGER {
		critical (1),
		major (2),
		minor (3),
		warning (4),
		cleared (5)
	}
	MAX-ACCESS read-only
	STATUS     current
	DESCRIPTION 
		"This attribute describes the severity of the cause of the trap.
		The attribute can take the following values:
		
		Critical (1)
		Major (2)
		Minor (3)
		Warning (4)
		Cleared (5)
		"
	::= { dvbtAlarmTrapEntry 4 }

timeStampTrap  OBJECT-TYPE
	SYNTAX     OCTET STRING (SIZE(19))
	MAX-ACCESS read-only
	STATUS     current
	DESCRIPTION 
		"This is a timestamp indicating the time at which the notification was generated
		
		hh:mm:ss dd/MM/YYYY"
	::= { dvbtAlarmTrapEntry 5 }

additionalTextTrap  OBJECT-TYPE
	SYNTAX     OCTET STRING (SIZE(0..48))
	MAX-ACCESS read-only
	STATUS     current
	DESCRIPTION 
		"This attribute is a string that provides the RF reference 
		(or phisical y this module is not a RF module) reference.
		
		Typical values:
		
		'Gap Filler RF 68 [Ctrl 2]'  i's mean that this trap 
		
		'UCA subrack 2 [Ctrl 22] it's meaning "
	::= { dvbtAlarmTrapEntry 6 }

fanAlarm1Trap  NOTIFICATION-TYPE
	OBJECTS { eventIdTrap, 
		notificationIdTrap, 
		perceivedSeverityTrap, 
		timeStampTrap, 
		additionalTextTrap }
	STATUS     current
	DESCRIPTION 
		"MUX index 1"
	::= { fanAlarmTrapsPrefix 1 }

fanAlarm2Trap  NOTIFICATION-TYPE
	OBJECTS { eventIdTrap, 
		notificationIdTrap, 
		perceivedSeverityTrap, 
		timeStampTrap, 
		additionalTextTrap }
	STATUS     current
	DESCRIPTION 
		"MUX index 2"
	::= { fanAlarmTrapsPrefix 2 }

fanAlarm3Trap  NOTIFICATION-TYPE
	OBJECTS { eventIdTrap, 
		notificationIdTrap, 
		perceivedSeverityTrap, 
		timeStampTrap, 
		additionalTextTrap }
	STATUS     current
	DESCRIPTION 
		"MUX index 3"
	::= { fanAlarmTrapsPrefix 3 }

fanAlarm4Trap  NOTIFICATION-TYPE
	OBJECTS { eventIdTrap, 
		notificationIdTrap, 
		perceivedSeverityTrap, 
		timeStampTrap, 
		additionalTextTrap }
	STATUS     current
	DESCRIPTION 
		"MUX index 4"
	::= { fanAlarmTrapsPrefix 4 }

fanAlarm5Trap  NOTIFICATION-TYPE
	OBJECTS { eventIdTrap, 
		notificationIdTrap, 
		perceivedSeverityTrap, 
		timeStampTrap, 
		additionalTextTrap }
	STATUS     current
	DESCRIPTION 
		"MUX index 5"
	::= { fanAlarmTrapsPrefix 5 }

fanAlarm6Trap  NOTIFICATION-TYPE
	OBJECTS { eventIdTrap, 
		notificationIdTrap, 
		perceivedSeverityTrap, 
		timeStampTrap, 
		additionalTextTrap }
	STATUS     current
	DESCRIPTION 
		"MUX index 6"
	::= { fanAlarmTrapsPrefix 6 }

fanAlarm7Trap  NOTIFICATION-TYPE
	OBJECTS { eventIdTrap, 
		notificationIdTrap, 
		perceivedSeverityTrap, 
		timeStampTrap, 
		additionalTextTrap }
	STATUS     current
	DESCRIPTION 
		"MUX index 7"
	::= { fanAlarmTrapsPrefix 7 }

fanAlarm8Trap  NOTIFICATION-TYPE
	OBJECTS { eventIdTrap, 
		notificationIdTrap, 
		perceivedSeverityTrap, 
		timeStampTrap, 
		additionalTextTrap }
	STATUS     current
	DESCRIPTION 
		"MUX index 8"
	::= { fanAlarmTrapsPrefix 8 }

fanAlarm9Trap  NOTIFICATION-TYPE
	OBJECTS { eventIdTrap, 
		notificationIdTrap, 
		perceivedSeverityTrap, 
		timeStampTrap, 
		additionalTextTrap }
	STATUS     current
	DESCRIPTION 
		"MUX index 9"
	::= { fanAlarmTrapsPrefix 9 }

fanAlarm10Trap  NOTIFICATION-TYPE
	OBJECTS { eventIdTrap, 
		notificationIdTrap, 
		perceivedSeverityTrap, 
		timeStampTrap, 
		additionalTextTrap }
	STATUS     current
	DESCRIPTION 
		"MUX index 10"
	::= { fanAlarmTrapsPrefix 10 }

fanAlarm11Trap  NOTIFICATION-TYPE
	OBJECTS { eventIdTrap, 
		notificationIdTrap, 
		perceivedSeverityTrap, 
		timeStampTrap, 
		additionalTextTrap }
	STATUS     current
	DESCRIPTION 
		"MUX index 11"
	::= { fanAlarmTrapsPrefix 11 }

fanAlarm12Trap  NOTIFICATION-TYPE
	OBJECTS { eventIdTrap, 
		notificationIdTrap, 
		perceivedSeverityTrap, 
		timeStampTrap, 
		additionalTextTrap }
	STATUS     current
	DESCRIPTION 
		"MUX index 12"
	::= { fanAlarmTrapsPrefix 12 }

fanAlarm13Trap  NOTIFICATION-TYPE
	OBJECTS { eventIdTrap, 
		notificationIdTrap, 
		perceivedSeverityTrap, 
		timeStampTrap, 
		additionalTextTrap }
	STATUS     current
	DESCRIPTION 
		"MUX index 13"
	::= { fanAlarmTrapsPrefix 13 }

fanAlarm14Trap  NOTIFICATION-TYPE
	OBJECTS { eventIdTrap, 
		notificationIdTrap, 
		perceivedSeverityTrap, 
		timeStampTrap, 
		additionalTextTrap }
	STATUS     current
	DESCRIPTION 
		"MUX index 14"
	::= { fanAlarmTrapsPrefix 14 }

fanAlarm15Trap  NOTIFICATION-TYPE
	OBJECTS { eventIdTrap, 
		notificationIdTrap, 
		perceivedSeverityTrap, 
		timeStampTrap, 
		additionalTextTrap }
	STATUS     current
	DESCRIPTION 
		"MUX index 15"
	::= { fanAlarmTrapsPrefix 15 }

fanAlarm16Trap  NOTIFICATION-TYPE
	OBJECTS { eventIdTrap, 
		notificationIdTrap, 
		perceivedSeverityTrap, 
		timeStampTrap, 
		additionalTextTrap }
	STATUS     current
	DESCRIPTION 
		"MUX index 16"
	::= { fanAlarmTrapsPrefix 16 }

fanAlarm17Trap  NOTIFICATION-TYPE
	OBJECTS { eventIdTrap, 
		notificationIdTrap, 
		perceivedSeverityTrap, 
		timeStampTrap, 
		additionalTextTrap }
	STATUS     current
	DESCRIPTION 
		"MUX index 17"
	::= { fanAlarmTrapsPrefix 17 }

fanAlarm18Trap  NOTIFICATION-TYPE
	OBJECTS { eventIdTrap, 
		notificationIdTrap, 
		perceivedSeverityTrap, 
		timeStampTrap, 
		additionalTextTrap }
	STATUS     current
	DESCRIPTION 
		"MUX index 18"
	::= { fanAlarmTrapsPrefix 18 }

fanAlarm19Trap  NOTIFICATION-TYPE
	OBJECTS { eventIdTrap, 
		notificationIdTrap, 
		perceivedSeverityTrap, 
		timeStampTrap, 
		additionalTextTrap }
	STATUS     current
	DESCRIPTION 
		"MUX index 19"
	::= { fanAlarmTrapsPrefix 19 }

fanAlarm20Trap  NOTIFICATION-TYPE
	OBJECTS { eventIdTrap, 
		notificationIdTrap, 
		perceivedSeverityTrap, 
		timeStampTrap, 
		additionalTextTrap }
	STATUS     current
	DESCRIPTION 
		"MUX index 20"
	::= { fanAlarmTrapsPrefix 20 }

fanAlarm21Trap  NOTIFICATION-TYPE
	OBJECTS { eventIdTrap, 
		notificationIdTrap, 
		perceivedSeverityTrap, 
		timeStampTrap, 
		additionalTextTrap }
	STATUS     current
	DESCRIPTION 
		"MUX index 21"
	::= { fanAlarmTrapsPrefix 21 }

fanAlarm22Trap  NOTIFICATION-TYPE
	OBJECTS { eventIdTrap, 
		notificationIdTrap, 
		perceivedSeverityTrap, 
		timeStampTrap, 
		additionalTextTrap }
	STATUS     current
	DESCRIPTION 
		"MUX index 22"
	::= { fanAlarmTrapsPrefix 22 }

fanAlarm23Trap  NOTIFICATION-TYPE
	OBJECTS { eventIdTrap, 
		notificationIdTrap, 
		perceivedSeverityTrap, 
		timeStampTrap, 
		additionalTextTrap }
	STATUS     current
	DESCRIPTION 
		"MUX index 23"
	::= { fanAlarmTrapsPrefix 23 }

fanAlarm24Trap  NOTIFICATION-TYPE
	OBJECTS { eventIdTrap, 
		notificationIdTrap, 
		perceivedSeverityTrap, 
		timeStampTrap, 
		additionalTextTrap }
	STATUS     current
	DESCRIPTION 
		"MUX index 24"
	::= { fanAlarmTrapsPrefix 24 }

fanAlarm25Trap  NOTIFICATION-TYPE
	OBJECTS { eventIdTrap, 
		notificationIdTrap, 
		perceivedSeverityTrap, 
		timeStampTrap, 
		additionalTextTrap }
	STATUS     current
	DESCRIPTION 
		"MUX index 25"
	::= { fanAlarmTrapsPrefix 25 }

fanAlarm26Trap  NOTIFICATION-TYPE
	OBJECTS { eventIdTrap, 
		notificationIdTrap, 
		perceivedSeverityTrap, 
		timeStampTrap, 
		additionalTextTrap }
	STATUS     current
	DESCRIPTION 
		"MUX index 26"
	::= { fanAlarmTrapsPrefix 26 }

fanAlarm27Trap  NOTIFICATION-TYPE
	OBJECTS { eventIdTrap, 
		notificationIdTrap, 
		perceivedSeverityTrap, 
		timeStampTrap, 
		additionalTextTrap }
	STATUS     current
	DESCRIPTION 
		"MUX index 27"
	::= { fanAlarmTrapsPrefix 27 }

fanAlarm28Trap  NOTIFICATION-TYPE
	OBJECTS { eventIdTrap, 
		notificationIdTrap, 
		perceivedSeverityTrap, 
		timeStampTrap, 
		additionalTextTrap }
	STATUS     current
	DESCRIPTION 
		"MUX index 28"
	::= { fanAlarmTrapsPrefix 28 }

fanAlarm29Trap  NOTIFICATION-TYPE
	OBJECTS { eventIdTrap, 
		notificationIdTrap, 
		perceivedSeverityTrap, 
		timeStampTrap, 
		additionalTextTrap }
	STATUS     current
	DESCRIPTION 
		"MUX index 29"
	::= { fanAlarmTrapsPrefix 29 }

fanAlarm30Trap  NOTIFICATION-TYPE
	OBJECTS { eventIdTrap, 
		notificationIdTrap, 
		perceivedSeverityTrap, 
		timeStampTrap, 
		additionalTextTrap }
	STATUS     current
	DESCRIPTION 
		"MUX index 30"
	::= { fanAlarmTrapsPrefix 30 }

gpsSyncGPS1Trap  NOTIFICATION-TYPE
	OBJECTS { eventIdTrap, 
		notificationIdTrap, 
		perceivedSeverityTrap, 
		timeStampTrap, 
		additionalTextTrap }
	STATUS     current
	DESCRIPTION 
		"GPS 1"
	::= { gpsSyncTrapsPrefix 1 }

gpsSyncGPS2Trap  NOTIFICATION-TYPE
	OBJECTS { eventIdTrap, 
		notificationIdTrap, 
		perceivedSeverityTrap, 
		timeStampTrap, 
		additionalTextTrap }
	STATUS     current
	DESCRIPTION 
		"GPS 2"
	::= { gpsSyncTrapsPrefix 2 }

asi2Error1Trap  NOTIFICATION-TYPE
	OBJECTS { eventIdTrap, 
		notificationIdTrap, 
		perceivedSeverityTrap, 
		timeStampTrap, 
		additionalTextTrap }
	STATUS     current
	DESCRIPTION 
		"MUX index 1"
	::= { asi2ErrorTrapsPrefix 1 }

asi2Error2Trap  NOTIFICATION-TYPE
	OBJECTS { eventIdTrap, 
		notificationIdTrap, 
		perceivedSeverityTrap, 
		timeStampTrap, 
		additionalTextTrap }
	STATUS     current
	DESCRIPTION 
		"MUX index 2"
	::= { asi2ErrorTrapsPrefix 2 }

asi2Error3Trap  NOTIFICATION-TYPE
	OBJECTS { eventIdTrap, 
		notificationIdTrap, 
		perceivedSeverityTrap, 
		timeStampTrap, 
		additionalTextTrap }
	STATUS     current
	DESCRIPTION 
		"MUX index 3"
	::= { asi2ErrorTrapsPrefix 3 }

asi2Error4Trap  NOTIFICATION-TYPE
	OBJECTS { eventIdTrap, 
		notificationIdTrap, 
		perceivedSeverityTrap, 
		timeStampTrap, 
		additionalTextTrap }
	STATUS     current
	DESCRIPTION 
		"MUX index 4"
	::= { asi2ErrorTrapsPrefix 4 }

asi2Error5Trap  NOTIFICATION-TYPE
	OBJECTS { eventIdTrap, 
		notificationIdTrap, 
		perceivedSeverityTrap, 
		timeStampTrap, 
		additionalTextTrap }
	STATUS     current
	DESCRIPTION 
		"MUX index 5"
	::= { asi2ErrorTrapsPrefix 5 }

asi2Error6Trap  NOTIFICATION-TYPE
	OBJECTS { eventIdTrap, 
		notificationIdTrap, 
		perceivedSeverityTrap, 
		timeStampTrap, 
		additionalTextTrap }
	STATUS     current
	DESCRIPTION 
		"MUX index 6"
	::= { asi2ErrorTrapsPrefix 6 }

asi2Error7Trap  NOTIFICATION-TYPE
	OBJECTS { eventIdTrap, 
		notificationIdTrap, 
		perceivedSeverityTrap, 
		timeStampTrap, 
		additionalTextTrap }
	STATUS     current
	DESCRIPTION 
		"MUX index 7"
	::= { asi2ErrorTrapsPrefix 7 }

asi2Error8Trap  NOTIFICATION-TYPE
	OBJECTS { eventIdTrap, 
		notificationIdTrap, 
		perceivedSeverityTrap, 
		timeStampTrap, 
		additionalTextTrap }
	STATUS     current
	DESCRIPTION 
		"MUX index 8"
	::= { asi2ErrorTrapsPrefix 8 }

asi2Error9Trap  NOTIFICATION-TYPE
	OBJECTS { eventIdTrap, 
		notificationIdTrap, 
		perceivedSeverityTrap, 
		timeStampTrap, 
		additionalTextTrap }
	STATUS     current
	DESCRIPTION 
		"MUX index 9"
	::= { asi2ErrorTrapsPrefix 9 }

asi2Error10Trap  NOTIFICATION-TYPE
	OBJECTS { eventIdTrap, 
		notificationIdTrap, 
		perceivedSeverityTrap, 
		timeStampTrap, 
		additionalTextTrap }
	STATUS     current
	DESCRIPTION 
		"MUX index 10"
	::= { asi2ErrorTrapsPrefix 10 }

asi2Error11Trap  NOTIFICATION-TYPE
	OBJECTS { eventIdTrap, 
		notificationIdTrap, 
		perceivedSeverityTrap, 
		timeStampTrap, 
		additionalTextTrap }
	STATUS     current
	DESCRIPTION 
		"MUX index 11"
	::= { asi2ErrorTrapsPrefix 11 }

asi2Error12Trap  NOTIFICATION-TYPE
	OBJECTS { eventIdTrap, 
		notificationIdTrap, 
		perceivedSeverityTrap, 
		timeStampTrap, 
		additionalTextTrap }
	STATUS     current
	DESCRIPTION 
		"MUX index 12"
	::= { asi2ErrorTrapsPrefix 12 }

asi2Error13Trap  NOTIFICATION-TYPE
	OBJECTS { eventIdTrap, 
		notificationIdTrap, 
		perceivedSeverityTrap, 
		timeStampTrap, 
		additionalTextTrap }
	STATUS     current
	DESCRIPTION 
		"MUX index 13"
	::= { asi2ErrorTrapsPrefix 13 }

asi2Error14Trap  NOTIFICATION-TYPE
	OBJECTS { eventIdTrap, 
		notificationIdTrap, 
		perceivedSeverityTrap, 
		timeStampTrap, 
		additionalTextTrap }
	STATUS     current
	DESCRIPTION 
		"MUX index 14"
	::= { asi2ErrorTrapsPrefix 14 }

asi2Error15Trap  NOTIFICATION-TYPE
	OBJECTS { eventIdTrap, 
		notificationIdTrap, 
		perceivedSeverityTrap, 
		timeStampTrap, 
		additionalTextTrap }
	STATUS     current
	DESCRIPTION 
		"MUX index 15"
	::= { asi2ErrorTrapsPrefix 15 }

asi2Error16Trap  NOTIFICATION-TYPE
	OBJECTS { eventIdTrap, 
		notificationIdTrap, 
		perceivedSeverityTrap, 
		timeStampTrap, 
		additionalTextTrap }
	STATUS     current
	DESCRIPTION 
		"MUX index 16"
	::= { asi2ErrorTrapsPrefix 16 }

asi2Error17Trap  NOTIFICATION-TYPE
	OBJECTS { eventIdTrap, 
		notificationIdTrap, 
		perceivedSeverityTrap, 
		timeStampTrap, 
		additionalTextTrap }
	STATUS     current
	DESCRIPTION 
		"MUX index 17"
	::= { asi2ErrorTrapsPrefix 17 }

asi2Error18Trap  NOTIFICATION-TYPE
	OBJECTS { eventIdTrap, 
		notificationIdTrap, 
		perceivedSeverityTrap, 
		timeStampTrap, 
		additionalTextTrap }
	STATUS     current
	DESCRIPTION 
		"MUX index 18"
	::= { asi2ErrorTrapsPrefix 18 }

asi2Error19Trap  NOTIFICATION-TYPE
	OBJECTS { eventIdTrap, 
		notificationIdTrap, 
		perceivedSeverityTrap, 
		timeStampTrap, 
		additionalTextTrap }
	STATUS     current
	DESCRIPTION 
		"MUX index 19"
	::= { asi2ErrorTrapsPrefix 19 }

asi2Error20Trap  NOTIFICATION-TYPE
	OBJECTS { eventIdTrap, 
		notificationIdTrap, 
		perceivedSeverityTrap, 
		timeStampTrap, 
		additionalTextTrap }
	STATUS     current
	DESCRIPTION 
		"MUX index 20"
	::= { asi2ErrorTrapsPrefix 20 }

asi2Error21Trap  NOTIFICATION-TYPE
	OBJECTS { eventIdTrap, 
		notificationIdTrap, 
		perceivedSeverityTrap, 
		timeStampTrap, 
		additionalTextTrap }
	STATUS     current
	DESCRIPTION 
		"MUX index 21"
	::= { asi2ErrorTrapsPrefix 21 }

asi2Error22Trap  NOTIFICATION-TYPE
	OBJECTS { eventIdTrap, 
		notificationIdTrap, 
		perceivedSeverityTrap, 
		timeStampTrap, 
		additionalTextTrap }
	STATUS     current
	DESCRIPTION 
		"MUX index 22"
	::= { asi2ErrorTrapsPrefix 22 }

asi2Error23Trap  NOTIFICATION-TYPE
	OBJECTS { eventIdTrap, 
		notificationIdTrap, 
		perceivedSeverityTrap, 
		timeStampTrap, 
		additionalTextTrap }
	STATUS     current
	DESCRIPTION 
		"MUX index 23"
	::= { asi2ErrorTrapsPrefix 23 }

asi2Error24Trap  NOTIFICATION-TYPE
	OBJECTS { eventIdTrap, 
		notificationIdTrap, 
		perceivedSeverityTrap, 
		timeStampTrap, 
		additionalTextTrap }
	STATUS     current
	DESCRIPTION 
		"MUX index 24"
	::= { asi2ErrorTrapsPrefix 24 }

asi2Error25Trap  NOTIFICATION-TYPE
	OBJECTS { eventIdTrap, 
		notificationIdTrap, 
		perceivedSeverityTrap, 
		timeStampTrap, 
		additionalTextTrap }
	STATUS     current
	DESCRIPTION 
		"MUX index 25"
	::= { asi2ErrorTrapsPrefix 25 }

asi2Error26Trap  NOTIFICATION-TYPE
	OBJECTS { eventIdTrap, 
		notificationIdTrap, 
		perceivedSeverityTrap, 
		timeStampTrap, 
		additionalTextTrap }
	STATUS     current
	DESCRIPTION 
		"MUX index 26"
	::= { asi2ErrorTrapsPrefix 26 }

asi2Error27Trap  NOTIFICATION-TYPE
	OBJECTS { eventIdTrap, 
		notificationIdTrap, 
		perceivedSeverityTrap, 
		timeStampTrap, 
		additionalTextTrap }
	STATUS     current
	DESCRIPTION 
		"MUX index 27"
	::= { asi2ErrorTrapsPrefix 27 }

asi2Error28Trap  NOTIFICATION-TYPE
	OBJECTS { eventIdTrap, 
		notificationIdTrap, 
		perceivedSeverityTrap, 
		timeStampTrap, 
		additionalTextTrap }
	STATUS     current
	DESCRIPTION 
		"MUX index 28"
	::= { asi2ErrorTrapsPrefix 28 }

asi2Error29Trap  NOTIFICATION-TYPE
	OBJECTS { eventIdTrap, 
		notificationIdTrap, 
		perceivedSeverityTrap, 
		timeStampTrap, 
		additionalTextTrap }
	STATUS     current
	DESCRIPTION 
		"MUX index 29"
	::= { asi2ErrorTrapsPrefix 29 }

asi2Error30Trap  NOTIFICATION-TYPE
	OBJECTS { eventIdTrap, 
		notificationIdTrap, 
		perceivedSeverityTrap, 
		timeStampTrap, 
		additionalTextTrap }
	STATUS     current
	DESCRIPTION 
		"MUX index 30"
	::= { asi2ErrorTrapsPrefix 30 }

mpeg1Error1Trap  NOTIFICATION-TYPE
	OBJECTS { eventIdTrap, 
		notificationIdTrap, 
		perceivedSeverityTrap, 
		timeStampTrap, 
		additionalTextTrap }
	STATUS     current
	DESCRIPTION 
		"MUX index 1"
	::= { mpeg1ErrorTrapsPrefix 1 }

mpeg1Error2Trap  NOTIFICATION-TYPE
	OBJECTS { eventIdTrap, 
		notificationIdTrap, 
		perceivedSeverityTrap, 
		timeStampTrap, 
		additionalTextTrap }
	STATUS     current
	DESCRIPTION 
		"MUX index 2"
	::= { mpeg1ErrorTrapsPrefix 2 }

mpeg1Error3Trap  NOTIFICATION-TYPE
	OBJECTS { eventIdTrap, 
		notificationIdTrap, 
		perceivedSeverityTrap, 
		timeStampTrap, 
		additionalTextTrap }
	STATUS     current
	DESCRIPTION 
		"MUX index 3"
	::= { mpeg1ErrorTrapsPrefix 3 }

mpeg1Error4Trap  NOTIFICATION-TYPE
	OBJECTS { eventIdTrap, 
		notificationIdTrap, 
		perceivedSeverityTrap, 
		timeStampTrap, 
		additionalTextTrap }
	STATUS     current
	DESCRIPTION 
		"MUX index 4"
	::= { mpeg1ErrorTrapsPrefix 4 }

mpeg1Error5Trap  NOTIFICATION-TYPE
	OBJECTS { eventIdTrap, 
		notificationIdTrap, 
		perceivedSeverityTrap, 
		timeStampTrap, 
		additionalTextTrap }
	STATUS     current
	DESCRIPTION 
		"MUX index 5"
	::= { mpeg1ErrorTrapsPrefix 5 }

mpeg1Error6Trap  NOTIFICATION-TYPE
	OBJECTS { eventIdTrap, 
		notificationIdTrap, 
		perceivedSeverityTrap, 
		timeStampTrap, 
		additionalTextTrap }
	STATUS     current
	DESCRIPTION 
		"MUX index 6"
	::= { mpeg1ErrorTrapsPrefix 6 }

mpeg1Error7Trap  NOTIFICATION-TYPE
	OBJECTS { eventIdTrap, 
		notificationIdTrap, 
		perceivedSeverityTrap, 
		timeStampTrap, 
		additionalTextTrap }
	STATUS     current
	DESCRIPTION 
		"MUX index 7"
	::= { mpeg1ErrorTrapsPrefix 7 }

mpeg1Error8Trap  NOTIFICATION-TYPE
	OBJECTS { eventIdTrap, 
		notificationIdTrap, 
		perceivedSeverityTrap, 
		timeStampTrap, 
		additionalTextTrap }
	STATUS     current
	DESCRIPTION 
		"MUX index 8"
	::= { mpeg1ErrorTrapsPrefix 8 }

mpeg1Error9Trap  NOTIFICATION-TYPE
	OBJECTS { eventIdTrap, 
		notificationIdTrap, 
		perceivedSeverityTrap, 
		timeStampTrap, 
		additionalTextTrap }
	STATUS     current
	DESCRIPTION 
		"MUX index 9"
	::= { mpeg1ErrorTrapsPrefix 9 }

mpeg1Error10Trap  NOTIFICATION-TYPE
	OBJECTS { eventIdTrap, 
		notificationIdTrap, 
		perceivedSeverityTrap, 
		timeStampTrap, 
		additionalTextTrap }
	STATUS     current
	DESCRIPTION 
		"MUX index 10"
	::= { mpeg1ErrorTrapsPrefix 10 }

mpeg1Error11Trap  NOTIFICATION-TYPE
	OBJECTS { eventIdTrap, 
		notificationIdTrap, 
		perceivedSeverityTrap, 
		timeStampTrap, 
		additionalTextTrap }
	STATUS     current
	DESCRIPTION 
		"MUX index 11"
	::= { mpeg1ErrorTrapsPrefix 11 }

mpeg1Error12Trap  NOTIFICATION-TYPE
	OBJECTS { eventIdTrap, 
		notificationIdTrap, 
		perceivedSeverityTrap, 
		timeStampTrap, 
		additionalTextTrap }
	STATUS     current
	DESCRIPTION 
		"MUX index 12"
	::= { mpeg1ErrorTrapsPrefix 12 }

mpeg1Error13Trap  NOTIFICATION-TYPE
	OBJECTS { eventIdTrap, 
		notificationIdTrap, 
		perceivedSeverityTrap, 
		timeStampTrap, 
		additionalTextTrap }
	STATUS     current
	DESCRIPTION 
		"MUX index 13"
	::= { mpeg1ErrorTrapsPrefix 13 }

mpeg1Error14Trap  NOTIFICATION-TYPE
	OBJECTS { eventIdTrap, 
		notificationIdTrap, 
		perceivedSeverityTrap, 
		timeStampTrap, 
		additionalTextTrap }
	STATUS     current
	DESCRIPTION 
		"MUX index 14"
	::= { mpeg1ErrorTrapsPrefix 14 }

mpeg1Error15Trap  NOTIFICATION-TYPE
	OBJECTS { eventIdTrap, 
		notificationIdTrap, 
		perceivedSeverityTrap, 
		timeStampTrap, 
		additionalTextTrap }
	STATUS     current
	DESCRIPTION 
		"MUX index 15"
	::= { mpeg1ErrorTrapsPrefix 15 }

mpeg1Error16Trap  NOTIFICATION-TYPE
	OBJECTS { eventIdTrap, 
		notificationIdTrap, 
		perceivedSeverityTrap, 
		timeStampTrap, 
		additionalTextTrap }
	STATUS     current
	DESCRIPTION 
		"MUX index 16"
	::= { mpeg1ErrorTrapsPrefix 16 }

mpeg1Error17Trap  NOTIFICATION-TYPE
	OBJECTS { eventIdTrap, 
		notificationIdTrap, 
		perceivedSeverityTrap, 
		timeStampTrap, 
		additionalTextTrap }
	STATUS     current
	DESCRIPTION 
		"MUX index 17"
	::= { mpeg1ErrorTrapsPrefix 17 }

mpeg1Error18Trap  NOTIFICATION-TYPE
	OBJECTS { eventIdTrap, 
		notificationIdTrap, 
		perceivedSeverityTrap, 
		timeStampTrap, 
		additionalTextTrap }
	STATUS     current
	DESCRIPTION 
		"MUX index 18"
	::= { mpeg1ErrorTrapsPrefix 18 }

mpeg1Error19Trap  NOTIFICATION-TYPE
	OBJECTS { eventIdTrap, 
		notificationIdTrap, 
		perceivedSeverityTrap, 
		timeStampTrap, 
		additionalTextTrap }
	STATUS     current
	DESCRIPTION 
		"MUX index 19"
	::= { mpeg1ErrorTrapsPrefix 19 }

mpeg1Error20Trap  NOTIFICATION-TYPE
	OBJECTS { eventIdTrap, 
		notificationIdTrap, 
		perceivedSeverityTrap, 
		timeStampTrap, 
		additionalTextTrap }
	STATUS     current
	DESCRIPTION 
		"MUX index 20"
	::= { mpeg1ErrorTrapsPrefix 20 }

mpeg1Error21Trap  NOTIFICATION-TYPE
	OBJECTS { eventIdTrap, 
		notificationIdTrap, 
		perceivedSeverityTrap, 
		timeStampTrap, 
		additionalTextTrap }
	STATUS     current
	DESCRIPTION 
		"MUX index 21"
	::= { mpeg1ErrorTrapsPrefix 21 }

mpeg1Error22Trap  NOTIFICATION-TYPE
	OBJECTS { eventIdTrap, 
		notificationIdTrap, 
		perceivedSeverityTrap, 
		timeStampTrap, 
		additionalTextTrap }
	STATUS     current
	DESCRIPTION 
		"MUX index 22"
	::= { mpeg1ErrorTrapsPrefix 22 }

mpeg1Error23Trap  NOTIFICATION-TYPE
	OBJECTS { eventIdTrap, 
		notificationIdTrap, 
		perceivedSeverityTrap, 
		timeStampTrap, 
		additionalTextTrap }
	STATUS     current
	DESCRIPTION 
		"MUX index 23"
	::= { mpeg1ErrorTrapsPrefix 23 }

mpeg1Error24Trap  NOTIFICATION-TYPE
	OBJECTS { eventIdTrap, 
		notificationIdTrap, 
		perceivedSeverityTrap, 
		timeStampTrap, 
		additionalTextTrap }
	STATUS     current
	DESCRIPTION 
		"MUX index 24"
	::= { mpeg1ErrorTrapsPrefix 24 }

mpeg1Error25Trap  NOTIFICATION-TYPE
	OBJECTS { eventIdTrap, 
		notificationIdTrap, 
		perceivedSeverityTrap, 
		timeStampTrap, 
		additionalTextTrap }
	STATUS     current
	DESCRIPTION 
		"MUX index 25"
	::= { mpeg1ErrorTrapsPrefix 25 }

mpeg1Error26Trap  NOTIFICATION-TYPE
	OBJECTS { eventIdTrap, 
		notificationIdTrap, 
		perceivedSeverityTrap, 
		timeStampTrap, 
		additionalTextTrap }
	STATUS     current
	DESCRIPTION 
		"MUX index 26"
	::= { mpeg1ErrorTrapsPrefix 26 }

mpeg1Error27Trap  NOTIFICATION-TYPE
	OBJECTS { eventIdTrap, 
		notificationIdTrap, 
		perceivedSeverityTrap, 
		timeStampTrap, 
		additionalTextTrap }
	STATUS     current
	DESCRIPTION 
		"MUX index 27"
	::= { mpeg1ErrorTrapsPrefix 27 }

mpeg1Error28Trap  NOTIFICATION-TYPE
	OBJECTS { eventIdTrap, 
		notificationIdTrap, 
		perceivedSeverityTrap, 
		timeStampTrap, 
		additionalTextTrap }
	STATUS     current
	DESCRIPTION 
		"MUX index 28"
	::= { mpeg1ErrorTrapsPrefix 28 }

mpeg1Error29Trap  NOTIFICATION-TYPE
	OBJECTS { eventIdTrap, 
		notificationIdTrap, 
		perceivedSeverityTrap, 
		timeStampTrap, 
		additionalTextTrap }
	STATUS     current
	DESCRIPTION 
		"MUX index 29"
	::= { mpeg1ErrorTrapsPrefix 29 }

mpeg1Error30Trap  NOTIFICATION-TYPE
	OBJECTS { eventIdTrap, 
		notificationIdTrap, 
		perceivedSeverityTrap, 
		timeStampTrap, 
		additionalTextTrap }
	STATUS     current
	DESCRIPTION 
		"MUX index 30"
	::= { mpeg1ErrorTrapsPrefix 30 }

mpeg2Error1Trap  NOTIFICATION-TYPE
	OBJECTS { eventIdTrap, 
		notificationIdTrap, 
		perceivedSeverityTrap, 
		timeStampTrap, 
		additionalTextTrap }
	STATUS     current
	DESCRIPTION 
		"MUX index 1"
	::= { mpeg2ErrorTrapsPrefix 1 }

mpeg2Error2Trap  NOTIFICATION-TYPE
	OBJECTS { eventIdTrap, 
		notificationIdTrap, 
		perceivedSeverityTrap, 
		timeStampTrap, 
		additionalTextTrap }
	STATUS     current
	DESCRIPTION 
		"MUX index 2"
	::= { mpeg2ErrorTrapsPrefix 2 }

mpeg2Error3Trap  NOTIFICATION-TYPE
	OBJECTS { eventIdTrap, 
		notificationIdTrap, 
		perceivedSeverityTrap, 
		timeStampTrap, 
		additionalTextTrap }
	STATUS     current
	DESCRIPTION 
		"MUX index 3"
	::= { mpeg2ErrorTrapsPrefix 3 }

mpeg2Error4Trap  NOTIFICATION-TYPE
	OBJECTS { eventIdTrap, 
		notificationIdTrap, 
		perceivedSeverityTrap, 
		timeStampTrap, 
		additionalTextTrap }
	STATUS     current
	DESCRIPTION 
		"MUX index 4"
	::= { mpeg2ErrorTrapsPrefix 4 }

mpeg2Error5Trap  NOTIFICATION-TYPE
	OBJECTS { eventIdTrap, 
		notificationIdTrap, 
		perceivedSeverityTrap, 
		timeStampTrap, 
		additionalTextTrap }
	STATUS     current
	DESCRIPTION 
		"MUX index 5"
	::= { mpeg2ErrorTrapsPrefix 5 }

mpeg2Error6Trap  NOTIFICATION-TYPE
	OBJECTS { eventIdTrap, 
		notificationIdTrap, 
		perceivedSeverityTrap, 
		timeStampTrap, 
		additionalTextTrap }
	STATUS     current
	DESCRIPTION 
		"MUX index 6"
	::= { mpeg2ErrorTrapsPrefix 6 }

mpeg2Error7Trap  NOTIFICATION-TYPE
	OBJECTS { eventIdTrap, 
		notificationIdTrap, 
		perceivedSeverityTrap, 
		timeStampTrap, 
		additionalTextTrap }
	STATUS     current
	DESCRIPTION 
		"MUX index 7"
	::= { mpeg2ErrorTrapsPrefix 7 }

mpeg2Error8Trap  NOTIFICATION-TYPE
	OBJECTS { eventIdTrap, 
		notificationIdTrap, 
		perceivedSeverityTrap, 
		timeStampTrap, 
		additionalTextTrap }
	STATUS     current
	DESCRIPTION 
		"MUX index 8"
	::= { mpeg2ErrorTrapsPrefix 8 }

mpeg2Error9Trap  NOTIFICATION-TYPE
	OBJECTS { eventIdTrap, 
		notificationIdTrap, 
		perceivedSeverityTrap, 
		timeStampTrap, 
		additionalTextTrap }
	STATUS     current
	DESCRIPTION 
		"MUX index 9"
	::= { mpeg2ErrorTrapsPrefix 9 }

mpeg2Error10Trap  NOTIFICATION-TYPE
	OBJECTS { eventIdTrap, 
		notificationIdTrap, 
		perceivedSeverityTrap, 
		timeStampTrap, 
		additionalTextTrap }
	STATUS     current
	DESCRIPTION 
		"MUX index 10"
	::= { mpeg2ErrorTrapsPrefix 10 }

mpeg2Error11Trap  NOTIFICATION-TYPE
	OBJECTS { eventIdTrap, 
		notificationIdTrap, 
		perceivedSeverityTrap, 
		timeStampTrap, 
		additionalTextTrap }
	STATUS     current
	DESCRIPTION 
		"MUX index 11"
	::= { mpeg2ErrorTrapsPrefix 11 }

mpeg2Error12Trap  NOTIFICATION-TYPE
	OBJECTS { eventIdTrap, 
		notificationIdTrap, 
		perceivedSeverityTrap, 
		timeStampTrap, 
		additionalTextTrap }
	STATUS     current
	DESCRIPTION 
		"MUX index 12"
	::= { mpeg2ErrorTrapsPrefix 12 }

mpeg2Error13Trap  NOTIFICATION-TYPE
	OBJECTS { eventIdTrap, 
		notificationIdTrap, 
		perceivedSeverityTrap, 
		timeStampTrap, 
		additionalTextTrap }
	STATUS     current
	DESCRIPTION 
		"MUX index 13"
	::= { mpeg2ErrorTrapsPrefix 13 }

mpeg2Error14Trap  NOTIFICATION-TYPE
	OBJECTS { eventIdTrap, 
		notificationIdTrap, 
		perceivedSeverityTrap, 
		timeStampTrap, 
		additionalTextTrap }
	STATUS     current
	DESCRIPTION 
		"MUX index 14"
	::= { mpeg2ErrorTrapsPrefix 14 }

mpeg2Error15Trap  NOTIFICATION-TYPE
	OBJECTS { eventIdTrap, 
		notificationIdTrap, 
		perceivedSeverityTrap, 
		timeStampTrap, 
		additionalTextTrap }
	STATUS     current
	DESCRIPTION 
		"MUX index 15"
	::= { mpeg2ErrorTrapsPrefix 15 }

mpeg2Error16Trap  NOTIFICATION-TYPE
	OBJECTS { eventIdTrap, 
		notificationIdTrap, 
		perceivedSeverityTrap, 
		timeStampTrap, 
		additionalTextTrap }
	STATUS     current
	DESCRIPTION 
		"MUX index 16"
	::= { mpeg2ErrorTrapsPrefix 16 }

mpeg2Error17Trap  NOTIFICATION-TYPE
	OBJECTS { eventIdTrap, 
		notificationIdTrap, 
		perceivedSeverityTrap, 
		timeStampTrap, 
		additionalTextTrap }
	STATUS     current
	DESCRIPTION 
		"MUX index 17"
	::= { mpeg2ErrorTrapsPrefix 17 }

mpeg2Error18Trap  NOTIFICATION-TYPE
	OBJECTS { eventIdTrap, 
		notificationIdTrap, 
		perceivedSeverityTrap, 
		timeStampTrap, 
		additionalTextTrap }
	STATUS     current
	DESCRIPTION 
		"MUX index 18"
	::= { mpeg2ErrorTrapsPrefix 18 }

mpeg2Error19Trap  NOTIFICATION-TYPE
	OBJECTS { eventIdTrap, 
		notificationIdTrap, 
		perceivedSeverityTrap, 
		timeStampTrap, 
		additionalTextTrap }
	STATUS     current
	DESCRIPTION 
		"MUX index 19"
	::= { mpeg2ErrorTrapsPrefix 19 }

mpeg2Error20Trap  NOTIFICATION-TYPE
	OBJECTS { eventIdTrap, 
		notificationIdTrap, 
		perceivedSeverityTrap, 
		timeStampTrap, 
		additionalTextTrap }
	STATUS     current
	DESCRIPTION 
		"MUX index 20"
	::= { mpeg2ErrorTrapsPrefix 20 }

mpeg2Error21Trap  NOTIFICATION-TYPE
	OBJECTS { eventIdTrap, 
		notificationIdTrap, 
		perceivedSeverityTrap, 
		timeStampTrap, 
		additionalTextTrap }
	STATUS     current
	DESCRIPTION 
		"MUX index 21"
	::= { mpeg2ErrorTrapsPrefix 21 }

mpeg2Error22Trap  NOTIFICATION-TYPE
	OBJECTS { eventIdTrap, 
		notificationIdTrap, 
		perceivedSeverityTrap, 
		timeStampTrap, 
		additionalTextTrap }
	STATUS     current
	DESCRIPTION 
		"MUX index 22"
	::= { mpeg2ErrorTrapsPrefix 22 }

mpeg2Error23Trap  NOTIFICATION-TYPE
	OBJECTS { eventIdTrap, 
		notificationIdTrap, 
		perceivedSeverityTrap, 
		timeStampTrap, 
		additionalTextTrap }
	STATUS     current
	DESCRIPTION 
		"MUX index 23"
	::= { mpeg2ErrorTrapsPrefix 23 }

mpeg2Error24Trap  NOTIFICATION-TYPE
	OBJECTS { eventIdTrap, 
		notificationIdTrap, 
		perceivedSeverityTrap, 
		timeStampTrap, 
		additionalTextTrap }
	STATUS     current
	DESCRIPTION 
		"MUX index 24"
	::= { mpeg2ErrorTrapsPrefix 24 }

mpeg2Error25Trap  NOTIFICATION-TYPE
	OBJECTS { eventIdTrap, 
		notificationIdTrap, 
		perceivedSeverityTrap, 
		timeStampTrap, 
		additionalTextTrap }
	STATUS     current
	DESCRIPTION 
		"MUX index 25"
	::= { mpeg2ErrorTrapsPrefix 25 }

mpeg2Error26Trap  NOTIFICATION-TYPE
	OBJECTS { eventIdTrap, 
		notificationIdTrap, 
		perceivedSeverityTrap, 
		timeStampTrap, 
		additionalTextTrap }
	STATUS     current
	DESCRIPTION 
		"MUX index 26"
	::= { mpeg2ErrorTrapsPrefix 26 }

mpeg2Error27Trap  NOTIFICATION-TYPE
	OBJECTS { eventIdTrap, 
		notificationIdTrap, 
		perceivedSeverityTrap, 
		timeStampTrap, 
		additionalTextTrap }
	STATUS     current
	DESCRIPTION 
		"MUX index 27"
	::= { mpeg2ErrorTrapsPrefix 27 }

mpeg2Error28Trap  NOTIFICATION-TYPE
	OBJECTS { eventIdTrap, 
		notificationIdTrap, 
		perceivedSeverityTrap, 
		timeStampTrap, 
		additionalTextTrap }
	STATUS     current
	DESCRIPTION 
		"MUX index 28"
	::= { mpeg2ErrorTrapsPrefix 28 }

mpeg2Error29Trap  NOTIFICATION-TYPE
	OBJECTS { eventIdTrap, 
		notificationIdTrap, 
		perceivedSeverityTrap, 
		timeStampTrap, 
		additionalTextTrap }
	STATUS     current
	DESCRIPTION 
		"MUX index 29"
	::= { mpeg2ErrorTrapsPrefix 29 }

mpeg2Error30Trap  NOTIFICATION-TYPE
	OBJECTS { eventIdTrap, 
		notificationIdTrap, 
		perceivedSeverityTrap, 
		timeStampTrap, 
		additionalTextTrap }
	STATUS     current
	DESCRIPTION 
		"MUX index 30"
	::= { mpeg2ErrorTrapsPrefix 30 }

sfnError1Trap  NOTIFICATION-TYPE
	OBJECTS { eventIdTrap, 
		notificationIdTrap, 
		perceivedSeverityTrap, 
		timeStampTrap, 
		additionalTextTrap }
	STATUS     current
	DESCRIPTION 
		"MUX index 1"
	::= { sfnErrorTrapsPrefix 1 }

sfnError2Trap  NOTIFICATION-TYPE
	OBJECTS { eventIdTrap, 
		notificationIdTrap, 
		perceivedSeverityTrap, 
		timeStampTrap, 
		additionalTextTrap }
	STATUS     current
	DESCRIPTION 
		"MUX index 2"
	::= { sfnErrorTrapsPrefix 2 }

sfnError3Trap  NOTIFICATION-TYPE
	OBJECTS { eventIdTrap, 
		notificationIdTrap, 
		perceivedSeverityTrap, 
		timeStampTrap, 
		additionalTextTrap }
	STATUS     current
	DESCRIPTION 
		"MUX index 3"
	::= { sfnErrorTrapsPrefix 3 }

sfnError4Trap  NOTIFICATION-TYPE
	OBJECTS { eventIdTrap, 
		notificationIdTrap, 
		perceivedSeverityTrap, 
		timeStampTrap, 
		additionalTextTrap }
	STATUS     current
	DESCRIPTION 
		"MUX index 4"
	::= { sfnErrorTrapsPrefix 4 }

sfnError5Trap  NOTIFICATION-TYPE
	OBJECTS { eventIdTrap, 
		notificationIdTrap, 
		perceivedSeverityTrap, 
		timeStampTrap, 
		additionalTextTrap }
	STATUS     current
	DESCRIPTION 
		"MUX index 5"
	::= { sfnErrorTrapsPrefix 5 }

sfnError6Trap  NOTIFICATION-TYPE
	OBJECTS { eventIdTrap, 
		notificationIdTrap, 
		perceivedSeverityTrap, 
		timeStampTrap, 
		additionalTextTrap }
	STATUS     current
	DESCRIPTION 
		"MUX index 6"
	::= { sfnErrorTrapsPrefix 6 }

sfnError7Trap  NOTIFICATION-TYPE
	OBJECTS { eventIdTrap, 
		notificationIdTrap, 
		perceivedSeverityTrap, 
		timeStampTrap, 
		additionalTextTrap }
	STATUS     current
	DESCRIPTION 
		"MUX index 7"
	::= { sfnErrorTrapsPrefix 7 }

sfnError8Trap  NOTIFICATION-TYPE
	OBJECTS { eventIdTrap, 
		notificationIdTrap, 
		perceivedSeverityTrap, 
		timeStampTrap, 
		additionalTextTrap }
	STATUS     current
	DESCRIPTION 
		"MUX index 8"
	::= { sfnErrorTrapsPrefix 8 }

sfnError9Trap  NOTIFICATION-TYPE
	OBJECTS { eventIdTrap, 
		notificationIdTrap, 
		perceivedSeverityTrap, 
		timeStampTrap, 
		additionalTextTrap }
	STATUS     current
	DESCRIPTION 
		"MUX index 9"
	::= { sfnErrorTrapsPrefix 9 }

sfnError10Trap  NOTIFICATION-TYPE
	OBJECTS { eventIdTrap, 
		notificationIdTrap, 
		perceivedSeverityTrap, 
		timeStampTrap, 
		additionalTextTrap }
	STATUS     current
	DESCRIPTION 
		"MUX index 10"
	::= { sfnErrorTrapsPrefix 10 }

sfnError11Trap  NOTIFICATION-TYPE
	OBJECTS { eventIdTrap, 
		notificationIdTrap, 
		perceivedSeverityTrap, 
		timeStampTrap, 
		additionalTextTrap }
	STATUS     current
	DESCRIPTION 
		"MUX index 11"
	::= { sfnErrorTrapsPrefix 11 }

sfnError12Trap  NOTIFICATION-TYPE
	OBJECTS { eventIdTrap, 
		notificationIdTrap, 
		perceivedSeverityTrap, 
		timeStampTrap, 
		additionalTextTrap }
	STATUS     current
	DESCRIPTION 
		"MUX index 12"
	::= { sfnErrorTrapsPrefix 12 }

sfnError13Trap  NOTIFICATION-TYPE
	OBJECTS { eventIdTrap, 
		notificationIdTrap, 
		perceivedSeverityTrap, 
		timeStampTrap, 
		additionalTextTrap }
	STATUS     current
	DESCRIPTION 
		"MUX index 13"
	::= { sfnErrorTrapsPrefix 13 }

sfnError14Trap  NOTIFICATION-TYPE
	OBJECTS { eventIdTrap, 
		notificationIdTrap, 
		perceivedSeverityTrap, 
		timeStampTrap, 
		additionalTextTrap }
	STATUS     current
	DESCRIPTION 
		"MUX index 14"
	::= { sfnErrorTrapsPrefix 14 }

sfnError15Trap  NOTIFICATION-TYPE
	OBJECTS { eventIdTrap, 
		notificationIdTrap, 
		perceivedSeverityTrap, 
		timeStampTrap, 
		additionalTextTrap }
	STATUS     current
	DESCRIPTION 
		"MUX index 15"
	::= { sfnErrorTrapsPrefix 15 }

sfnError16Trap  NOTIFICATION-TYPE
	OBJECTS { eventIdTrap, 
		notificationIdTrap, 
		perceivedSeverityTrap, 
		timeStampTrap, 
		additionalTextTrap }
	STATUS     current
	DESCRIPTION 
		"MUX index 16"
	::= { sfnErrorTrapsPrefix 16 }

sfnError17Trap  NOTIFICATION-TYPE
	OBJECTS { eventIdTrap, 
		notificationIdTrap, 
		perceivedSeverityTrap, 
		timeStampTrap, 
		additionalTextTrap }
	STATUS     current
	DESCRIPTION 
		"MUX index 17"
	::= { sfnErrorTrapsPrefix 17 }

sfnError18Trap  NOTIFICATION-TYPE
	OBJECTS { eventIdTrap, 
		notificationIdTrap, 
		perceivedSeverityTrap, 
		timeStampTrap, 
		additionalTextTrap }
	STATUS     current
	DESCRIPTION 
		"MUX index 18"
	::= { sfnErrorTrapsPrefix 18 }

sfnError19Trap  NOTIFICATION-TYPE
	OBJECTS { eventIdTrap, 
		notificationIdTrap, 
		perceivedSeverityTrap, 
		timeStampTrap, 
		additionalTextTrap }
	STATUS     current
	DESCRIPTION 
		"MUX index 19"
	::= { sfnErrorTrapsPrefix 19 }

sfnError20Trap  NOTIFICATION-TYPE
	OBJECTS { eventIdTrap, 
		notificationIdTrap, 
		perceivedSeverityTrap, 
		timeStampTrap, 
		additionalTextTrap }
	STATUS     current
	DESCRIPTION 
		"MUX index 20"
	::= { sfnErrorTrapsPrefix 20 }

sfnError21Trap  NOTIFICATION-TYPE
	OBJECTS { eventIdTrap, 
		notificationIdTrap, 
		perceivedSeverityTrap, 
		timeStampTrap, 
		additionalTextTrap }
	STATUS     current
	DESCRIPTION 
		"MUX index 21"
	::= { sfnErrorTrapsPrefix 21 }

sfnError22Trap  NOTIFICATION-TYPE
	OBJECTS { eventIdTrap, 
		notificationIdTrap, 
		perceivedSeverityTrap, 
		timeStampTrap, 
		additionalTextTrap }
	STATUS     current
	DESCRIPTION 
		"MUX index 22"
	::= { sfnErrorTrapsPrefix 22 }

sfnError23Trap  NOTIFICATION-TYPE
	OBJECTS { eventIdTrap, 
		notificationIdTrap, 
		perceivedSeverityTrap, 
		timeStampTrap, 
		additionalTextTrap }
	STATUS     current
	DESCRIPTION 
		"MUX index 23"
	::= { sfnErrorTrapsPrefix 23 }

sfnError24Trap  NOTIFICATION-TYPE
	OBJECTS { eventIdTrap, 
		notificationIdTrap, 
		perceivedSeverityTrap, 
		timeStampTrap, 
		additionalTextTrap }
	STATUS     current
	DESCRIPTION 
		"MUX index 24"
	::= { sfnErrorTrapsPrefix 24 }

sfnError25Trap  NOTIFICATION-TYPE
	OBJECTS { eventIdTrap, 
		notificationIdTrap, 
		perceivedSeverityTrap, 
		timeStampTrap, 
		additionalTextTrap }
	STATUS     current
	DESCRIPTION 
		"MUX index 25"
	::= { sfnErrorTrapsPrefix 25 }

sfnError26Trap  NOTIFICATION-TYPE
	OBJECTS { eventIdTrap, 
		notificationIdTrap, 
		perceivedSeverityTrap, 
		timeStampTrap, 
		additionalTextTrap }
	STATUS     current
	DESCRIPTION 
		"MUX index 26"
	::= { sfnErrorTrapsPrefix 26 }

sfnError27Trap  NOTIFICATION-TYPE
	OBJECTS { eventIdTrap, 
		notificationIdTrap, 
		perceivedSeverityTrap, 
		timeStampTrap, 
		additionalTextTrap }
	STATUS     current
	DESCRIPTION 
		"MUX index 27"
	::= { sfnErrorTrapsPrefix 27 }

sfnError28Trap  NOTIFICATION-TYPE
	OBJECTS { eventIdTrap, 
		notificationIdTrap, 
		perceivedSeverityTrap, 
		timeStampTrap, 
		additionalTextTrap }
	STATUS     current
	DESCRIPTION 
		"MUX index 28"
	::= { sfnErrorTrapsPrefix 28 }

sfnError29Trap  NOTIFICATION-TYPE
	OBJECTS { eventIdTrap, 
		notificationIdTrap, 
		perceivedSeverityTrap, 
		timeStampTrap, 
		additionalTextTrap }
	STATUS     current
	DESCRIPTION 
		"MUX index 29"
	::= { sfnErrorTrapsPrefix 29 }

sfnError30Trap  NOTIFICATION-TYPE
	OBJECTS { eventIdTrap, 
		notificationIdTrap, 
		perceivedSeverityTrap, 
		timeStampTrap, 
		additionalTextTrap }
	STATUS     current
	DESCRIPTION 
		"MUX index 30"
	::= { sfnErrorTrapsPrefix 30 }

tsError1Trap  NOTIFICATION-TYPE
	OBJECTS { eventIdTrap, 
		notificationIdTrap, 
		perceivedSeverityTrap, 
		timeStampTrap, 
		additionalTextTrap }
	STATUS     current
	DESCRIPTION 
		"MUX index 1"
	::= { tsErrorTrapsPrefix 1 }

tsError2Trap  NOTIFICATION-TYPE
	OBJECTS { eventIdTrap, 
		notificationIdTrap, 
		perceivedSeverityTrap, 
		timeStampTrap, 
		additionalTextTrap }
	STATUS     current
	DESCRIPTION 
		"MUX index 2"
	::= { tsErrorTrapsPrefix 2 }

tsError3Trap  NOTIFICATION-TYPE
	OBJECTS { eventIdTrap, 
		notificationIdTrap, 
		perceivedSeverityTrap, 
		timeStampTrap, 
		additionalTextTrap }
	STATUS     current
	DESCRIPTION 
		"MUX index 3"
	::= { tsErrorTrapsPrefix 3 }

tsError4Trap  NOTIFICATION-TYPE
	OBJECTS { eventIdTrap, 
		notificationIdTrap, 
		perceivedSeverityTrap, 
		timeStampTrap, 
		additionalTextTrap }
	STATUS     current
	DESCRIPTION 
		"MUX index 4"
	::= { tsErrorTrapsPrefix 4 }

tsError5Trap  NOTIFICATION-TYPE
	OBJECTS { eventIdTrap, 
		notificationIdTrap, 
		perceivedSeverityTrap, 
		timeStampTrap, 
		additionalTextTrap }
	STATUS     current
	DESCRIPTION 
		"MUX index 5"
	::= { tsErrorTrapsPrefix 5 }

tsError6Trap  NOTIFICATION-TYPE
	OBJECTS { eventIdTrap, 
		notificationIdTrap, 
		perceivedSeverityTrap, 
		timeStampTrap, 
		additionalTextTrap }
	STATUS     current
	DESCRIPTION 
		"MUX index 6"
	::= { tsErrorTrapsPrefix 6 }

tsError7Trap  NOTIFICATION-TYPE
	OBJECTS { eventIdTrap, 
		notificationIdTrap, 
		perceivedSeverityTrap, 
		timeStampTrap, 
		additionalTextTrap }
	STATUS     current
	DESCRIPTION 
		"MUX index 7"
	::= { tsErrorTrapsPrefix 7 }

tsError8Trap  NOTIFICATION-TYPE
	OBJECTS { eventIdTrap, 
		notificationIdTrap, 
		perceivedSeverityTrap, 
		timeStampTrap, 
		additionalTextTrap }
	STATUS     current
	DESCRIPTION 
		"MUX index 8"
	::= { tsErrorTrapsPrefix 8 }

tsError9Trap  NOTIFICATION-TYPE
	OBJECTS { eventIdTrap, 
		notificationIdTrap, 
		perceivedSeverityTrap, 
		timeStampTrap, 
		additionalTextTrap }
	STATUS     current
	DESCRIPTION 
		"MUX index 9"
	::= { tsErrorTrapsPrefix 9 }

tsError10Trap  NOTIFICATION-TYPE
	OBJECTS { eventIdTrap, 
		notificationIdTrap, 
		perceivedSeverityTrap, 
		timeStampTrap, 
		additionalTextTrap }
	STATUS     current
	DESCRIPTION 
		"MUX index 10"
	::= { tsErrorTrapsPrefix 10 }

tsError11Trap  NOTIFICATION-TYPE
	OBJECTS { eventIdTrap, 
		notificationIdTrap, 
		perceivedSeverityTrap, 
		timeStampTrap, 
		additionalTextTrap }
	STATUS     current
	DESCRIPTION 
		"MUX index 11"
	::= { tsErrorTrapsPrefix 11 }

tsError12Trap  NOTIFICATION-TYPE
	OBJECTS { eventIdTrap, 
		notificationIdTrap, 
		perceivedSeverityTrap, 
		timeStampTrap, 
		additionalTextTrap }
	STATUS     current
	DESCRIPTION 
		"MUX index 12"
	::= { tsErrorTrapsPrefix 12 }

tsError13Trap  NOTIFICATION-TYPE
	OBJECTS { eventIdTrap, 
		notificationIdTrap, 
		perceivedSeverityTrap, 
		timeStampTrap, 
		additionalTextTrap }
	STATUS     current
	DESCRIPTION 
		"MUX index 13"
	::= { tsErrorTrapsPrefix 13 }

tsError14Trap  NOTIFICATION-TYPE
	OBJECTS { eventIdTrap, 
		notificationIdTrap, 
		perceivedSeverityTrap, 
		timeStampTrap, 
		additionalTextTrap }
	STATUS     current
	DESCRIPTION 
		"MUX index 14"
	::= { tsErrorTrapsPrefix 14 }

tsError15Trap  NOTIFICATION-TYPE
	OBJECTS { eventIdTrap, 
		notificationIdTrap, 
		perceivedSeverityTrap, 
		timeStampTrap, 
		additionalTextTrap }
	STATUS     current
	DESCRIPTION 
		"MUX index 15"
	::= { tsErrorTrapsPrefix 15 }

tsError16Trap  NOTIFICATION-TYPE
	OBJECTS { eventIdTrap, 
		notificationIdTrap, 
		perceivedSeverityTrap, 
		timeStampTrap, 
		additionalTextTrap }
	STATUS     current
	DESCRIPTION 
		"MUX index 16"
	::= { tsErrorTrapsPrefix 16 }

tsError17Trap  NOTIFICATION-TYPE
	OBJECTS { eventIdTrap, 
		notificationIdTrap, 
		perceivedSeverityTrap, 
		timeStampTrap, 
		additionalTextTrap }
	STATUS     current
	DESCRIPTION 
		"MUX index 17"
	::= { tsErrorTrapsPrefix 17 }

tsError18Trap  NOTIFICATION-TYPE
	OBJECTS { eventIdTrap, 
		notificationIdTrap, 
		perceivedSeverityTrap, 
		timeStampTrap, 
		additionalTextTrap }
	STATUS     current
	DESCRIPTION 
		"MUX index 18"
	::= { tsErrorTrapsPrefix 18 }

tsError19Trap  NOTIFICATION-TYPE
	OBJECTS { eventIdTrap, 
		notificationIdTrap, 
		perceivedSeverityTrap, 
		timeStampTrap, 
		additionalTextTrap }
	STATUS     current
	DESCRIPTION 
		"MUX index 19"
	::= { tsErrorTrapsPrefix 19 }

tsError20Trap  NOTIFICATION-TYPE
	OBJECTS { eventIdTrap, 
		notificationIdTrap, 
		perceivedSeverityTrap, 
		timeStampTrap, 
		additionalTextTrap }
	STATUS     current
	DESCRIPTION 
		"MUX index 20"
	::= { tsErrorTrapsPrefix 20 }

tsError21Trap  NOTIFICATION-TYPE
	OBJECTS { eventIdTrap, 
		notificationIdTrap, 
		perceivedSeverityTrap, 
		timeStampTrap, 
		additionalTextTrap }
	STATUS     current
	DESCRIPTION 
		"MUX index 21"
	::= { tsErrorTrapsPrefix 21 }

tsError22Trap  NOTIFICATION-TYPE
	OBJECTS { eventIdTrap, 
		notificationIdTrap, 
		perceivedSeverityTrap, 
		timeStampTrap, 
		additionalTextTrap }
	STATUS     current
	DESCRIPTION 
		"MUX index 22"
	::= { tsErrorTrapsPrefix 22 }

tsError23Trap  NOTIFICATION-TYPE
	OBJECTS { eventIdTrap, 
		notificationIdTrap, 
		perceivedSeverityTrap, 
		timeStampTrap, 
		additionalTextTrap }
	STATUS     current
	DESCRIPTION 
		"MUX index 23"
	::= { tsErrorTrapsPrefix 23 }

tsError24Trap  NOTIFICATION-TYPE
	OBJECTS { eventIdTrap, 
		notificationIdTrap, 
		perceivedSeverityTrap, 
		timeStampTrap, 
		additionalTextTrap }
	STATUS     current
	DESCRIPTION 
		"MUX index 24"
	::= { tsErrorTrapsPrefix 24 }

tsError25Trap  NOTIFICATION-TYPE
	OBJECTS { eventIdTrap, 
		notificationIdTrap, 
		perceivedSeverityTrap, 
		timeStampTrap, 
		additionalTextTrap }
	STATUS     current
	DESCRIPTION 
		"MUX index 25"
	::= { tsErrorTrapsPrefix 25 }

tsError26Trap  NOTIFICATION-TYPE
	OBJECTS { eventIdTrap, 
		notificationIdTrap, 
		perceivedSeverityTrap, 
		timeStampTrap, 
		additionalTextTrap }
	STATUS     current
	DESCRIPTION 
		"MUX index 26"
	::= { tsErrorTrapsPrefix 26 }

tsError27Trap  NOTIFICATION-TYPE
	OBJECTS { eventIdTrap, 
		notificationIdTrap, 
		perceivedSeverityTrap, 
		timeStampTrap, 
		additionalTextTrap }
	STATUS     current
	DESCRIPTION 
		"MUX index 27"
	::= { tsErrorTrapsPrefix 27 }

tsError28Trap  NOTIFICATION-TYPE
	OBJECTS { eventIdTrap, 
		notificationIdTrap, 
		perceivedSeverityTrap, 
		timeStampTrap, 
		additionalTextTrap }
	STATUS     current
	DESCRIPTION 
		"MUX index 28"
	::= { tsErrorTrapsPrefix 28 }

tsError29Trap  NOTIFICATION-TYPE
	OBJECTS { eventIdTrap, 
		notificationIdTrap, 
		perceivedSeverityTrap, 
		timeStampTrap, 
		additionalTextTrap }
	STATUS     current
	DESCRIPTION 
		"MUX index 29"
	::= { tsErrorTrapsPrefix 29 }

tsError30Trap  NOTIFICATION-TYPE
	OBJECTS { eventIdTrap, 
		notificationIdTrap, 
		perceivedSeverityTrap, 
		timeStampTrap, 
		additionalTextTrap }
	STATUS     current
	DESCRIPTION 
		"MUX index 30"
	::= { tsErrorTrapsPrefix 30 }

t2miError1Trap  NOTIFICATION-TYPE
	OBJECTS { eventIdTrap, 
		notificationIdTrap, 
		perceivedSeverityTrap, 
		timeStampTrap, 
		additionalTextTrap }
	STATUS     current
	DESCRIPTION 
		"MUX index 1"
	::= { t2miErrorTrapsPrefix 1 }

t2miError2Trap  NOTIFICATION-TYPE
	OBJECTS { eventIdTrap, 
		notificationIdTrap, 
		perceivedSeverityTrap, 
		timeStampTrap, 
		additionalTextTrap }
	STATUS     current
	DESCRIPTION 
		"MUX index 2"
	::= { t2miErrorTrapsPrefix 2 }

t2miError3Trap  NOTIFICATION-TYPE
	OBJECTS { eventIdTrap, 
		notificationIdTrap, 
		perceivedSeverityTrap, 
		timeStampTrap, 
		additionalTextTrap }
	STATUS     current
	DESCRIPTION 
		"MUX index 3"
	::= { t2miErrorTrapsPrefix 3 }

t2miError4Trap  NOTIFICATION-TYPE
	OBJECTS { eventIdTrap, 
		notificationIdTrap, 
		perceivedSeverityTrap, 
		timeStampTrap, 
		additionalTextTrap }
	STATUS     current
	DESCRIPTION 
		"MUX index 4"
	::= { t2miErrorTrapsPrefix 4 }

t2miError5Trap  NOTIFICATION-TYPE
	OBJECTS { eventIdTrap, 
		notificationIdTrap, 
		perceivedSeverityTrap, 
		timeStampTrap, 
		additionalTextTrap }
	STATUS     current
	DESCRIPTION 
		"MUX index 5"
	::= { t2miErrorTrapsPrefix 5 }

t2miError6Trap  NOTIFICATION-TYPE
	OBJECTS { eventIdTrap, 
		notificationIdTrap, 
		perceivedSeverityTrap, 
		timeStampTrap, 
		additionalTextTrap }
	STATUS     current
	DESCRIPTION 
		"MUX index 6"
	::= { t2miErrorTrapsPrefix 6 }

t2miError7Trap  NOTIFICATION-TYPE
	OBJECTS { eventIdTrap, 
		notificationIdTrap, 
		perceivedSeverityTrap, 
		timeStampTrap, 
		additionalTextTrap }
	STATUS     current
	DESCRIPTION 
		"MUX index 7"
	::= { t2miErrorTrapsPrefix 7 }

t2miError8Trap  NOTIFICATION-TYPE
	OBJECTS { eventIdTrap, 
		notificationIdTrap, 
		perceivedSeverityTrap, 
		timeStampTrap, 
		additionalTextTrap }
	STATUS     current
	DESCRIPTION 
		"MUX index 8"
	::= { t2miErrorTrapsPrefix 8 }

t2miError9Trap  NOTIFICATION-TYPE
	OBJECTS { eventIdTrap, 
		notificationIdTrap, 
		perceivedSeverityTrap, 
		timeStampTrap, 
		additionalTextTrap }
	STATUS     current
	DESCRIPTION 
		"MUX index 9"
	::= { t2miErrorTrapsPrefix 9 }

t2miError10Trap  NOTIFICATION-TYPE
	OBJECTS { eventIdTrap, 
		notificationIdTrap, 
		perceivedSeverityTrap, 
		timeStampTrap, 
		additionalTextTrap }
	STATUS     current
	DESCRIPTION 
		"MUX index 10"
	::= { t2miErrorTrapsPrefix 10 }

t2miError11Trap  NOTIFICATION-TYPE
	OBJECTS { eventIdTrap, 
		notificationIdTrap, 
		perceivedSeverityTrap, 
		timeStampTrap, 
		additionalTextTrap }
	STATUS     current
	DESCRIPTION 
		"MUX index 11"
	::= { t2miErrorTrapsPrefix 11 }

t2miError12Trap  NOTIFICATION-TYPE
	OBJECTS { eventIdTrap, 
		notificationIdTrap, 
		perceivedSeverityTrap, 
		timeStampTrap, 
		additionalTextTrap }
	STATUS     current
	DESCRIPTION 
		"MUX index 12"
	::= { t2miErrorTrapsPrefix 12 }

t2miError13Trap  NOTIFICATION-TYPE
	OBJECTS { eventIdTrap, 
		notificationIdTrap, 
		perceivedSeverityTrap, 
		timeStampTrap, 
		additionalTextTrap }
	STATUS     current
	DESCRIPTION 
		"MUX index 13"
	::= { t2miErrorTrapsPrefix 13 }

t2miError14Trap  NOTIFICATION-TYPE
	OBJECTS { eventIdTrap, 
		notificationIdTrap, 
		perceivedSeverityTrap, 
		timeStampTrap, 
		additionalTextTrap }
	STATUS     current
	DESCRIPTION 
		"MUX index 14"
	::= { t2miErrorTrapsPrefix 14 }

t2miError15Trap  NOTIFICATION-TYPE
	OBJECTS { eventIdTrap, 
		notificationIdTrap, 
		perceivedSeverityTrap, 
		timeStampTrap, 
		additionalTextTrap }
	STATUS     current
	DESCRIPTION 
		"MUX index 15"
	::= { t2miErrorTrapsPrefix 15 }

t2miError16Trap  NOTIFICATION-TYPE
	OBJECTS { eventIdTrap, 
		notificationIdTrap, 
		perceivedSeverityTrap, 
		timeStampTrap, 
		additionalTextTrap }
	STATUS     current
	DESCRIPTION 
		"MUX index 16"
	::= { t2miErrorTrapsPrefix 16 }

t2miError17Trap  NOTIFICATION-TYPE
	OBJECTS { eventIdTrap, 
		notificationIdTrap, 
		perceivedSeverityTrap, 
		timeStampTrap, 
		additionalTextTrap }
	STATUS     current
	DESCRIPTION 
		"MUX index 17"
	::= { t2miErrorTrapsPrefix 17 }

t2miError18Trap  NOTIFICATION-TYPE
	OBJECTS { eventIdTrap, 
		notificationIdTrap, 
		perceivedSeverityTrap, 
		timeStampTrap, 
		additionalTextTrap }
	STATUS     current
	DESCRIPTION 
		"MUX index 18"
	::= { t2miErrorTrapsPrefix 18 }

t2miError19Trap  NOTIFICATION-TYPE
	OBJECTS { eventIdTrap, 
		notificationIdTrap, 
		perceivedSeverityTrap, 
		timeStampTrap, 
		additionalTextTrap }
	STATUS     current
	DESCRIPTION 
		"MUX index 19"
	::= { t2miErrorTrapsPrefix 19 }

t2miError20Trap  NOTIFICATION-TYPE
	OBJECTS { eventIdTrap, 
		notificationIdTrap, 
		perceivedSeverityTrap, 
		timeStampTrap, 
		additionalTextTrap }
	STATUS     current
	DESCRIPTION 
		"MUX index 20"
	::= { t2miErrorTrapsPrefix 20 }

t2miError21Trap  NOTIFICATION-TYPE
	OBJECTS { eventIdTrap, 
		notificationIdTrap, 
		perceivedSeverityTrap, 
		timeStampTrap, 
		additionalTextTrap }
	STATUS     current
	DESCRIPTION 
		"MUX index 21"
	::= { t2miErrorTrapsPrefix 21 }

t2miError22Trap  NOTIFICATION-TYPE
	OBJECTS { eventIdTrap, 
		notificationIdTrap, 
		perceivedSeverityTrap, 
		timeStampTrap, 
		additionalTextTrap }
	STATUS     current
	DESCRIPTION 
		"MUX index 22"
	::= { t2miErrorTrapsPrefix 22 }

t2miError23Trap  NOTIFICATION-TYPE
	OBJECTS { eventIdTrap, 
		notificationIdTrap, 
		perceivedSeverityTrap, 
		timeStampTrap, 
		additionalTextTrap }
	STATUS     current
	DESCRIPTION 
		"MUX index 23"
	::= { t2miErrorTrapsPrefix 23 }

t2miError24Trap  NOTIFICATION-TYPE
	OBJECTS { eventIdTrap, 
		notificationIdTrap, 
		perceivedSeverityTrap, 
		timeStampTrap, 
		additionalTextTrap }
	STATUS     current
	DESCRIPTION 
		"MUX index 24"
	::= { t2miErrorTrapsPrefix 24 }

t2miError25Trap  NOTIFICATION-TYPE
	OBJECTS { eventIdTrap, 
		notificationIdTrap, 
		perceivedSeverityTrap, 
		timeStampTrap, 
		additionalTextTrap }
	STATUS     current
	DESCRIPTION 
		"MUX index 25"
	::= { t2miErrorTrapsPrefix 25 }

t2miError26Trap  NOTIFICATION-TYPE
	OBJECTS { eventIdTrap, 
		notificationIdTrap, 
		perceivedSeverityTrap, 
		timeStampTrap, 
		additionalTextTrap }
	STATUS     current
	DESCRIPTION 
		"MUX index 26"
	::= { t2miErrorTrapsPrefix 26 }

t2miError27Trap  NOTIFICATION-TYPE
	OBJECTS { eventIdTrap, 
		notificationIdTrap, 
		perceivedSeverityTrap, 
		timeStampTrap, 
		additionalTextTrap }
	STATUS     current
	DESCRIPTION 
		"MUX index 27"
	::= { t2miErrorTrapsPrefix 27 }

t2miError28Trap  NOTIFICATION-TYPE
	OBJECTS { eventIdTrap, 
		notificationIdTrap, 
		perceivedSeverityTrap, 
		timeStampTrap, 
		additionalTextTrap }
	STATUS     current
	DESCRIPTION 
		"MUX index 28"
	::= { t2miErrorTrapsPrefix 28 }

t2miError29Trap  NOTIFICATION-TYPE
	OBJECTS { eventIdTrap, 
		notificationIdTrap, 
		perceivedSeverityTrap, 
		timeStampTrap, 
		additionalTextTrap }
	STATUS     current
	DESCRIPTION 
		"MUX index 29"
	::= { t2miErrorTrapsPrefix 29 }

t2miError30Trap  NOTIFICATION-TYPE
	OBJECTS { eventIdTrap, 
		notificationIdTrap, 
		perceivedSeverityTrap, 
		timeStampTrap, 
		additionalTextTrap }
	STATUS     current
	DESCRIPTION 
		"MUX index 30"
	::= { t2miErrorTrapsPrefix 30 }

dvbs2AsiFaultTrap  NOTIFICATION-TYPE
	OBJECTS { eventIdTrap, 
		notificationIdTrap, 
		perceivedSeverityTrap, 
		timeStampTrap, 
		additionalTextTrap, 
		dvbs2AsiAlarmsCtrlAddress, 
		dvbs2AsiAlarmsFault }
	STATUS     current
	DESCRIPTION 
		"Fault Trap"
	::= { dvbs2AsiTrapComp 1 }

dvbs2AsiWarningTrap  NOTIFICATION-TYPE
	OBJECTS { eventIdTrap, 
		notificationIdTrap, 
		perceivedSeverityTrap, 
		timeStampTrap, 
		additionalTextTrap, 
		dvbs2AsiAlarmsCtrlAddress, 
		dvbs2AsiAlarmsMinor }
	STATUS     current
	DESCRIPTION 
		"Minor Trap"
	::= { dvbs2AsiTrapComp 2 }

dvbs2AsiInputUnlock1Trap  NOTIFICATION-TYPE
	OBJECTS { eventIdTrap, 
		notificationIdTrap, 
		perceivedSeverityTrap, 
		timeStampTrap, 
		additionalTextTrap, 
		dvbs2AsiAlarmsCtrlAddress, 
		dvbs2AsiAlarmsInputUnlock1 }
	STATUS     current
	DESCRIPTION 
		"Input RF 1 is unlocked"
	::= { dvbs2AsiTrapComp 3 }

dvbs2AsiInputUnlock2Trap  NOTIFICATION-TYPE
	OBJECTS { eventIdTrap, 
		notificationIdTrap, 
		perceivedSeverityTrap, 
		timeStampTrap, 
		additionalTextTrap, 
		dvbs2AsiAlarmsCtrlAddress, 
		dvbs2AsiAlarmsInputUnlock2 }
	STATUS     current
	DESCRIPTION 
		"Input RF 2 is unlocked"
	::= { dvbs2AsiTrapComp 4 }

dvbs2AsiInputUnlock3Trap  NOTIFICATION-TYPE
	OBJECTS { eventIdTrap, 
		notificationIdTrap, 
		perceivedSeverityTrap, 
		timeStampTrap, 
		additionalTextTrap, 
		dvbs2AsiAlarmsCtrlAddress, 
		dvbs2AsiAlarmsInputUnlock3 }
	STATUS     current
	DESCRIPTION 
		"Input RF 3 is unlocked"
	::= { dvbs2AsiTrapComp 5 }

dvbs2AsiInputUnlock4Trap  NOTIFICATION-TYPE
	OBJECTS { eventIdTrap, 
		notificationIdTrap, 
		perceivedSeverityTrap, 
		timeStampTrap, 
		additionalTextTrap, 
		dvbs2AsiAlarmsCtrlAddress, 
		dvbs2AsiAlarmsInputUnlock4 }
	STATUS     current
	DESCRIPTION 
		"Input RF 4 is unlocked"
	::= { dvbs2AsiTrapComp 6 }

dvbs2AsiLnb1Trap  NOTIFICATION-TYPE
	OBJECTS { eventIdTrap, 
		notificationIdTrap, 
		perceivedSeverityTrap, 
		timeStampTrap, 
		additionalTextTrap, 
		dvbs2AsiAlarmsCtrlAddress, 
		dvbs2AsiAlarmsLnb1 }
	STATUS     current
	DESCRIPTION 
		"LNB 1 shortcircuit"
	::= { dvbs2AsiTrapComp 11 }

dvbs2AsiLnb2Trap  NOTIFICATION-TYPE
	OBJECTS { eventIdTrap, 
		notificationIdTrap, 
		perceivedSeverityTrap, 
		timeStampTrap, 
		additionalTextTrap, 
		dvbs2AsiAlarmsCtrlAddress, 
		dvbs2AsiAlarmsLnb2 }
	STATUS     current
	DESCRIPTION 
		"LNB 2 shortcircuit"
	::= { dvbs2AsiTrapComp 12 }

dvbs2AsiLnb3Trap  NOTIFICATION-TYPE
	OBJECTS { eventIdTrap, 
		notificationIdTrap, 
		perceivedSeverityTrap, 
		timeStampTrap, 
		additionalTextTrap, 
		dvbs2AsiAlarmsCtrlAddress, 
		dvbs2AsiAlarmsLnb3 }
	STATUS     current
	DESCRIPTION 
		"LNB 3 shortcircuit"
	::= { dvbs2AsiTrapComp 13 }

dvbs2AsiLnb4Trap  NOTIFICATION-TYPE
	OBJECTS { eventIdTrap, 
		notificationIdTrap, 
		perceivedSeverityTrap, 
		timeStampTrap, 
		additionalTextTrap, 
		dvbs2AsiAlarmsCtrlAddress, 
		dvbs2AsiAlarmsLnb4 }
	STATUS     current
	DESCRIPTION 
		"LNB 4 shortcircuit"
	::= { dvbs2AsiTrapComp 14 }

dvbs2AsiInputQuality1Trap  NOTIFICATION-TYPE
	OBJECTS { eventIdTrap, 
		notificationIdTrap, 
		perceivedSeverityTrap, 
		timeStampTrap, 
		additionalTextTrap, 
		dvbs2AsiAlarmsCtrlAddress, 
		dvbs2AsiAlarmsInputQuality1 }
	STATUS     current
	DESCRIPTION 
		"Input RF 1 quality low"
	::= { dvbs2AsiTrapComp 15 }

dvbs2AsiInputQuality2Trap  NOTIFICATION-TYPE
	OBJECTS { eventIdTrap, 
		notificationIdTrap, 
		perceivedSeverityTrap, 
		timeStampTrap, 
		additionalTextTrap, 
		dvbs2AsiAlarmsCtrlAddress, 
		dvbs2AsiAlarmsInputQuality2 }
	STATUS     current
	DESCRIPTION 
		"Input RF 2 quality low"
	::= { dvbs2AsiTrapComp 16 }

dvbs2AsiInputQuality3Trap  NOTIFICATION-TYPE
	OBJECTS { eventIdTrap, 
		notificationIdTrap, 
		perceivedSeverityTrap, 
		timeStampTrap, 
		additionalTextTrap, 
		dvbs2AsiAlarmsCtrlAddress, 
		dvbs2AsiAlarmsInputQuality3 }
	STATUS     current
	DESCRIPTION 
		"Input RF 3 quality low"
	::= { dvbs2AsiTrapComp 17 }

dvbs2AsiInputQuality4Trap  NOTIFICATION-TYPE
	OBJECTS { eventIdTrap, 
		notificationIdTrap, 
		perceivedSeverityTrap, 
		timeStampTrap, 
		additionalTextTrap, 
		dvbs2AsiAlarmsCtrlAddress, 
		dvbs2AsiAlarmsInputQuality4 }
	STATUS     current
	DESCRIPTION 
		"Input RF 4 quality low"
	::= { dvbs2AsiTrapComp 18 }

dvbs2AsiOutputAsi1Trap  NOTIFICATION-TYPE
	OBJECTS { eventIdTrap, 
		notificationIdTrap, 
		perceivedSeverityTrap, 
		timeStampTrap, 
		additionalTextTrap, 
		dvbs2AsiAlarmsCtrlAddress, 
		dvbs2AsiAlarmsOutputAsi1 }
	STATUS     current
	DESCRIPTION 
		"Asi Output 1 error"
	::= { dvbs2AsiTrapComp 19 }

dvbs2AsiOutputAsi2Trap  NOTIFICATION-TYPE
	OBJECTS { eventIdTrap, 
		notificationIdTrap, 
		perceivedSeverityTrap, 
		timeStampTrap, 
		additionalTextTrap, 
		dvbs2AsiAlarmsCtrlAddress, 
		dvbs2AsiAlarmsOutputAsi2 }
	STATUS     current
	DESCRIPTION 
		"Asi Output 2 error"
	::= { dvbs2AsiTrapComp 20 }

dvbs2AsiOutputAsi3Trap  NOTIFICATION-TYPE
	OBJECTS { eventIdTrap, 
		notificationIdTrap, 
		perceivedSeverityTrap, 
		timeStampTrap, 
		additionalTextTrap, 
		dvbs2AsiAlarmsCtrlAddress, 
		dvbs2AsiAlarmsOutputAsi3 }
	STATUS     current
	DESCRIPTION 
		"Asi Output 3 error"
	::= { dvbs2AsiTrapComp 21 }

dvbs2AsiOutputAsi4Trap  NOTIFICATION-TYPE
	OBJECTS { eventIdTrap, 
		notificationIdTrap, 
		perceivedSeverityTrap, 
		timeStampTrap, 
		additionalTextTrap, 
		dvbs2AsiAlarmsCtrlAddress, 
		dvbs2AsiAlarmsOutputAsi4 }
	STATUS     current
	DESCRIPTION 
		"Asi Output 4 error"
	::= { dvbs2AsiTrapComp 22 }

dvbs2AsiOutputAsi5Trap  NOTIFICATION-TYPE
	OBJECTS { eventIdTrap, 
		notificationIdTrap, 
		perceivedSeverityTrap, 
		timeStampTrap, 
		additionalTextTrap, 
		dvbs2AsiAlarmsCtrlAddress, 
		dvbs2AsiAlarmsOutputAsi5 }
	STATUS     current
	DESCRIPTION 
		"Asi Output 5 error"
	::= { dvbs2AsiTrapComp 23 }

dvbs2AsiOutputAsi6Trap  NOTIFICATION-TYPE
	OBJECTS { eventIdTrap, 
		notificationIdTrap, 
		perceivedSeverityTrap, 
		timeStampTrap, 
		additionalTextTrap, 
		dvbs2AsiAlarmsCtrlAddress, 
		dvbs2AsiAlarmsOutputAsi6 }
	STATUS     current
	DESCRIPTION 
		"Asi Output 6 error"
	::= { dvbs2AsiTrapComp 24 }

dvbs2AsiOutputAsi7Trap  NOTIFICATION-TYPE
	OBJECTS { eventIdTrap, 
		notificationIdTrap, 
		perceivedSeverityTrap, 
		timeStampTrap, 
		additionalTextTrap, 
		dvbs2AsiAlarmsCtrlAddress, 
		dvbs2AsiEnableAlarmsOutputAsi7 }
	STATUS     current
	DESCRIPTION 
		"Asi Output 7 error"
	::= { dvbs2AsiTrapComp 25 }

dvbs2AsiTemperatureTrap  NOTIFICATION-TYPE
	OBJECTS { eventIdTrap, 
		notificationIdTrap, 
		perceivedSeverityTrap, 
		timeStampTrap, 
		additionalTextTrap, 
		dvbs2AsiAlarmsCtrlAddress, 
		dvbs2AsiAlarmsTemperature }
	STATUS     current
	DESCRIPTION 
		"Temperature Trap"
	::= { dvbs2AsiTrapComp 26 }

dvbs2AsiHwTrap  NOTIFICATION-TYPE
	OBJECTS { eventIdTrap, 
		notificationIdTrap, 
		perceivedSeverityTrap, 
		timeStampTrap, 
		additionalTextTrap, 
		dvbs2AsiAlarmsCtrlAddress, 
		dvbs2AsiAlarmsHw }
	STATUS     current
	DESCRIPTION 
		"Hardward Error Trap"
	::= { dvbs2AsiTrapComp 27 }

ip2AsiFaultTrap  NOTIFICATION-TYPE
	OBJECTS { eventIdTrap, 
		notificationIdTrap, 
		perceivedSeverityTrap, 
		timeStampTrap, 
		additionalTextTrap, 
		ip2AsiCtrlAddressAlarm, 
		ip2AsiMajorAlarm }
	STATUS     current
	DESCRIPTION 
		"Major Trap"
	::= { ip2AsiTrapComp 1 }

ip2AsiMinorTrap  NOTIFICATION-TYPE
	OBJECTS { eventIdTrap, 
		notificationIdTrap, 
		perceivedSeverityTrap, 
		timeStampTrap, 
		additionalTextTrap, 
		ip2AsiCtrlAddressAlarm, 
		ip2AsiMinorAlarm }
	STATUS     current
	DESCRIPTION 
		"Minor Trap"
	::= { ip2AsiTrapComp 2 }

ip2AsiTemperatureTrap  NOTIFICATION-TYPE
	OBJECTS { eventIdTrap, 
		notificationIdTrap, 
		perceivedSeverityTrap, 
		timeStampTrap, 
		additionalTextTrap, 
		ip2AsiCtrlAddressAlarm, 
		ip2AsiTemperatureAlarm }
	STATUS     current
	DESCRIPTION 
		"Temperature Trap"
	::= { ip2AsiTrapComp 3 }

ip2AsiHwTrap  NOTIFICATION-TYPE
	OBJECTS { eventIdTrap, 
		notificationIdTrap, 
		perceivedSeverityTrap, 
		timeStampTrap, 
		additionalTextTrap, 
		ip2AsiCtrlAddressAlarm, 
		ip2AsiHwAlarm }
	STATUS     current
	DESCRIPTION 
		"HWTrap"
	::= { ip2AsiTrapComp 4 }

ip2AsiCommunicationTrap  NOTIFICATION-TYPE
	OBJECTS { eventIdTrap, 
		notificationIdTrap, 
		perceivedSeverityTrap, 
		timeStampTrap, 
		additionalTextTrap, 
		ip2AsiCtrlAddressAlarm, 
		ip2AsiCommunicationAlarm }
	STATUS     current
	DESCRIPTION 
		"Communication Trap"
	::= { ip2AsiTrapComp 5 }

ip2AsiSocketIp01Trap  NOTIFICATION-TYPE
	OBJECTS { eventIdTrap, 
		notificationIdTrap, 
		perceivedSeverityTrap, 
		timeStampTrap, 
		additionalTextTrap, 
		ip2AsiCtrlAddressAlarm, 
		ip2AsiSocketIp01Alarm }
	STATUS     current
	DESCRIPTION 
		"Socket IP-01 Trap"
	::= { ip2AsiTrapComp 6 }

ip2AsiAsiOutput01Trap  NOTIFICATION-TYPE
	OBJECTS { eventIdTrap, 
		notificationIdTrap, 
		perceivedSeverityTrap, 
		timeStampTrap, 
		additionalTextTrap, 
		ip2AsiCtrlAddressAlarm, 
		ip2AsiAsiOutput01Alarm }
	STATUS     current
	DESCRIPTION 
		"Output ASI-01 Trap"
	::= { ip2AsiTrapComp 7 }

ip2AsiSocketIp02Trap  NOTIFICATION-TYPE
	OBJECTS { eventIdTrap, 
		notificationIdTrap, 
		perceivedSeverityTrap, 
		timeStampTrap, 
		additionalTextTrap, 
		ip2AsiCtrlAddressAlarm, 
		ip2AsiSocketIp02Alarm }
	STATUS     current
	DESCRIPTION 
		"Socket IP-02 Trap"
	::= { ip2AsiTrapComp 8 }

ip2AsiAsiOutput02Trap  NOTIFICATION-TYPE
	OBJECTS { eventIdTrap, 
		notificationIdTrap, 
		perceivedSeverityTrap, 
		timeStampTrap, 
		additionalTextTrap, 
		ip2AsiCtrlAddressAlarm, 
		ip2AsiAsiOutput02Alarm }
	STATUS     current
	DESCRIPTION 
		"Output ASI-02 Trap"
	::= { ip2AsiTrapComp 9 }

ip2AsiSocketIp03Trap  NOTIFICATION-TYPE
	OBJECTS { eventIdTrap, 
		notificationIdTrap, 
		perceivedSeverityTrap, 
		timeStampTrap, 
		additionalTextTrap, 
		ip2AsiCtrlAddressAlarm, 
		ip2AsiSocketIp03Alarm }
	STATUS     current
	DESCRIPTION 
		"Socket IP-03 Trap"
	::= { ip2AsiTrapComp 10 }

ip2AsiAsiOutput03Trap  NOTIFICATION-TYPE
	OBJECTS { eventIdTrap, 
		notificationIdTrap, 
		perceivedSeverityTrap, 
		timeStampTrap, 
		additionalTextTrap, 
		ip2AsiCtrlAddressAlarm, 
		ip2AsiAsiOutput03Alarm }
	STATUS     current
	DESCRIPTION 
		"Output ASI-03 Trap"
	::= { ip2AsiTrapComp 11 }

ip2AsiSocketIp04Trap  NOTIFICATION-TYPE
	OBJECTS { eventIdTrap, 
		notificationIdTrap, 
		perceivedSeverityTrap, 
		timeStampTrap, 
		additionalTextTrap, 
		ip2AsiCtrlAddressAlarm, 
		ip2AsiSocketIp04Alarm }
	STATUS     current
	DESCRIPTION 
		"Socket IP-04 Trap"
	::= { ip2AsiTrapComp 12 }

ip2AsiAsiOutput04Trap  NOTIFICATION-TYPE
	OBJECTS { eventIdTrap, 
		notificationIdTrap, 
		perceivedSeverityTrap, 
		timeStampTrap, 
		additionalTextTrap, 
		ip2AsiCtrlAddressAlarm, 
		ip2AsiAsiOutput04Alarm }
	STATUS     current
	DESCRIPTION 
		"Output ASI-04 Trap"
	::= { ip2AsiTrapComp 13 }

ip2AsiSocketIp05Trap  NOTIFICATION-TYPE
	OBJECTS { eventIdTrap, 
		notificationIdTrap, 
		perceivedSeverityTrap, 
		timeStampTrap, 
		additionalTextTrap, 
		ip2AsiCtrlAddressAlarm, 
		ip2AsiSocketIp05Alarm }
	STATUS     current
	DESCRIPTION 
		"Socket IP-05 Trap"
	::= { ip2AsiTrapComp 14 }

ip2AsiAsiOutput05Trap  NOTIFICATION-TYPE
	OBJECTS { eventIdTrap, 
		notificationIdTrap, 
		perceivedSeverityTrap, 
		timeStampTrap, 
		additionalTextTrap, 
		ip2AsiCtrlAddressAlarm, 
		ip2AsiAsiOutput05Alarm }
	STATUS     current
	DESCRIPTION 
		"Output ASI-05 Trap"
	::= { ip2AsiTrapComp 15 }

ip2AsiSocketIp06Trap  NOTIFICATION-TYPE
	OBJECTS { eventIdTrap, 
		notificationIdTrap, 
		perceivedSeverityTrap, 
		timeStampTrap, 
		additionalTextTrap, 
		ip2AsiCtrlAddressAlarm, 
		ip2AsiSocketIp06Alarm }
	STATUS     current
	DESCRIPTION 
		"Socket IP-06 Trap"
	::= { ip2AsiTrapComp 16 }

ip2AsiAsiOutput06Trap  NOTIFICATION-TYPE
	OBJECTS { eventIdTrap, 
		notificationIdTrap, 
		perceivedSeverityTrap, 
		timeStampTrap, 
		additionalTextTrap, 
		ip2AsiCtrlAddressAlarm, 
		ip2AsiAsiOutput06Alarm }
	STATUS     current
	DESCRIPTION 
		"Output ASI-06 Trap"
	::= { ip2AsiTrapComp 17 }

ip2AsiSocketIp07Trap  NOTIFICATION-TYPE
	OBJECTS { eventIdTrap, 
		notificationIdTrap, 
		perceivedSeverityTrap, 
		timeStampTrap, 
		additionalTextTrap, 
		ip2AsiCtrlAddressAlarm, 
		ip2AsiSocketIp07Alarm }
	STATUS     current
	DESCRIPTION 
		"Socket IP-07 Trap"
	::= { ip2AsiTrapComp 18 }

ip2AsiAsiOutput07Trap  NOTIFICATION-TYPE
	OBJECTS { eventIdTrap, 
		notificationIdTrap, 
		perceivedSeverityTrap, 
		timeStampTrap, 
		additionalTextTrap, 
		ip2AsiCtrlAddressAlarm, 
		ip2AsiAsiOutput07Alarm }
	STATUS     current
	DESCRIPTION 
		"Output ASI-07 Trap"
	::= { ip2AsiTrapComp 19 }

groupSystem  OBJECT-GROUP
	OBJECTS { sysCycleDBTM, 
		sysDescrDBTM, 
		sysFileDateHourDBTM, 
		sysNameDBTM, 
		sysManagementVersionDBTM, 
		sysKernelVersionDBTM, 
		sysRedundanceDBTM, 
		sysSnmpVersionDBTM }
	STATUS     current
	DESCRIPTION 
		"Contains all the objects from system branch of the MIB"
	::= { objectGroups 1 }

groupAdmin  OBJECT-GROUP
	OBJECTS { date, 
		hour, 
		status, 
		networkIpAddress, 
		networkMaskAddress, 
		networkGatewayAddress, 
		networkRoutingDestination, 
		networkRoutingEnabled, 
		networkRoutingGateway, 
		networkRoutingInterfaz, 
		networkRoutingMask, 
		ntpServerDays, 
		ntpServerHours, 
		ntpServerIp, 
		ntpServerMinutes, 
		ntpServerOffset, 
		ntpServerUpdate, 
		ntpServerStatus, 
		powerSupplyStatus, 
		snmpFastTrapsSync, 
		snmpInformAck, 
		snmpInformRetries, 
		snmpInformTimeout, 
		snmpReadCommunity, 
		snmpTrapsPeriodic, 
		snmpWriteCommunity, 
		snmpTrapControlRateStatus, 
		snmpTrapControlPeriod, 
		snmpTrapsDestionationEnable, 
		snmpTrapsSync, 
		snmpTrapsAuthTrapEnable, 
		snmpTrapsCommunity, 
		snmpTrapsDestinationIP, 
		webserverAutoRefresh, 
		webserverUser1, 
		webserverUser2, 
		webserverNewPass }
	STATUS     current
	DESCRIPTION 
		"Contains all the objects from general branch of the MIB"
	::= { objectGroups 2 }

groupAlarmTrapTable  OBJECT-GROUP
	OBJECTS { eventIdTrap, 
		notificationIdTrap, 
		perceivedSeverityTrap, 
		timeStampTrap, 
		additionalTextTrap }
	STATUS     current
	DESCRIPTION 
		"Contains all the objects from the dvbtAlarmTrapTable branch of the MIB"
	::= { objectGroups 3 }

groupAlarmsTraps  NOTIFICATION-GROUP
	NOTIFICATIONS { adaptativeEcho10Trap, 
		adaptativeEcho11Trap, 
		adaptativeEcho12Trap, 
		adaptativeEcho13Trap, 
		adaptativeEcho14Trap, 
		adaptativeEcho15Trap, 
		adaptativeEcho1Trap, 
		adaptativeEcho2Trap, 
		adaptativeEcho3Trap, 
		adaptativeEcho4Trap, 
		adaptativeEcho5Trap, 
		adaptativeEcho6Trap, 
		adaptativeEcho7Trap, 
		adaptativeEcho8Trap, 
		adaptativeEcho9Trap, 
		adaptativeEcho25Trap, 
		adaptativeEcho26Trap, 
		adaptativeEcho27Trap, 
		adaptativeEcho28Trap, 
		adaptativeEcho29Trap, 
		adaptativeEcho30Trap, 
		gpsSyncGPS1Trap, 
		gpsSyncGPS2Trap, 
		adaptativeEcho16Trap, 
		adaptativeEcho17Trap, 
		adaptativeEcho18Trap, 
		adaptativeEcho19Trap, 
		adaptativeEcho20Trap, 
		adaptativeEcho21Trap, 
		adaptativeEcho22Trap, 
		adaptativeEcho23Trap, 
		adaptativeEcho24Trap, 
		asi1Error10Trap, 
		asi1Error11Trap, 
		asi1Error12Trap, 
		asi1Error13Trap, 
		asi1Error14Trap, 
		asi1Error15Trap, 
		asi1Error1Trap, 
		asi1Error2Trap, 
		asi1Error3Trap, 
		asi1Error4Trap, 
		asi1Error5Trap, 
		asi1Error6Trap, 
		asi1Error7Trap, 
		asi1Error8Trap, 
		asi1Error9Trap, 
		asi1Error25Trap, 
		asi1Error26Trap, 
		asi1Error27Trap, 
		asi1Error28Trap, 
		asi1Error29Trap, 
		asi1Error30Trap, 
		asi1Error16Trap, 
		asi1Error17Trap, 
		asi1Error18Trap, 
		asi1Error19Trap, 
		asi1Error20Trap, 
		asi1Error21Trap, 
		asi1Error22Trap, 
		asi1Error23Trap, 
		asi1Error24Trap, 
		channelBer1Trap, 
		channelBer2Trap, 
		channelBer3Trap, 
		channelBer4Trap, 
		channelBer5Trap, 
		channelBer6Trap, 
		channelBer7Trap, 
		channelBer8Trap, 
		channelBer9Trap, 
		channelBer10Trap, 
		channelBer11Trap, 
		channelBer12Trap, 
		channelBer13Trap, 
		channelBer14Trap, 
		channelBer15Trap, 
		channelBer16Trap, 
		channelBer17Trap, 
		channelBer18Trap, 
		channelBer19Trap, 
		channelBer20Trap, 
		channelBer21Trap, 
		channelBer22Trap, 
		channelBer23Trap, 
		channelBer24Trap, 
		channelBer25Trap, 
		channelBer26Trap, 
		channelBer27Trap, 
		channelBer28Trap, 
		channelBer29Trap, 
		channelBer30Trap, 
		coldStartTrap, 
		dvbs2AsiHwTrap, 
		dvbs2AsiInputQuality1Trap, 
		dvbs2AsiInputQuality2Trap, 
		dvbs2AsiInputQuality3Trap, 
		dvbs2AsiInputQuality4Trap, 
		dvbs2AsiInputUnlock3Trap, 
		dvbs2AsiInputUnlock4Trap, 
		dvbs2AsiLnb1Trap, 
		dvbs2AsiLnb2Trap, 
		dvbs2AsiLnb3Trap, 
		dvbs2AsiLnb4Trap, 
		dvbs2AsiOutputAsi1Trap, 
		dvbs2AsiOutputAsi2Trap, 
		dvbs2AsiOutputAsi3Trap, 
		dvbs2AsiOutputAsi4Trap, 
		dvbs2AsiOutputAsi5Trap, 
		dvbs2AsiOutputAsi6Trap, 
		dvbs2AsiOutputAsi7Trap, 
		dvbs2AsiTemperatureTrap, 
		fanAlarm10Trap, 
		fanAlarm11Trap, 
		fanAlarm12Trap, 
		fanAlarm13Trap, 
		fanAlarm14Trap, 
		fanAlarm15Trap, 
		fanAlarm16Trap, 
		fanAlarm17Trap, 
		fanAlarm18Trap, 
		fanAlarm19Trap, 
		fanAlarm1Trap, 
		fanAlarm20Trap, 
		fanAlarm21Trap, 
		fanAlarm22Trap, 
		fanAlarm23Trap, 
		fanAlarm24Trap, 
		fanAlarm25Trap, 
		fanAlarm26Trap, 
		fanAlarm27Trap, 
		fanAlarm28Trap, 
		fanAlarm29Trap, 
		fanAlarm2Trap, 
		fanAlarm30Trap, 
		fanAlarm3Trap, 
		fanAlarm4Trap, 
		fanAlarm5Trap, 
		fanAlarm6Trap, 
		fanAlarm7Trap, 
		fanAlarm8Trap, 
		fanAlarm9Trap, 
		newConfigurationFileTrap, 
		majorMUX16Traps, 
		majorMUX17Traps, 
		majorMUX18Traps, 
		majorMUX19Traps, 
		majorMUX20Traps, 
		majorMUX21Traps, 
		majorMUX22Traps, 
		majorMUX23Traps, 
		majorMUX24Traps, 
		majorMUX25Traps, 
		majorMUX26Traps, 
		majorMUX27Traps, 
		majorMUX28Traps, 
		majorMUX29Traps, 
		majorMUX30Traps, 
		minorMUX16Traps, 
		minorMUX17Traps, 
		minorMUX18Traps, 
		minorMUX19Traps, 
		minorMUX20Traps, 
		minorMUX21Traps, 
		minorMUX22Traps, 
		minorMUX23Traps, 
		minorMUX24Traps, 
		minorMUX25Traps, 
		minorMUX26Traps, 
		minorMUX27Traps, 
		minorMUX28Traps, 
		minorMUX29Traps, 
		minorMUX30Traps, 
		mipError1Trap, 
		mipError2Trap, 
		mipError3Trap, 
		mipError4Trap, 
		mipError5Trap, 
		mipError6Trap, 
		mipError7Trap, 
		mipError8Trap, 
		mipError9Trap, 
		mipError10Trap, 
		mipError11Trap, 
		mipError12Trap, 
		mipError13Trap, 
		mipError14Trap, 
		mipError15Trap, 
		mipError16Trap, 
		mipError17Trap, 
		mipError18Trap, 
		mipError19Trap, 
		mipError20Trap, 
		mipError21Trap, 
		mipError22Trap, 
		mipError23Trap, 
		mipError24Trap, 
		mipError25Trap, 
		mipError26Trap, 
		mipError27Trap, 
		mipError28Trap, 
		mipError29Trap, 
		mipError30Trap, 
		pps1Trap, 
		pps2Trap, 
		pps3Trap, 
		pps4Trap, 
		pps5Trap, 
		pps6Trap, 
		pps7Trap, 
		pps8Trap, 
		pps9Trap, 
		pps10Trap, 
		pps11Trap, 
		pps12Trap, 
		pps13Trap, 
		pps14Trap, 
		pps15Trap, 
		pps16Trap, 
		pps17Trap, 
		pps18Trap, 
		pps19Trap, 
		pps20Trap, 
		pps21Trap, 
		pps22Trap, 
		pps23Trap, 
		pps24Trap, 
		pps25Trap, 
		pps26Trap, 
		pps27Trap, 
		pps28Trap, 
		pps29Trap, 
		pps30Trap, 
		iFDVBTSignal1Trap, 
		iFDVBTSignal2Trap, 
		iFDVBTSignal3Trap, 
		iFDVBTSignal4Trap, 
		iFDVBTSignal5Trap, 
		iFDVBTSignal6Trap, 
		iFDVBTSignal7Trap, 
		iFDVBTSignal8Trap, 
		iFDVBTSignal9Trap, 
		iFDVBTSignal10Trap, 
		iFDVBTSignal11Trap, 
		iFDVBTSignal12Trap, 
		iFDVBTSignal13Trap, 
		iFDVBTSignal14Trap, 
		iFDVBTSignal15Trap, 
		iFDVBTSignal16Trap, 
		iFDVBTSignal17Trap, 
		iFDVBTSignal18Trap, 
		iFDVBTSignal19Trap, 
		iFDVBTSignal20Trap, 
		iFDVBTSignal21Trap, 
		iFDVBTSignal22Trap, 
		iFDVBTSignal23Trap, 
		iFDVBTSignal24Trap, 
		iFDVBTSignal25Trap, 
		iFDVBTSignal26Trap, 
		iFDVBTSignal27Trap, 
		iFDVBTSignal28Trap, 
		iFDVBTSignal29Trap, 
		iFDVBTSignal30Trap, 
		gps10MHz1Trap, 
		gps10MHz2Trap, 
		gps10MHz3Trap, 
		gps10MHz4Trap, 
		gps10MHz5Trap, 
		gps10MHz6Trap, 
		gps10MHz7Trap, 
		gps10MHz8Trap, 
		gps10MHz9Trap, 
		gps10MHz10Trap, 
		gps10MHz11Trap, 
		gps10MHz12Trap, 
		gps10MHz13Trap, 
		gps10MHz14Trap, 
		gps10MHz15Trap, 
		gps10MHz16Trap, 
		gps10MHz17Trap, 
		gps10MHz18Trap, 
		gps10MHz19Trap, 
		gps10MHz20Trap, 
		gps10MHz21Trap, 
		gps10MHz22Trap, 
		gps10MHz23Trap, 
		gps10MHz24Trap, 
		gps10MHz25Trap, 
		gps10MHz26Trap, 
		gps10MHz27Trap, 
		gps10MHz28Trap, 
		gps10MHz29Trap, 
		gps10MHz30Trap, 
		input10Traps, 
		input11Traps, 
		input12Traps, 
		input13Traps, 
		input14Traps, 
		input15Traps, 
		input1Traps, 
		input2Traps, 
		input3Traps, 
		input4Traps, 
		input5Traps, 
		input6Traps, 
		input7Traps, 
		input8Traps, 
		input9Traps, 
		moduleCommunicationUCA1Trap, 
		moduleCommunicationUCA3Trap, 
		powerAmplifierCommunic1Trap, 
		powerAmplifierCommunic2Trap, 
		powerAmplifierCommunic3Trap, 
		powerAmplifierCommunic4Trap, 
		powerAmplifierCommunic5Trap, 
		powerAmplifierCommunic6Trap, 
		powerAmplifierCommunic7Trap, 
		powerAmplifierCommunic8Trap, 
		powerAmplifierCommunic9Trap, 
		powerAmplifierCommunic10Trap, 
		powerAmplifierCommunic11Trap, 
		powerAmplifierCommunic12Trap, 
		powerAmplifierCommunic13Trap, 
		powerAmplifierCommunic14Trap, 
		powerAmplifierCommunic15Trap, 
		powerAmplifierCommunic16Trap, 
		powerAmplifierCommunic17Trap, 
		powerAmplifierCommunic18Trap, 
		powerAmplifierCommunic19Trap, 
		powerAmplifierCommunic20Trap, 
		powerAmplifierCommunic21Trap, 
		powerAmplifierCommunic22Trap, 
		powerAmplifierCommunic23Trap, 
		powerAmplifierCommunic24Trap, 
		powerAmplifierCommunic25Trap, 
		powerAmplifierCommunic26Trap, 
		powerAmplifierCommunic27Trap, 
		powerAmplifierCommunic28Trap, 
		powerAmplifierCommunic29Trap, 
		powerAmplifierCommunic30Trap, 
		moduleCommunication1Trap, 
		moduleCommunication2Trap, 
		moduleCommunication3Trap, 
		moduleCommunication4Trap, 
		moduleCommunication5Trap, 
		moduleCommunication6Trap, 
		moduleCommunication7Trap, 
		moduleCommunication8Trap, 
		moduleCommunication9Trap, 
		moduleCommunication10Trap, 
		moduleCommunication11Trap, 
		moduleCommunication13Trap, 
		moduleCommunication14Trap, 
		moduleCommunication15Trap, 
		moduleCommunication2BTrap, 
		moduleCommunication3BTrap, 
		moduleCommunication4BTrap, 
		moduleCommunication5BTrap, 
		moduleCommunication6BTrap, 
		moduleCommunication7BTrap, 
		moduleCommunication8BTrap, 
		moduleCommunication9BTrap, 
		moduleCommunication10BTrap, 
		moduleCommunication11BTrap, 
		moduleCommunication13BTrap, 
		moduleCommunication14BTrap, 
		moduleCommunication15BTrap, 
		n1conmutation5Trap, 
		powerSupply1UCASSCCTrap, 
		powerSupply1UCA1Trap, 
		powerSupply1UCA2Trap, 
		powerSupply1UCA3Trap, 
		powerSupply2UCASSCCTrap, 
		powerSupply2UCA1Trap, 
		powerSupply2UCA2Trap, 
		powerSupply2UCA3Trap, 
		gpsHoldoverGPS1Trap, 
		gpsHoldoverGPS2Trap, 
		gpsAntennaGPS1Trap, 
		gpsAntennaGPS2Trap, 
		moduleCommunicationCONTACTSTrap, 
		moduleCommunicationGPS1Trap, 
		moduleCommunicationGPS2Trap, 
		moduleCommunicationUCA2Trap, 
		moduleCommunicationUCASSCCTrap, 
		relay1Trap, 
		relay2Trap, 
		relay3Trap, 
		relay4Trap, 
		relay5Trap, 
		relay6Trap, 
		relay7Trap, 
		relay8Trap, 
		relay9Trap, 
		relay10Trap, 
		relay11Trap, 
		relay12Trap, 
		relay13Trap, 
		relay14Trap, 
		relay15Trap, 
		minorMUX1Traps, 
		minorMUX2Traps, 
		minorMUX3Traps, 
		minorMUX4Traps, 
		minorMUX5Traps, 
		minorMUX6Traps, 
		minorMUX7Traps, 
		minorMUX8Traps, 
		minorMUX9Traps, 
		minorMUX10Traps, 
		minorMUX11Traps, 
		minorMUX12Traps, 
		minorMUX13Traps, 
		minorMUX14Traps, 
		minorMUX15Traps, 
		majorMUX10Traps, 
		majorMUX11Traps, 
		majorMUX12Traps, 
		majorMUX13Traps, 
		majorMUX14Traps, 
		majorMUX15Traps, 
		minorUCAsTraps, 
		minorGPSTraps, 
		majorMUX1Traps, 
		majorMUX2Traps, 
		majorMUX3Traps, 
		majorMUX4Traps, 
		majorMUX5Traps, 
		majorMUX6Traps, 
		majorMUX7Traps, 
		majorMUX8Traps, 
		majorMUX9Traps, 
		majorUCAsTraps, 
		majorGPSsTraps, 
		moduleCommunication12Trap, 
		moduleCommunication1BTrap, 
		moduleCommunication12BTrap, 
		moduleCommunicationUCA101Trap, 
		moduleCommunicationUCA102Trap, 
		moduleCommunicationUCA103Trap, 
		moduleCommunicationUCA104Trap, 
		moduleCommunicationUCA105Trap, 
		moduleCommunicationUCA106Trap, 
		moduleCommunicationUCA107Trap, 
		moduleCommunicationUCA108Trap, 
		moduleCommunicationUCA109Trap, 
		moduleCommunicationUCA110Trap, 
		moduleCommunicationUCA111Trap, 
		moduleCommunicationUCA112Trap, 
		moduleCommunicationUCA113Trap, 
		moduleCommunicationUCA114Trap, 
		moduleCommunicationUCA115Trap, 
		moduleCommunicationUCA4Trap, 
		moduleCommunicationUCA5Trap, 
		n1conmutation1Trap, 
		n1conmutation2Trap, 
		n1conmutation3Trap, 
		n1conmutation4Trap, 
		n1conmutation6Trap, 
		noInputSignal10Trap, 
		noInputSignal11Trap, 
		noInputSignal12Trap, 
		noInputSignal13Trap, 
		noInputSignal14Trap, 
		noInputSignal15Trap, 
		noInputSignal1Trap, 
		noInputSignal2Trap, 
		noInputSignal3Trap, 
		noInputSignal4Trap, 
		noInputSignal5Trap, 
		noInputSignal6Trap, 
		noInputSignal7Trap, 
		noInputSignal8Trap, 
		noInputSignal9Trap, 
		noInputSignal25Trap, 
		noInputSignal26Trap, 
		noInputSignal27Trap, 
		noInputSignal28Trap, 
		noInputSignal29Trap, 
		noInputSignal30Trap, 
		noInputSignal16Trap, 
		noInputSignal17Trap, 
		noInputSignal18Trap, 
		noInputSignal19Trap, 
		noInputSignal20Trap, 
		noInputSignal21Trap, 
		noInputSignal22Trap, 
		noInputSignal23Trap, 
		noInputSignal24Trap, 
		periodicTrap, 
		externalSupplyTrap, 
		powerSupply1UC4Trap, 
		powerSupply1UCA5Trap, 
		powerSupply2UCA4Trap, 
		powerSupply2UCA5Trap, 
		reflectedPower10Trap, 
		reflectedPower11Trap, 
		reflectedPower12Trap, 
		reflectedPower13Trap, 
		reflectedPower14Trap, 
		reflectedPower15Trap, 
		reflectedPower1Trap, 
		reflectedPower2Trap, 
		reflectedPower3Trap, 
		reflectedPower4Trap, 
		reflectedPower5Trap, 
		reflectedPower6Trap, 
		reflectedPower7Trap, 
		reflectedPower8Trap, 
		reflectedPower9Trap, 
		reflectedPower25Trap, 
		reflectedPower26Trap, 
		reflectedPower27Trap, 
		reflectedPower28Trap, 
		reflectedPower29Trap, 
		reflectedPower30Trap, 
		reflectedPower16Trap, 
		reflectedPower17Trap, 
		reflectedPower18Trap, 
		reflectedPower19Trap, 
		reflectedPower20Trap, 
		reflectedPower21Trap, 
		reflectedPower22Trap, 
		reflectedPower23Trap, 
		reflectedPower24Trap, 
		uca103MuxBTrap, 
		uca103UndeterminatedPositionTrap, 
		uca104BlockedBTrap, 
		uca104ConmutationErrorTrap, 
		uca104ConmutationTrap, 
		uca104MuxATrap, 
		uca104MuxBTrap, 
		uca104UndeterminatedPositionTrap, 
		uca105BlockedBTrap, 
		uca105ConmutationErrorTrap, 
		uca105ConmutationTrap, 
		uca105MuxATrap, 
		uca105MuxBTrap, 
		uca105UndeterminatedPositionTrap, 
		uca106BlockedBTrap, 
		uca106ConmutationErrorTrap, 
		uca106ConmutationTrap, 
		uca106MuxATrap, 
		uca106MuxBTrap, 
		uca106UndeterminatedPositionTrap, 
		uca107BlockedBTrap, 
		uca107ConmutationErrorTrap, 
		uca107ConmutationTrap, 
		uca107MuxATrap, 
		uca107MuxBTrap, 
		uca107UndeterminatedPositionTrap, 
		uca108BlockedBTrap, 
		uca108ConmutationErrorTrap, 
		uca108ConmutationTrap, 
		uca108MuxATrap, 
		uca108MuxBTrap, 
		uca108UndeterminatedPositionTrap, 
		uca109BlockedBTrap, 
		uca109ConmutationErrorTrap, 
		uca109ConmutationTrap, 
		uca109IncorrectConfigurationTrap, 
		uca109MuxBTrap, 
		uca109UndeterminatedPositionTrap, 
		uca110BlockedBTrap, 
		uca110ConmutationErrorTrap, 
		uca110ConmutationTrap, 
		uca110MuxATrap, 
		uca110MuxBTrap, 
		uca110UndeterminatedPositionTrap, 
		uca111BlockedBTrap, 
		uca111ConmutationErrorTrap, 
		uca111ConmutationTrap, 
		uca111MuxATrap, 
		uca111MuxBTrap, 
		uca111UndeterminatedPositionTrap, 
		uca112BlockedBTrap, 
		uca112ConmutationErrorTrap, 
		uca112ConmutationTrap, 
		uca112MuxATrap, 
		uca112MuxBTrap, 
		uca112UndeterminatedPositionTrap, 
		uca113BlockedBTrap, 
		uca113ConmutationErrorTrap, 
		uca113ConmutationTrap, 
		uca113MuxATrap, 
		uca113MuxBTrap, 
		uca113UndeterminatedPositionTrap, 
		uca114BlockedBTrap, 
		uca114ConmutationErrorTrap, 
		uca114ConmutationTrap, 
		uca114MuxATrap, 
		uca114MuxBTrap, 
		uca114UndeterminatedPositionTrap, 
		uca115BlockedBTrap, 
		uca115ConmutationErrorTrap, 
		uca115ConmutationTrap, 
		uca115MuxATrap, 
		uca115MuxBTrap, 
		uca115UndeterminatedPositionTrap, 
		temperature10Trap, 
		temperature11Trap, 
		temperature12Trap, 
		temperature13Trap, 
		temperature14Trap, 
		temperature15Trap, 
		temperature1Trap, 
		temperature2Trap, 
		temperature3Trap, 
		temperature4Trap, 
		temperature5Trap, 
		temperature6Trap, 
		temperature7Trap, 
		temperature8Trap, 
		temperature9Trap, 
		temperature25Trap, 
		temperature26Trap, 
		temperature27Trap, 
		temperature28Trap, 
		temperature29Trap, 
		temperature30Trap, 
		temperature16Trap, 
		temperature17Trap, 
		temperature18Trap, 
		temperature19Trap, 
		temperature20Trap, 
		temperature21Trap, 
		temperature22Trap, 
		temperature23Trap, 
		temperature24Trap, 
		transmittedPower10Trap, 
		transmittedPower11Trap, 
		transmittedPower12Trap, 
		transmittedPower13Trap, 
		transmittedPower14Trap, 
		transmittedPower15Trap, 
		transmittedPower1Trap, 
		transmittedPower2Trap, 
		transmittedPower3Trap, 
		transmittedPower4Trap, 
		transmittedPower5Trap, 
		transmittedPower6Trap, 
		transmittedPower7Trap, 
		transmittedPower8Trap, 
		transmittedPower9Trap, 
		transmittedPower25Trap, 
		transmittedPower26Trap, 
		transmittedPower27Trap, 
		transmittedPower28Trap, 
		transmittedPower29Trap, 
		transmittedPower30Trap, 
		transmittedPower16Trap, 
		transmittedPower17Trap, 
		transmittedPower18Trap, 
		transmittedPower19Trap, 
		transmittedPower20Trap, 
		transmittedPower21Trap, 
		transmittedPower22Trap, 
		transmittedPower23Trap, 
		transmittedPower24Trap, 
		trtCurrentsOutRange10Trap, 
		trtCurrentsOutRange11Trap, 
		trtCurrentsOutRange12Trap, 
		trtCurrentsOutRange13Trap, 
		trtCurrentsOutRange14Trap, 
		trtCurrentsOutRange15Trap, 
		trtCurrentsOutRange1Trap, 
		trtCurrentsOutRange2Trap, 
		trtCurrentsOutRange3Trap, 
		trtCurrentsOutRange4Trap, 
		trtCurrentsOutRange5Trap, 
		trtCurrentsOutRange6Trap, 
		trtCurrentsOutRange7Trap, 
		trtCurrentsOutRange8Trap, 
		trtCurrentsOutRange9Trap, 
		trtCurrentsOutRange25Trap, 
		trtCurrentsOutRange26Trap, 
		trtCurrentsOutRange27Trap, 
		trtCurrentsOutRange28Trap, 
		trtCurrentsOutRange29Trap, 
		trtCurrentsOutRange30Trap, 
		trtCurrentsOutRange16Trap, 
		trtCurrentsOutRange17Trap, 
		trtCurrentsOutRange18Trap, 
		trtCurrentsOutRange19Trap, 
		trtCurrentsOutRange20Trap, 
		trtCurrentsOutRange21Trap, 
		trtCurrentsOutRange22Trap, 
		trtCurrentsOutRange23Trap, 
		trtCurrentsOutRange24Trap, 
		uca101BlockedATrap, 
		uca101BlockedBTrap, 
		uca101ConmutationErrorTrap, 
		uca101IncorrectConfigurationTrap, 
		uca101UndeterminatedPositionTrap, 
		uca101ConmutationTrap, 
		uca101MuxATrap, 
		uca101MuxBTrap, 
		uca102BlockedATrap, 
		uca102BlockedBTrap, 
		uca102ConmutationErrorTrap, 
		uca102ConmutationTrap, 
		uca102IncorrectConfigurationTrap, 
		uca102MuxATrap, 
		uca102MuxBTrap, 
		uca102UndeterminatedPositionTrap, 
		uca103BlockedATrap, 
		uca103BlockedBTrap, 
		uca103ConmutationErrorTrap, 
		uca103ConmutationTrap, 
		uca103IncorrectConfigurationTrap, 
		uca103MuxATrap, 
		uca104BlockedATrap, 
		uca104IncorrectConfigurationTrap, 
		uca105BlockedATrap, 
		uca105IncorrectConfigurationTrap, 
		uca106BlockedATrap, 
		uca106IncorrectConfigurationTrap, 
		uca107BlockedATrap, 
		uca107IncorrectConfigurationTrap, 
		uca108BlockedATrap, 
		uca108IncorrectConfigurationTrap, 
		uca109BlockedATrap, 
		uca109MuxATrap, 
		uca110BlockedATrap, 
		uca110IncorrectConfigurationTrap, 
		uca111BlockedATrap, 
		uca111IncorrectConfigurationTrap, 
		uca112BlockedATrap, 
		uca112IncorrectConfigurationTrap, 
		uca113BlockedATrap, 
		uca113IncorrectConfigurationTrap, 
		uca114BlockedATrap, 
		uca114IncorrectConfigurationTrap, 
		uca115BlockedATrap, 
		uca115IncorrectConfigurationTrap, 
		unlockTS10Trap, 
		unlockTS11Trap, 
		unlockTS12Trap, 
		unlockTS13Trap, 
		unlockTS14Trap, 
		unlockTS15Trap, 
		unlockTS1Trap, 
		unlockTS2Trap, 
		unlockTS3Trap, 
		unlockTS4Trap, 
		unlockTS5Trap, 
		unlockTS6Trap, 
		unlockTS7Trap, 
		unlockTS8Trap, 
		unlockTS9Trap, 
		unlockTS25Trap, 
		unlockTS26Trap, 
		unlockTS27Trap, 
		unlockTS28Trap, 
		unlockTS29Trap, 
		unlockTS30Trap, 
		unlockTS16Trap, 
		unlockTS17Trap, 
		unlockTS18Trap, 
		unlockTS19Trap, 
		unlockTS20Trap, 
		unlockTS21Trap, 
		unlockTS22Trap, 
		unlockTS23Trap, 
		unlockTS24Trap, 
		viterbiBer10Trap, 
		viterbiBer11Trap, 
		viterbiBer12Trap, 
		viterbiBer13Trap, 
		viterbiBer14Trap, 
		viterbiBer15Trap, 
		viterbiBer1Trap, 
		viterbiBer2Trap, 
		viterbiBer3Trap, 
		viterbiBer4Trap, 
		viterbiBer5Trap, 
		viterbiBer6Trap, 
		viterbiBer7Trap, 
		viterbiBer8Trap, 
		viterbiBer9Trap, 
		viterbiBer25Trap, 
		viterbiBer26Trap, 
		viterbiBer27Trap, 
		viterbiBer28Trap, 
		viterbiBer29Trap, 
		viterbiBer30Trap, 
		viterbiBer16Trap, 
		viterbiBer17Trap, 
		viterbiBer18Trap, 
		viterbiBer19Trap, 
		viterbiBer20Trap, 
		viterbiBer21Trap, 
		viterbiBer22Trap, 
		viterbiBer23Trap, 
		viterbiBer24Trap,
		asi2Error1Trap, 
		asi2Error2Trap, 
		asi2Error3Trap, 
		asi2Error4Trap, 
		asi2Error5Trap, 
		asi2Error6Trap, 
		asi2Error7Trap, 
		asi2Error8Trap, 
		asi2Error9Trap, 
		asi2Error10Trap, 
		asi2Error11Trap, 
		asi2Error12Trap, 
		asi2Error13Trap, 
		asi2Error14Trap, 
		asi2Error15Trap, 
		asi2Error16Trap, 
		asi2Error17Trap, 
		asi2Error18Trap, 
		asi2Error19Trap, 
		asi2Error20Trap, 
		asi2Error21Trap, 
		asi2Error22Trap, 
		asi2Error23Trap, 
		asi2Error24Trap, 
		asi2Error25Trap, 
		asi2Error26Trap, 
		asi2Error27Trap, 
		asi2Error28Trap, 
		asi2Error29Trap, 
		asi2Error30Trap,
		mpeg1Error1Trap, 
		mpeg1Error2Trap, 
		mpeg1Error3Trap, 
		mpeg1Error4Trap, 
		mpeg1Error5Trap, 
		mpeg1Error6Trap, 
		mpeg1Error7Trap, 
		mpeg1Error8Trap, 
		mpeg1Error9Trap, 
		mpeg1Error10Trap, 
		mpeg1Error11Trap, 
		mpeg1Error12Trap, 
		mpeg1Error13Trap, 
		mpeg1Error14Trap, 
		mpeg1Error15Trap, 
		mpeg1Error16Trap, 
		mpeg1Error17Trap, 
		mpeg1Error18Trap, 
		mpeg1Error19Trap, 
		mpeg1Error20Trap, 
		mpeg1Error21Trap, 
		mpeg1Error22Trap, 
		mpeg1Error23Trap, 
		mpeg1Error24Trap, 
		mpeg1Error25Trap, 
		mpeg1Error26Trap, 
		mpeg1Error27Trap, 
		mpeg1Error28Trap, 
		mpeg1Error29Trap, 
		mpeg1Error30Trap,
		mpeg2Error1Trap, 
		mpeg2Error2Trap, 
		mpeg2Error3Trap, 
		mpeg2Error4Trap, 
		mpeg2Error5Trap, 
		mpeg2Error6Trap, 
		mpeg2Error7Trap, 
		mpeg2Error8Trap, 
		mpeg2Error9Trap, 
		mpeg2Error10Trap, 
		mpeg2Error11Trap, 
		mpeg2Error12Trap, 
		mpeg2Error13Trap, 
		mpeg2Error14Trap, 
		mpeg2Error15Trap, 
		mpeg2Error16Trap, 
		mpeg2Error17Trap, 
		mpeg2Error18Trap, 
		mpeg2Error19Trap, 
		mpeg2Error20Trap, 
		mpeg2Error21Trap, 
		mpeg2Error22Trap, 
		mpeg2Error23Trap, 
		mpeg2Error24Trap, 
		mpeg2Error25Trap, 
		mpeg2Error26Trap, 
		mpeg2Error27Trap, 
		mpeg2Error28Trap, 
		mpeg2Error29Trap, 
		mpeg2Error30Trap,
		sfnError1Trap, 
		sfnError2Trap, 
		sfnError3Trap, 
		sfnError4Trap, 
		sfnError5Trap, 
		sfnError6Trap, 
		sfnError7Trap, 
		sfnError8Trap, 
		sfnError9Trap, 
		sfnError10Trap, 
		sfnError11Trap, 
		sfnError12Trap, 
		sfnError13Trap, 
		sfnError14Trap, 
		sfnError15Trap, 
		sfnError16Trap, 
		sfnError17Trap, 
		sfnError18Trap, 
		sfnError19Trap, 
		sfnError20Trap, 
		sfnError21Trap, 
		sfnError22Trap, 
		sfnError23Trap, 
		sfnError24Trap, 
		sfnError25Trap, 
		sfnError26Trap, 
		sfnError27Trap, 
		sfnError28Trap, 
		sfnError29Trap, 
		sfnError30Trap,
		tsError1Trap, 
		tsError2Trap, 
		tsError3Trap, 
		tsError4Trap, 
		tsError5Trap, 
		tsError6Trap, 
		tsError7Trap, 
		tsError8Trap, 
		tsError9Trap, 
		tsError10Trap, 
		tsError11Trap, 
		tsError12Trap, 
		tsError13Trap, 
		tsError14Trap, 
		tsError15Trap, 
		tsError16Trap, 
		tsError17Trap, 
		tsError18Trap, 
		tsError19Trap, 
		tsError20Trap, 
		tsError21Trap, 
		tsError22Trap, 
		tsError23Trap, 
		tsError24Trap, 
		tsError25Trap, 
		tsError26Trap, 
		tsError27Trap, 
		tsError28Trap, 
		tsError29Trap, 
		tsError30Trap,
		t2miError1Trap, 
		t2miError2Trap, 
		t2miError3Trap, 
		t2miError4Trap, 
		t2miError5Trap, 
		t2miError6Trap, 
		t2miError7Trap, 
		t2miError8Trap, 
		t2miError9Trap, 
		t2miError10Trap, 
		t2miError11Trap, 
		t2miError12Trap, 
		t2miError13Trap, 
		t2miError14Trap, 
		t2miError15Trap, 
		t2miError16Trap, 
		t2miError17Trap, 
		t2miError18Trap, 
		t2miError19Trap, 
		t2miError20Trap, 
		t2miError21Trap, 
		t2miError22Trap, 
		t2miError23Trap, 
		t2miError24Trap, 
		t2miError25Trap, 
		t2miError26Trap, 
		t2miError27Trap, 
		t2miError28Trap, 
		t2miError29Trap, 
		t2miError30Trap,
		dvbs2AsiFaultTrap, 
		dvbs2AsiWarningTrap, 
		dvbs2AsiInputUnlock1Trap, 
		dvbs2AsiInputUnlock2Trap,
		ip2AsiFaultTrap,
		ip2AsiMinorTrap,
		ip2AsiTemperatureTrap,
		ip2AsiHwTrap,
		ip2AsiCommunicationTrap,
		ip2AsiSocketIp01Trap,
		ip2AsiAsiOutput01Trap,
		ip2AsiSocketIp02Trap,
		ip2AsiAsiOutput02Trap,
		ip2AsiSocketIp03Trap,
		ip2AsiAsiOutput03Trap,
		ip2AsiSocketIp04Trap,
		ip2AsiAsiOutput04Trap,
		ip2AsiSocketIp05Trap,
		ip2AsiAsiOutput05Trap,
		ip2AsiSocketIp06Trap,
		ip2AsiAsiOutput06Trap,
		ip2AsiSocketIp07Trap,
		ip2AsiAsiOutput07Trap
	}
	STATUS     current
	DESCRIPTION 
		"Contains all traps/notifications from the MIB."
	::= { objectGroups 4 }

groupGPS  OBJECT-GROUP
	OBJECTS { gps1IdSatellite, 
		gps1LockedSatellite, 
		gps1SnrSatellite, 
		gps2IdSatellite, 
		gps2LockedSatellite, 
		gps2SnrSatellite, 
		gpsAltitude, 
		gpsAntennaAlarm, 
		gpsAntennaEnableAlarm, 
		gpsAntennaEnableTrap, 
		gpsCommunicationAlarm, 
		gpsCommunicationEnableTrap, 
		gpsMajorAlarm, 
		gpsCtrlAddress, 
		gpsCtrlAddressAlarm, 
		gpsCtrlAddressEnableAlarm, 
		gpsCtrlAddressEnableTrap, 
		gpsGMTdate, 
		gpsHardware, 
		gpsHoldoverDrift, 
		gpsLatitude, 
		gpsLongitude, 
		gpsMinorAlarm, 
		gpsHoldoverAlarm, 
		gpsHoldoverEnableAlarm, 
		gpsSatellites, 
		gpsFirmware, 
		gpsHoldoverEnableTrap, 
		gpsSplitterActivedOutput, 
		gpsSplitterCommunicationAlarm, 
		gpsSplitterCtrlAddress, 
		gpsSplitterGPS1Status, 
		gpsSplitterGPS2Status, 
		gpsState, 
		gpsSyncAlarm, 
		gpsSyncEnableAlarm, 
		gpsSyncEnableTrap }
	STATUS     current
	DESCRIPTION 
		"Contains all the objects from GPS module branch of the MIB"
	::= { objectGroups 5 }

groupUCA  OBJECT-GROUP
	OBJECTS { ucaCommunicationAlarms, 
		ucaCtrlAddress, 
		ucaCtrlAddressAlarm, 
		ucaCtrlAddressEnableAlarm, 
		ucaMinorAlarm, 
		ucaMux1OnOffReset, 
		ucaMux2OnOffReset, 
		ucaMux3OnOffReset, 
		ucaPowerSuppliesAlarm, 
		ucaPowerSuppliesEnableAlarm, 
		ucaPowerSupply1Alarm, 
		ucaPowerSupply1EnableAlarm, 
		ucaPowerSupply2Alarm, 
		ucaHysteresis, 
		ucaFirmware, 
		ucaMajorAlarm, 
		ucaPowerSupply2EnableAlarm }
	STATUS     current
	DESCRIPTION 
		"Contains all the objects from UCA module branch of the MIB"
	::= { objectGroups 6 }

groupMUX  OBJECT-GROUP
	OBJECTS { asi2ErrorAlarm, 
		asi2EnableAlarm, 
		asi2EnableTrap, 
		mpeg1ErrorAlarm, 
		mpeg1EnableAlarm, 
		mpeg1EnableTrap, 
		sfnErrorAlarm, 
		sfnErrorEnableAlarm, 
		sfnErrorEnableTrap, 
		mpeg2ErrorAlarm, 
		mpeg2EnableAlarm, 
		mpeg2EnableTrap, 
		tsErrorAlarm, 
		tsEnableAlarm, 
		tsEnableTrap, 
		t2miErrorAlarm, 
		t2miEnableAlarm, 
		t2miEnableTrap, 
		asi1Status, 
		asi2Status, 
		asi1ErrorAlarm, 
		asi1ErrorEnableAlarm, 
		gps10MHzAlarm, 
		asi1ErrorEnableTrap, 
		cBerAlarm, 
		echoAdaptationFactor, 
		echoMG, 
		gps10MHzEnableAlarm, 
		muxTCellIdValue, 
		muxConfigurationDescription, 
		gps10MHzEnableTrap, 
		iFDVBTSignalAlarm, 
		iFDVBTSignalEnableAlarm, 
		muxAsiInput, 
		muxTCellIdEnable, 
		muxCtrlAddress, 
		muxChannelIn, 
		moduleCommunitacionAlarm, 
		mipErrorAlarm, 
		mipErrorEnableAlarm, 
		muxChannelOut, 
		iFDVBTSignalEnableTrap, 
		muxAlarmsRowIndex, 
		muxCBerEnableAlarm, 
		muxConfigurationRowIndex, 
		muxCtrlAddressAlarm, 
		muxCtrlAddressVersion, 
		muxFreqIn, 
		muxFreqOut, 
		mipErrorEnableTrap, 
		muxTNetworkMode, 
		muxAutoMIP, 
		muxCBerEnableTrap, 
		muxFFTSize, 
		muxGuardInterval, 
		muxBW, 
		muxConstellation, 
		muxFEC, 
		muxUserLocalDelay, 
		muxMutes, 
		muxVcorr1, 
		muxCBERwarningLevel, 
		muxCBERcriticalLevel, 
		muxMeasurementDescription, 
		muxChannel, 
		muxChannelBER, 
		muxCtrlAddressEnableAlarm, 
		muxCtrlAddressEnableTrap, 
		muxCtrlAddressMeasurerement, 
		muxDeecWindow1Position, 
		muxDeecWindow1Speed, 
		muxDeecWindow1Stat, 
		muxDeecWindow2Position, 
		muxDeecWindow2Speed, 
		muxDeecWindow3Position, 
		muxDeecWindow3Speed, 
		muxEchoCancelerOn, 
		muxEnableTrapRowAlarm, 
		muxFan1ServiceTime, 
		muxTransmittedPower, 
		muxReflectedPower, 
		muxTemperature, 
		muxIdT1, 
		muxIdT2, 
		muxNetworkMaxDelay, 
		muxLocalMarginDelay, 
		muxDeecWindow3Stat, 
		muxEnableTrapRowIndex, 
		muxMajorAlarm, 
		muxMeasurementRowIndex, 
		muxMicrocontrollerVersion, 
		muxMicrocontrollerAmpVersion, 
		muxFPGAVersion, 
		muxMinorAlarm, 
		muxRfMute, 
		muxRFoutAlarm, 
		muxRFoutEnableAlarm, 
		muxRFoutEnableTrap, 
		muxRFoutVersion, 
		muxUmbralTemp, 
		muxVBERcriticalLevel, 
		muxVBerEnableAlarm, 
		muxVBerEnableTrap, 
		muxVBERwarningLevel, 
		muxVersionRowIndex, 
		muxViterbiBER, 
		noInputSignalEnableAlarm, 
		transmittedPower6dBEnableTrap, 
		trtCurrentsOutRangeEnableTrap, 
		reflectedPowerEnableTrap, 
		unLockTSEnableTrap, 
		noInputSignalAlarm, 
		noInputSignalEnableTrap, 
		ppsEnableTrap, 
		ppsAlarm, 
		ppsEnableAlarm, 
		reflectedPowerEnableAlarm, 
		temperatureAlarm, 
		temperatureEnableAlarm, 
		temperatureEnableTrap, 
		transmittedPower3dBEnableAlarm, 
		transmittedPower6dBAlarm, 
		transmittedPower6dBEnableAlarm, 
		trtCurrentsOutRangeAlarm, 
		reflectedPowerAlarm, 
		trtCurrentsOutRangeEnableAlarm, 
		unLockTSAlarm, 
		transmittedPower3dBAlarm, 
		transmittedPower3dBEnableTrap, 
		unLockTSEnableAlarm, 
		vBerAlarm,
		muxT2FramePAPR, 
		muxT2FramePreamb, 
		muxT2FrameT2Frames, 
		muxT2idCellID, 
		muxT2idT2SystemID, 
		muxT2Pid, 
		muxT2TTTx,
		muxT2Latency,
		muxT2plpId, 
		muxT2plpOk, 
		muxT2UserLocalDelay, 
		muxT2plpChannelOut, 
		muxT2plpType, 
		muxT2plpConstellation, 
		muxT2plpDescription, 
		muxT2plpGroupID, 
		muxT2plpIbSignal, 
		muxT2plpnBlocks, 
		muxT2plpRowIndex, 
		muxT2plpTiType, 
		muxT2plpTypePlp, 
		muxT2SystemCtrlAddress, 
		muxT2SystenRowIndex, 
		muxTcfgPPSedge, 
		muxTtxId, 
		muxUnitType,
		muxReflectedPowerthreshold,
		muxExtendedDeecMode,
		muxT2cfgBW, 
		muxT2cfgNetworkMode, 
		muxT2cfgPPSedge, 
		muxT2cfgSource, 
		muxT2cfgVersion, 
		muxT2FrameChannelOut, 
		muxT2FrameType, 
		muxT2FrameCtrlAddress, 
		muxT2FrameDataSymbol, 
		muxT2Perfil, 
		muxT2Group, 
		muxT2UserGroup, 
		muxT2FrameDescription, 
		muxT2FrameExtCarr, 
		muxT2FrameFFT, 
		muxT2FrameGuardInterval, 
		muxT2FrameL1Mode, 
		muxT2FramePilotPattern, 
		muxT2FrameRowIndex, 
		muxT2frequency, 
		muxT2idNetworkID, 
		muxT2idTxID, 
		muxT2plpCodeRate, 
		muxT2plpCtrlAddress, 
		muxT2plpFECtype, 
		muxT2plpMode, 
		muxT2plpRotCon, 
		muxT2plpTiLength, 
		muxT2SystemChannelOut, 
		muxT2SystemType, 
		muxT2SystemDescription, 
		muxConfigurationType, 
		muxUmbralTempFPGA, 
		muxMeasurementType, 
		muxTemperatureFpga, 
		muxTimeOffset,
		muxInputLevel,
		muxSelectedAsi,
		muxSeamlessStatus,
		muxVersionType }
	STATUS     current
	DESCRIPTION 
		"Contains all the objects from MUX module branch of the MIB"
	::= { objectGroups 7 }

groupContacts  OBJECT-GROUP
	OBJECTS { contactsInputAction, 
		contactsInputDescription, 
		contactsInputPulse, 
		contactsInputSimulate, 
		contactsInputState, 
		contactsOutputDescription, 
		contactsOutputDuration, 
		contactsOutputRest, 
		contactsOutputState, 
		contactsFirmware }
	STATUS     current
	DESCRIPTION 
		"Contains all the objects from contacts (relays) module branch of the MIB"
	::= { objectGroups 8 }

groupUcan  OBJECT-GROUP
	OBJECTS { ucanManual, 
		ucanAutoOff, 
		ucanAutoReturn, 
		ucanCAntenna, 
		ucanCAutoOff, 
		ucanCControlAddress, 
		ucanCInputSignalTest, 
		ucanCLocal, 
		ucanCManual, 
		ucanCommunication, 
		ucanCompactAlarmAddress, 
		ucanCompactAlarmAlimentationFault, 
		ucanCompactAlarmFault, 
		ucanCompactAlarmHW, 
		ucanCompactAlarmWarning, 
		ucanCompactRelay1Mux, 
		ucanCompactRelay1Priority, 
		ucanCompactRelay1MuteMux, 
		ucanCompactRelay2Mux, 
		ucanCompactRelay2Priority,
		ucanCompactRelay2MuteMux,  
		ucanCompactRelay3Mux, 
		ucanCompactRelay3Priority,
		ucanCompactRelay3MuteMux,  
		ucanCompactRelay4Mux, 
		ucanCompactRelay4Priority,
		ucanCompactRelay4MuteMux,  
		ucanCompactRelay5Mux, 
		ucanCompactRelay5Priority,
		ucanCompactRelay5MuteMux,  
		ucanCompactRelay6Mux, 
		ucanCompactRelay6Priority,
		ucanCompactRelay6MuteMux,  
		ucanCompactRelayReserve, 
		ucanCompactRelaysMuxCAddress, 
		ucanCompactRelaysPriorityAddress, 
		ucanCompactMuteMuxAddress, 
		ucanComunicationAlarm, 
		ucanCPriorities, 
		ucanCRestoration, 
		ucanCRestorationPerDay, 
		ucanCSwitchedMux, 
		ucanCTestingMux, 
		ucanCVerificationC, 
		ucanCVerification, 
		ucanCVerificationA, 
		ucanCVerificationAInterval, 
		ucanCVerificationATime, 
		ucanCVerificationB, 
		ucanCVerificationBTime, 
		ucanCVerificationDuration, 
		ucanCVerificationRetries, 
		ucanFirmware, 
		ucanGeneralAlarm, 
		ucanHysteresis, 
		ucanInputTest, 
		ucanPrioritiesMuxAddress, 
		ucanPrioritiesMuxValue, 
		ucanNoPriority, 
		ucanReceiver, 
		ucanLocal, 
		ucanReservationAlarm, 
		ucanReserve, 
		ucanStateCommutationMuxAddress, 
		ucanStateCommutationValue, 
		ucanReset, 
		ucanStateTestMuxAddress, 
		ucanStateTestValue, 
		ucanSwitchedMux, 
		ucanTestingMux }
	STATUS     current
	DESCRIPTION 
		"Contains all the objects from UCA n+1 module branch of the MIB"
	::= { objectGroups 9 }

groupUca1  OBJECT-GROUP
	OBJECTS { uca1AlarmsRowIndex, 
		uca1Antenna, 
		uca1BlockedA, 
		uca1BlockedB, 
		uca1ConmutationError, 
		uca1CtrlAddress, 
		uca1CtrlAddressAlarm, 
		uca1Firmware, 
		uca1IncorrectConfiguration, 
		uca1Mode, 
		uca1MuxA, 
		uca1MuxAsiErrorAlarm, 
		uca1MuxB, 
		uca1MuxCBerAlarm, 
		uca1MuxConmutationRowIndex, 
		uca1CtrlAddressConmutationAlarm, 
		uca1MuxGps10MHzAlarm, 
		uca1MuxIFDVBTSignalAlarm, 
		uca1MuxMipErrorAlarm, 
		uca1MuxModuleCommunitacionAlarm, 
		uca1MuxNoInputSignalAlarm, 
		uca1MuxPowerAmplifierCommunAlarm, 
		uca1MuxPpsAlarm, 
		uca1MuxReflectedPowerAlarm, 
		uca1MuxTemperatureAlarm, 
		uca1MuxTransmittedPowerAlarm, 
		uca1MuxTrtCurrentsOutRangeAlarm, 
		uca1MuxUnLockTSAlarm, 
		uca1MuxVBerAlarm, 
		uca1NoMute, 
		uca1Preferential, 
		uca1Ready, 
		uca1RowIndex, 
		uca1TestDuration, 
		uca1UndeterminatedRelay }
	STATUS     current
	DESCRIPTION 
		"Contains all the objects from UCA 1+1 module branch of the MIB"
	::= { objectGroups 10 }

groupObsolete  OBJECT-GROUP
	OBJECTS { contactsCtrlAddress, 
		fanAlarm, 
		fanEnableAlarm, 
		fanEnableTrap, 
		muxFan2ServiceTime, 
		muxFan3ServiceTime, 
		powerAmplifierCommunicatAlarm, 
		powerAmplifierCommunicatEnAlarm, 
		powerAmplifierCommunicatEnTrap }
	STATUS     obsolete
	DESCRIPTION 
		"objectGroups"
	::= { objectGroups 11 }

groupIP2ASI  OBJECT-GROUP
	OBJECTS { ip2AsiAsiMode, 
		ip2AsiAsiOutput01Alarm, 
		ip2AsiAsiOutput01EnableA, 
		ip2AsiAsiOutput01EnableT, 
		ip2AsiAsiOutput02Alarm, 
		ip2AsiAsiOutput02EnableA, 
		ip2AsiAsiOutput02EnableT, 
		ip2AsiAsiOutput03Alarm, 
		ip2AsiAsiOutput03EnableA, 
		ip2AsiAsiOutput03EnableT, 
		ip2AsiAsiOutput04Alarm, 
		ip2AsiAsiOutput04EnableA, 
		ip2AsiAsiOutput04EnableT, 
		ip2AsiAsiOutput05Alarm, 
		ip2AsiAsiOutput05EnableA, 
		ip2AsiAsiOutput05EnableT, 
		ip2AsiAsiOutput06Alarm, 
		ip2AsiAsiOutput06EnableA, 
		ip2AsiAsiOutput06EnableT, 
		ip2AsiAsiOutput07Alarm, 
		ip2AsiAsiOutput07EnableA, 
		ip2AsiAsiOutput07EnableT, 
		ip2AsiAsiRate, 
		ip2AsiCommunicationAlarm, 
		ip2AsiCommunicationEnableA, 
		ip2AsiCommunicationEnableT, 
		ip2AsiCtrlAddressAlarm, 
		ip2AsiCtrlAddressEnableA, 
		ip2AsiCtrlAddressEnableT, 
		ip2AsiGeralIgmpV, 
		ip2AsiGeralVlanId, 
		ip2AsiGeralAddress, 
		ip2AsiGeralDhcp, 
		ip2AsiGeralGateway, 
		ip2AsiGeralInput1State, 
		ip2AsiGeralInput2State, 
		ip2AsiGeralIp, 
		ip2AsiGeralMAC, 
		ip2AsiGeralNetmask, 
		ip2AsiGeralSerialNumber, 
		ip2AsiGeralTemperature, 
		ip2AsiGeralVersion, 
		ip2AsiGeralVlan, 
		ip2AsiHwAlarm, 
		ip2AsiHwEnableA, 
		ip2AsiHwEnableT, 
		ip2AsiInput, 
		ip2AsiInputLatency, 
		ip2AsiInputState, 
		ip2AsiIpSrc, 
		ip2AsiOutputState, 
		ip2AsiInputPort, 
		ip2AsiIOAddress, 
		ip2AsiIOInOut, 
		ip2AsiIpMulticast, 
		ip2AsiMajorAlarm, 
		ip2AsiMajorEnableA, 
		ip2AsiMajorEnableT, 
		ip2AsiMinorAlarm, 
		ip2AsiMinorEnableA, 
		ip2AsiMinorEnableT, 
		ip2AsiMulticast, 
		ip2AsiOutputAsi, 
		ip2AsiProtocol, 
		ip2AsiSocketIp, 
		ip2AsiSocketIp01Alarm, 
		ip2AsiSocketIp01EnableA, 
		ip2AsiSocketIp01EnableT, 
		ip2AsiSocketIp02Alarm, 
		ip2AsiSocketIp02EnableA, 
		ip2AsiSocketIp02EnableT, 
		ip2AsiSocketIp03Alarm, 
		ip2AsiSocketIp03EnableA, 
		ip2AsiSocketIp03EnableT, 
		ip2AsiSocketIp04Alarm, 
		ip2AsiSocketIp04EnableA, 
		ip2AsiSocketIp04EnableT, 
		ip2AsiSocketIp05Alarm, 
		ip2AsiSocketIp05EnableA, 
		ip2AsiSocketIp05EnableT, 
		ip2AsiSocketIp06Alarm, 
		ip2AsiSocketIp06EnableA, 
		ip2AsiSocketIp06EnableT, 
		ip2AsiSocketIp07Alarm, 
		ip2AsiSocketIp07EnableA, 
		ip2AsiSocketIp07EnableT, 
		ip2AsiTemperatureAlarm, 
		ip2AsiTemperatureEnableA, 
		ip2AsiTemperatureEnableT }
	STATUS     current
	DESCRIPTION 
		"Contains all the objects from IP/ASI module branch of the MIB"
	::= { objectGroups 16 }

groupDeprecated  OBJECT-GROUP
	OBJECTS { contactsHysteresis, 
		gpsHysteresis, 
		gpsStatusAlarm, 
		gpsTrapsConfiguration, 
		muxAlarmStatus, 
		muxCommunicationEnableTrap, 
		communicationEnableAlarm, 
		muxEchoAdaptation, 
		muxHysteresis, 
		muxTrapsConfiguration, 
		muxVcorr2, 
		ntpServerVersion, 
		onOffAlarm, 
		ucaStatusAlarm, 
		ucaTrapsConfiguration }
	STATUS     deprecated
	DESCRIPTION 
		"groupDeprecated"
	::= { objectGroups 12 }

groupDeprecatedTraps  NOTIFICATION-GROUP
	NOTIFICATIONS { generalAlarmTrap, 
		localTrap, 
		manualTrap, 
		noPriorityTrap, 
		reservationModuleTrap, 
		ucanCommunicationTrap,
		alternativeAsi10Trap, 
		alternativeAsi11Trap, 
		alternativeAsi12Trap, 
		alternativeAsi13Trap, 
		alternativeAsi14Trap, 
		alternativeAsi15Trap, 
		alternativeAsi1Trap, 
		alternativeAsi2Trap, 
		alternativeAsi3Trap, 
		alternativeAsi4Trap, 
		alternativeAsi5Trap, 
		alternativeAsi6Trap, 
		alternativeAsi7Trap, 
		alternativeAsi8Trap, 
		alternativeAsi9Trap, 
		alternativeAsi25Trap, 
		alternativeAsi26Trap, 
		alternativeAsi27Trap, 
		alternativeAsi28Trap, 
		alternativeAsi29Trap, 
		alternativeAsi30Trap, 
		alternativeAsi16Trap, 
		alternativeAsi17Trap, 
		alternativeAsi18Trap, 
		alternativeAsi19Trap, 
		alternativeAsi20Trap, 
		alternativeAsi21Trap, 
		alternativeAsi22Trap, 
		alternativeAsi23Trap, 
		alternativeAsi24Trap }
	STATUS     deprecated
	DESCRIPTION 
		"groupDeprecatedTraps"
	::= { objectGroups 13 }

groupDvbs2Asi  OBJECT-GROUP
	OBJECTS { dvbs2AsiEnableTrapCtrlAddress, 
		dvbs2AsiEnableTrapFault, 
		dvbs2AsiEnableTrapTemperature, 
		dvbs2AsiEnableTrapInputQuality1, 
		dvbs2AsiEnableTrapInputQuality2, 
		dvbs2AsiEnableTrapInputQuality3, 
		dvbs2AsiEnableTrapInputQuality4, 
		dvbs2AsiEnableTrapInputUnlock1, 
		dvbs2AsiEnableTrapInputUnlock2, 
		dvbs2AsiEnableTrapInputUnlock3, 
		dvbs2AsiEnableTrapInputUnlock4, 
		dvbs2AsiEnableTrapLnb1, 
		dvbs2AsiEnableTrapLnb2, 
		dvbs2AsiEnableTrapLnb3, 
		dvbs2AsiEnableTrapLnb4, 
		dvbs2AsiEnableTrapMinor, 
		dvbs2AsiEnableTrapOutputAsi1, 
		dvbs2AsiEnableTrapOutputAsi2, 
		dvbs2AsiEnableTrapOutputAsi3, 
		dvbs2AsiEnableTrapOutputAsi4, 
		dvbs2AsiEnableTrapOutputAsi5, 
		dvbs2AsiEnableTrapOutputAsi6, 
		dvbs2AsiEnableTrapOutputAsi7, 
		dvbs2AsiAlarmsCtrlAddress, 
		dvbs2AsiAlarmsFault, 
		dvbs2AsiAlarmsHw, 
		dvbs2AsiAlarmsTemperature, 
		dvbs2AsiAlarmsInputQuality1, 
		dvbs2AsiAlarmsInputQuality2, 
		dvbs2AsiAlarmsInputQuality3, 
		dvbs2AsiAlarmsInputQuality4, 
		dvbs2AsiAlarmsInputUnlock1, 
		dvbs2AsiAlarmsInputUnlock2, 
		dvbs2AsiAlarmsInputUnlock3, 
		dvbs2AsiAlarmsInputUnlock4, 
		dvbs2AsiAlarmsLnb1, 
		dvbs2AsiAlarmsLnb2, 
		dvbs2AsiAlarmsLnb3, 
		dvbs2AsiAlarmsLnb4, 
		dvbs2AsiAlarmsMinor, 
		dvbs2AsiAlarmsOutputAsi1, 
		dvbs2AsiAlarmsOutputAsi2, 
		dvbs2AsiAlarmsOutputAsi3, 
		dvbs2AsiAlarmsOutputAsi4, 
		dvbs2AsiAlarmsOutputAsi5, 
		dvbs2AsiAlarmsOutputAsi6, 
		dvbs2AsiAlarmsOutputAsi7, 
		dvbs2AsiControlCtrlAddress, 
		dvbs2AsiControlHysteresis, 
		dvbs2AsiControlSerialNumber, 
		dvbs2AsiControlTemperature, 
		dvbs2AsiControlVersion, 
		dvbs2AsiEnableAlarmsCtrlAddress, 
		dvbs2AsiEnableAlarmsFault, 
		dvbs2AsiEnableAlarmsHw, 
		dvbs2AsiEnableAlarmsTemperature, 
		dvbs2AsiEnableAlarmsInputQualit1, 
		dvbs2AsiEnableAlarmsInputQualit2, 
		dvbs2AsiEnableAlarmsInputQualit3, 
		dvbs2AsiEnableAlarmsInputQualit4, 
		dvbs2AsiEnableAlarmsInputUnlock1, 
		dvbs2AsiEnableAlarmsInputUnlock2, 
		dvbs2AsiEnableAlarmsInputUnlock3, 
		dvbs2AsiEnableAlarmsInputUnlock4, 
		dvbs2AsiEnableAlarmsLnb1, 
		dvbs2AsiEnableAlarmsLnb2, 
		dvbs2AsiEnableAlarmsLnb3, 
		dvbs2AsiEnableAlarmsLnb4, 
		dvbs2AsiEnableAlarmsMinor, 
		dvbs2AsiEnableAlarmsOutputAsi1, 
		dvbs2AsiEnableAlarmsOutputAsi2, 
		dvbs2AsiEnableAlarmsOutputAsi3, 
		dvbs2AsiEnableAlarmsOutputAsi4, 
		dvbs2AsiEnableAlarmsOutputAsi5, 
		dvbs2AsiEnableAlarmsOutputAsi6, 
		dvbs2AsiEnableAlarmsOutputAsi7, 
		dvbs2AsiEnableTrapHw, 
		inputRf, 
		inputRfBandFreq, 
		inputRfBandFreqLH, 
		inputRfCtrlAddress, 
		inputRfFrequency, 
		inputRfLnb, 
		inputRfLnbDual, 
		inputRfLnbHighFreq, 
		inputRfLnbLowFreq, 
		inputRfMode, 
		inputRfPls, 
		inputRfPolarization, 
		inputRfSatellite, 
		inputRfState, 
		inputRfSymbolRate, 
		inputRfSymbolRateAuto, 
		inputRfSymbolRateCurrent,
		inputRfIqModeCurrent,
		inputRfStandard,
		inputRfIsis,
		inputRfRollOff,
		inputRfPilot,
		inputRfFrameLength,
		inputRfModulation,
		inputRfFec,
		inputRfCber,
		inputRfVber,
		inputRfCn,
		inputRfLinkMargin,
		inputRfPower,
		outputAsiBitrate, 
		outputAsiCtrlAddress, 
		outputAsiIsi, 
		outputAsiMode, 
		outputAsiRfInput, 
		outputAsiState, 
		redundanceInput, 
		redundanceRfCtrlAddress }
	STATUS     current
	DESCRIPTION 
		"Contains all the objects from DVB-S2/ASI module branch of the MIB"
	::= { objectGroups 14 }

dvbtBroadcastBasicCompilance  MODULE-COMPLIANCE
	STATUS     current
	DESCRIPTION 
		"The compliance statement for dvbtBroadcastTredessMIB entities which
		            implement the dvbtBroadcast-TRedess MIB."
	MODULE
		MANDATORY-GROUPS { groupAdmin,
				groupAlarmsTraps,
				groupAlarmTrapTable,
				groupContacts,
				groupGPS,
				groupMUX,
				groupSystem,
				groupUCA,
				groupUcan,
				groupUca1,
				groupDvbs2Asi,
				groupIP2ASI } 
	::= { groupCompilance 1 }

dvbtDeprecatedBasicCompilance  MODULE-COMPLIANCE
	STATUS     deprecated
	DESCRIPTION 
		"The compliance statement for dvbtBroadcastTredessMIB entities which
		implement the dvbtBroadcast-TRedess MIB.
		Deprecated!"
	MODULE
		MANDATORY-GROUPS { groupDeprecated,
						groupDeprecatedTraps } 
	::= { groupCompilance 2 }
END
