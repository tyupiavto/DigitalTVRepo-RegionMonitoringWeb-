ENC1 DEFINITIONS ::= BEGIN

IMPORTS
    OBJECT-IDENTITY, OBJECT-TYPE, MODULE-IDENTITY,
    NOTIFICATION-TYPE,
    Integer32
        FROM SNMPv2-SMI
    MODULE-COMPLIANCE, OBJECT-GROUP
        FROM SNMPv2-CONF
    TEXTUAL-CONVENTION, DisplayString
        FROM SNMPv2-TC
    ccsp, subdeviceId, frameId, slotId, tableIdx,
    AlarmEnabled, AlarmAcknowledged
        FROM InfrastructureNetwork
    ;

enc1 MODULE-IDENTITY
    LAST-UPDATED "201410310702Z"

    ORGANIZATION
        "Harris Canada Systems, Inc.
        25 Dyas Road,
        North York, Ontario
        M3B 1V7, Canada"
    CONTACT-INFO
        "BCDService@harris.com"
    DESCRIPTION
        "MIB for product"
    REVISION "201410310702Z"
    DESCRIPTION
        "Harris Selenio Encoder"
::= { ccsp 21 6 }

enc1Params     OBJECT IDENTIFIER ::= { enc1 1 }
enc1Alarms     OBJECT IDENTIFIER ::= { enc1 2 }
enc1DeviceInfo OBJECT IDENTIFIER ::= { enc1 3 }

-- Enumeration Definitions
Enc1E0enumObj ::= TEXTUAL-CONVENTION
    STATUS current
    DESCRIPTION
    "EnumObj"
    SYNTAX INTEGER {
        v0-disable                    (0),    -- 'Disable'
        v1-enable                     (1)     -- 'Enable'
    }

Enc1E1enumObj ::= TEXTUAL-CONVENTION
    STATUS current
    DESCRIPTION
    "EnumObj"
    SYNTAX INTEGER {
        v0-off                        (0),    -- 'Off'
        v1-on                         (1)     -- 'On'
    }

Enc1E2enumObj ::= TEXTUAL-CONVENTION
    STATUS current
    DESCRIPTION
    "EnumObj"
    SYNTAX INTEGER {
        v0-off                        (0),    -- 'Off'
        v1-on                         (1),    -- 'On'
        v2-auto                       (2)     -- 'Auto'
    }

Enc1E3enumObj ::= TEXTUAL-CONVENTION
    STATUS current
    DESCRIPTION
    "EnumObj"
    SYNTAX INTEGER {
        v0-fault                      (0),    -- 'Fault'
        v1-warning                    (1),    -- 'Warning'
        v2-good                       (2)     -- 'Good'
    }

Enc1E4enumObj ::= TEXTUAL-CONVENTION
    STATUS current
    DESCRIPTION
    "EnumObj"
    SYNTAX INTEGER {
        v0-red                        (0),    -- 'Red'
        v1-green                      (1)     -- 'Green'
    }

Enc1E5enumObj ::= TEXTUAL-CONVENTION
    STATUS current
    DESCRIPTION
    "EnumObj"
    SYNTAX INTEGER {
        v0-noFault                    (0),    -- 'No Fault'
        v1-fault                      (1),    -- 'Fault'
        v2-unknown                    (2)     -- 'Unknown'
    }

Enc1E6enumObj ::= TEXTUAL-CONVENTION
    STATUS current
    DESCRIPTION
    "EnumObj"
    SYNTAX INTEGER {
        v0-noFault                    (0),    -- 'No Fault'
        v1-fault                      (1),    -- 'Fault'
        v2-unknown                    (2)     -- 'Unknown'
    }

Enc1E7enumObj ::= TEXTUAL-CONVENTION
    STATUS current
    DESCRIPTION
    "EnumObj"
    SYNTAX INTEGER {
        v0-ntsc                       (0),    -- 'NTSC'
        v1-pal                        (1),    -- 'PAL'
        v2-unknown                    (2)     -- 'Unknown'
    }

Enc1E8enumObj ::= TEXTUAL-CONVENTION
    STATUS current
    DESCRIPTION
    "EnumObj"
    SYNTAX INTEGER {
        v0-asi-188                    (0),    -- 'ASI-188'
        v1-asi-204                    (1),    -- 'ASI-204'
        v2-sdi-NTSC                   (2),    -- 'SDI-NTSC'
        v3-sdi-PAL                    (3),    -- 'SDI-PAL'
        v4-unknown                    (4)     -- 'Unknown'
    }

Enc1E9enumObj ::= TEXTUAL-CONVENTION
    STATUS current
    DESCRIPTION
    "EnumObj"
    SYNTAX INTEGER {
        v0-notPresent                 (0),    -- 'Not Present'
        v1-present                    (1),    -- 'Present'
        v2-na                         (2)     -- 'NA'
    }

Enc1E10enumObj ::= TEXTUAL-CONVENTION
    STATUS current
    DESCRIPTION
    "EnumObj"
    SYNTAX INTEGER {
        v0-locked                     (0),    -- 'Locked'
        v1-notLocked                  (1)     -- 'Not Locked'
    }

Enc1E11enumObj ::= TEXTUAL-CONVENTION
    STATUS current
    DESCRIPTION
    "EnumObj"
    SYNTAX INTEGER {
        v0-no                         (0),    -- 'No'
        v1-yes                        (1)     -- 'Yes'
    }

Enc1E12enumObj ::= TEXTUAL-CONVENTION
    STATUS current
    DESCRIPTION
    "EnumObj"
    SYNTAX INTEGER {
        v0-contribution               (0),    -- 'Contribution'
        v1-distribution               (1),    -- 'Distribution'
        v2-adaptiveBitRate            (2)     -- 'Adaptive Bit Rate'
    }

Enc1E13enumObj ::= TEXTUAL-CONVENTION
    STATUS current
    DESCRIPTION
    "EnumObj"
    SYNTAX INTEGER {
        v0-frame-auto                 (0),    -- 'Frame-auto'
        v1-frame-5                    (1),    -- 'Frame-5'
        v2-frame-10                   (2),    -- 'Frame-10'
        v3-frame-15                   (3),    -- 'Frame-15'
        v4-frame-25                   (4),    -- 'Frame-25'
        v5-frame-30                   (5)     -- 'Frame-30'
    }

Enc1E14enumObj ::= TEXTUAL-CONVENTION
    STATUS current
    DESCRIPTION
    "EnumObj"
    SYNTAX INTEGER {
        v0-closed                     (0),    -- 'Closed'
        v1-open                       (1)     -- 'Open'
    }

Enc1E15enumObj ::= TEXTUAL-CONVENTION
    STATUS current
    DESCRIPTION
    "EnumObj"
    SYNTAX INTEGER {
        v0-disable                    (0),    -- 'disable'
        v1-audio1Metadata             (1),    -- 'Audio1 Metadata'
        v2-audio2Metadata             (2),    -- 'Audio2 Metadata'
        v3-audio3Metadata             (3),    -- 'Audio3 Metadata'
        v4-audio4Metadata             (4),    -- 'Audio4 Metadata'
        v5-audio5Metadata             (5),    -- 'Audio5 Metadata'
        v6-audio6Metadata             (6),    -- 'Audio6 Metadata'
        v7-audio7Metadata             (7),    -- 'Audio7 Metadata'
        v8-audio8Metadata             (8),    -- 'Audio8 Metadata'
        v9-programData1               (9),    -- 'Program Data1'
        v10-programData2              (10)     -- 'Program Data2'
    }

Enc1E16enumObj ::= TEXTUAL-CONVENTION
    STATUS current
    DESCRIPTION
    "EnumObj"
    SYNTAX INTEGER {
        v0-rs-232                     (0),    -- 'RS-232'
        v1-rs-422                     (1)     -- 'RS-422'
    }

Enc1E17enumObj ::= TEXTUAL-CONVENTION
    STATUS current
    DESCRIPTION
    "EnumObj"
    SYNTAX INTEGER {
        v0-9600                       (0),    -- '9600'
        v1-19200                      (1),    -- '19200'
        v2-38400                      (2),    -- '38400'
        v3-57600                      (3),    -- '57600'
        v4-115200                     (4)     -- '115200'
    }

Enc1E18enumObj ::= TEXTUAL-CONVENTION
    STATUS current
    DESCRIPTION
    "EnumObj"
    SYNTAX INTEGER {
        v0-primary                    (0),    -- 'Primary'
        v1-secondary                  (1),    -- 'Secondary'
        v2-unknown                    (2)     -- 'Unknown'
    }

Enc1E19enumObj ::= TEXTUAL-CONVENTION
    STATUS current
    DESCRIPTION
    "EnumObj"
    SYNTAX INTEGER {
        v0-none                       (0),    -- 'None'
        v1-alm-Close                  (1),    -- 'Alm-Close'
        v2-alm-Cpen                   (2),    -- 'Alm-Cpen'
        v3-splice                     (3),    -- 'Splice'
        v4-customGPIScript            (4)     -- 'Custom GPI Script'
    }

Enc1E20enumObj ::= TEXTUAL-CONVENTION
    STATUS current
    DESCRIPTION
    "EnumObj"
    SYNTAX INTEGER {
        v0-neg                        (0),    -- '-'
        v1-apply                      (1)     -- 'Apply'
    }

Enc1E21enumObj ::= TEXTUAL-CONVENTION
    STATUS current
    DESCRIPTION
    "EnumObj"
    SYNTAX INTEGER {
        v0-neg                        (0),    -- '-'
        v1-save                       (1)     -- 'Save'
    }

Enc1E22enumObj ::= TEXTUAL-CONVENTION
    STATUS current
    DESCRIPTION
    "EnumObj"
    SYNTAX INTEGER {
        v0-neg                        (0),    -- '-'
        v1-previous                   (1)     -- 'Previous'
    }

Enc1E23enumObj ::= TEXTUAL-CONVENTION
    STATUS current
    DESCRIPTION
    "EnumObj"
    SYNTAX INTEGER {
        v0-neg                        (0),    -- '-'
        v1-next                       (1)     -- 'Next'
    }

Enc1E24enumObj ::= TEXTUAL-CONVENTION
    STATUS current
    DESCRIPTION
    "EnumObj"
    SYNTAX INTEGER {
        v0-neg                        (0),    -- '-'
        v1-select                     (1)     -- 'Select'
    }

Enc1E25enumObj ::= TEXTUAL-CONVENTION
    STATUS current
    DESCRIPTION
    "EnumObj"
    SYNTAX INTEGER {
        v0-none                       (0),    -- 'None'
        v1-1                          (1),    -- '1'
        v2-2                          (2),    -- '2'
        v3-3                          (3),    -- '3'
        v4-4                          (4),    -- '4'
        v5-5                          (5),    -- '5'
        v6-6                          (6),    -- '6'
        v7-7                          (7),    -- '7'
        v8-8                          (8),    -- '8'
        v9-9                          (9),    -- '9'
        v10-10                        (10)     -- '10'
    }

Enc1E26enumObj ::= TEXTUAL-CONVENTION
    STATUS current
    DESCRIPTION
    "EnumObj"
    SYNTAX INTEGER {
        v0-disabled                   (0),    -- 'Disabled'
        v1-enabled                    (1)     -- 'Enabled'
    }

Enc1E27enumObj ::= TEXTUAL-CONVENTION
    STATUS current
    DESCRIPTION
    "EnumObj"
    SYNTAX INTEGER {
        v0-off                        (0),    -- 'Off'
        v1-on                         (1)     -- 'On'
    }

Enc1E28enumObj ::= TEXTUAL-CONVENTION
    STATUS current
    DESCRIPTION
    "EnumObj"
    SYNTAX INTEGER {
        v0-off                        (0),    -- 'Off'
        v1-on                         (1)     -- 'On'
    }

Enc1E29enumObj ::= TEXTUAL-CONVENTION
    STATUS current
    DESCRIPTION
    "EnumObj"
    SYNTAX INTEGER {
        v0-off                        (0),    -- 'Off'
        v1-on                         (1),    -- 'On'
        v2-statMux                    (2)     -- 'StatMux'
    }

Enc1E30enumObj ::= TEXTUAL-CONVENTION
    STATUS current
    DESCRIPTION
    "EnumObj"
    SYNTAX INTEGER {
        v0-auto                       (0),    -- 'Auto'
        v1-manual                     (1)     -- 'Manual'
    }

Enc1E31enumObj ::= TEXTUAL-CONVENTION
    STATUS current
    DESCRIPTION
    "EnumObj"
    SYNTAX INTEGER {
        v0-disable                    (0),    -- 'Disable'
        v1-auto                       (1),    -- 'Auto'
        v2-1                          (2),    -- '1'
        v3-2                          (3),    -- '2'
        v4-3                          (4),    -- '3'
        v5-4                          (5),    -- '4'
        v6-5                          (6),    -- '5'
        v7-6                          (7),    -- '6'
        v8-7                          (8),    -- '7'
        v9-8                          (9),    -- '8'
        v10-9                         (10),    -- '9'
        v11-10                        (11),    -- '10'
        v12-11                        (12),    -- '11'
        v13-12                        (13),    -- '12'
        v14-13                        (14)     -- '13'
    }

Enc1E32enumObj ::= TEXTUAL-CONVENTION
    STATUS current
    DESCRIPTION
    "EnumObj"
    SYNTAX INTEGER {
        v0-disable                    (0),    -- 'Disable'
        v1-auto                       (1),    -- 'Auto'
        v2-1                          (2),    -- '1'
        v3-2                          (3),    -- '2'
        v4-3                          (4),    -- '3'
        v5-4                          (5),    -- '4'
        v6-5                          (6),    -- '5'
        v7-6                          (7),    -- '6'
        v8-7                          (8),    -- '7'
        v9-8                          (9)     -- '8'
    }

Enc1E33enumObj ::= TEXTUAL-CONVENTION
    STATUS current
    DESCRIPTION
    "EnumObj"
    SYNTAX INTEGER {
        v0-black                      (0),    -- 'Black'
        v1-stop                       (1),    -- 'Stop'
        v2-still                      (2),    -- 'Still'
        v3-image                      (3)     -- 'Image'
    }

Enc1E34enumObj ::= TEXTUAL-CONVENTION
    STATUS current
    DESCRIPTION
    "EnumObj"
    SYNTAX INTEGER {
        v0-neg                        (0),    -- '-'
        v1-restore                    (1)     -- 'Restore'
    }

Enc1E35enumObj ::= TEXTUAL-CONVENTION
    STATUS current
    DESCRIPTION
    "EnumObj"
    SYNTAX INTEGER {
        v0-none                       (0),    -- 'None'
        v1-black                      (1),    -- 'Black'
        v2-extsdi1                    (2),    -- 'EXT SDI 1'
        v3-ctrsdi                     (3),    -- 'CTR SDI'
        v4-extsdi2                    (4)     -- 'EXT SDI 2'
    }

Enc1E36enumObj ::= TEXTUAL-CONVENTION
    STATUS current
    DESCRIPTION
    "EnumObj"
    SYNTAX INTEGER {
        v0-none                       (0),    -- 'None'
        v1-black                      (1),    -- 'Black'
        v2-extsdi1                    (2),    -- 'EXT SDI 1'
        v3-ctrsdi                     (3),    -- 'CTR SDI'
        v4-extsdi2                    (4)     -- 'EXT SDI 2'
    }

Enc1E37enumObj ::= TEXTUAL-CONVENTION
    STATUS current
    DESCRIPTION
    "EnumObj"
    SYNTAX INTEGER {
        v0-unknown                    (0),    -- 'Unknown'
        v1-electrical                 (1),    -- 'Electrical'
        v2-optical                    (2)     -- 'Optical'
    }

Enc1E38enumObj ::= TEXTUAL-CONVENTION
    STATUS current
    DESCRIPTION
    "EnumObj"
    SYNTAX INTEGER {
        v0-revertive                  (0),    -- 'Revertive'
        v1-non-Revertive              (1)     -- 'Non-Revertive'
    }

Enc1E39enumObj ::= TEXTUAL-CONVENTION
    STATUS current
    DESCRIPTION
    "EnumObj"
    SYNTAX INTEGER {
        v0-interlaced                 (0),    -- 'Interlaced'
        v1-progressive                (1)     -- 'Progressive'
    }

Enc1E40enumObj ::= TEXTUAL-CONVENTION
    STATUS current
    DESCRIPTION
    "EnumObj"
    SYNTAX INTEGER {
        v0-auto                       (0),    -- 'Auto'
        v1-525                        (1),    -- '525'
        v2-625                        (2),    -- '625'
        v3-720p23unsupported          (3),    -- '720p 23 unsupported'
        v4-720p24unsupported          (4),    -- '720p 24 unsupported'
        v5-720p25unsupported          (5),    -- '720p 25 unsupported'
        v6-720p29unsupported          (6),    -- '720p 29 unsupported'
        v7-720p30unsupported          (7),    -- '720p 30 unsupported'
        v8-720p50                     (8),    -- '720p 50'
        v9-720p5994                   (9),    -- '720p 59.94'
        v10-720p60unsupported         (10),    -- '720p 60 unsupported'
        v11-1035i25unsupported        (11),    -- '1035i 25 unsupported'
        v12-1035i29unsupported        (12),    -- '1035i 29 unsupported'
        v13-1035i30unsupported        (13),    -- '1035i 30 unsupported'
        v14-1080i50                   (14),    -- '1080i 50'
        v15-1080i5994                 (15),    -- '1080i 59.94'
        v16-1080i30unsupported        (16),    -- '1080i 30 unsupported'
        v17-1080p23unsupported        (17),    -- '1080p 23 unsupported'
        v18-1080p2398unsupported      (18),    -- '1080p 23.98 unsupported'
        v19-1080p24unsupported        (19),    -- '1080p 24 unsupported'
        v20-1080p24Aunsupported       (20),    -- '1080p 24_A unsupported'
        v21-1080p25unsupported        (21),    -- '1080p 25 unsupported'
        v22-1080p25295Munsupported    (22),    -- '1080p 25_295M unsupported'
        v23-1080p2997unsupported      (23),    -- '1080p 29.97 unsupported'
        v24-1080p30unsupported        (24),    -- '1080p 30 unsupported'
        v25-1080p50                   (25),    -- '1080p 50'
        v26-1080p5994                 (26)     -- '1080p 59.94'
    }

Enc1E41enumObj ::= TEXTUAL-CONVENTION
    STATUS current
    DESCRIPTION
    "EnumObj"
    SYNTAX INTEGER {
        v0-1920x1080                  (0),    -- '1920x1080'
        v1-1440x1080                  (1),    -- '1440x1080'
        v2-1280x1080                  (2),    -- '1280x1080'
        v3-960x1080                   (3),    -- '960x1080'
        v4-1280x720                   (4),    -- '1280x720'
        v5-960x720                    (5),    -- '960x720'
        v6-640x720                    (6),    -- '640x720'
        v7-720x576                    (7),    -- '720x576'
        v8-704x576                    (8),    -- '704x576'
        v9-640x576                    (9),    -- '640x576'
        v10-544x576                   (10),    -- '544x576'
        v11-528x576                   (11),    -- '528x576'
        v12-480x576                   (12),    -- '480x576'
        v13-352x576                   (13),    -- '352x576'
        v14-720x480                   (14),    -- '720x480'
        v15-704x480                   (15),    -- '704x480'
        v16-640x480                   (16),    -- '640x480'
        v17-544x480                   (17),    -- '544x480'
        v18-528x480                   (18),    -- '528x480'
        v19-480x480                   (19),    -- '480x480'
        v20-352x480                   (20),    -- '352x480'
        v21-352x288                   (21),    -- '352x288'
        v22-416x240                   (22),    -- '416x240'
        v23-352x240                   (23),    -- '352x240'
        v24-320x240                   (24),    -- '320x240'
        v25-320x180                   (25),    -- '320x180'
        v26-192x192                   (26),    -- '192x192'
        v27-176x120                   (27),    -- '176x120'
        v28-160x120                   (28),    -- '160x120'
        v29-160x90                    (29),    -- '160x90'
        v30-128x96                    (30),    -- '128x96'
        v31-96x96                     (31)     -- '96x96'
    }

Enc1E42enumObj ::= TEXTUAL-CONVENTION
    STATUS current
    DESCRIPTION
    "EnumObj"
    SYNTAX INTEGER {
        v0-1920x1080                  (0),    -- '1920x1080'
        v1-1440x1080                  (1),    -- '1440x1080'
        v2-1280x1080                  (2),    -- '1280x1080'
        v3-960x1080                   (3),    -- '960x1080'
        v4-1280x720                   (4),    -- '1280x720'
        v5-960x720                    (5),    -- '960x720'
        v6-640x720                    (6),    -- '640x720'
        v7-720x576                    (7),    -- '720x576'
        v8-704x576                    (8),    -- '704x576'
        v9-544x576                    (9),    -- '544x576'
        v10-528x576                   (10),    -- '528x576'
        v11-352x576                   (11),    -- '352x576'
        v12-720x480                   (12),    -- '720x480'
        v13-704x480                   (13),    -- '704x480'
        v14-640x480                   (14),    -- '640x480'
        v15-544x480                   (15),    -- '544x480'
        v16-528x480                   (16),    -- '528x480'
        v17-480x480                   (17),    -- '480x480'
        v18-352x480                   (18),    -- '352x480'
        v19-352x288                   (19),    -- '352x288'
        v20-416x240                   (20),    -- '416x240'
        v21-352x240                   (21),    -- '352x240'
        v22-320x240                   (22),    -- '320x240'
        v23-320x180                   (23),    -- '320x180'
        v24-192x192                   (24),    -- '192x192'
        v25-176x120                   (25),    -- '176x120'
        v26-160x120                   (26),    -- '160x120'
        v27-160x90                    (27),    -- '160x90'
        v28-128x96                    (28),    -- '128x96'
        v29-96x96                     (29),    -- '96x96'
        v30-640x576                   (30),    -- '640x576'
        v31-480x576                   (31)     -- '480x576'
    }

Enc1E43enumObj ::= TEXTUAL-CONVENTION
    STATUS current
    DESCRIPTION
    "EnumObj"
    SYNTAX INTEGER {
        v0-1920x1080                  (0),    -- '1920x1080'
        v1-1440x1080                  (1),    -- '1440x1080'
        v2-1280x1080                  (2),    -- '1280x1080'
        v3-960x1080                   (3),    -- '960x1080'
        v4-1280x720                   (4),    -- '1280x720'
        v5-960x720                    (5),    -- '960x720'
        v6-640x720                    (6),    -- '640x720'
        v7-720x576                    (7),    -- '720x576'
        v8-704x576                    (8),    -- '704x576'
        v9-544x576                    (9),    -- '544x576'
        v10-528x576                   (10),    -- '528x576'
        v11-352x576                   (11),    -- '352x576'
        v12-720x480                   (12),    -- '720x480'
        v13-704x480                   (13),    -- '704x480'
        v14-640x480                   (14),    -- '640x480'
        v15-544x480                   (15),    -- '544x480'
        v16-528x480                   (16),    -- '528x480'
        v17-480x480                   (17),    -- '480x480'
        v18-352x480                   (18),    -- '352x480'
        v19-352x288                   (19),    -- '352x288'
        v20-416x240                   (20),    -- '416x240'
        v21-352x240                   (21),    -- '352x240'
        v22-320x240                   (22),    -- '320x240'
        v23-320x180                   (23),    -- '320x180'
        v24-192x192                   (24),    -- '192x192'
        v25-176x120                   (25),    -- '176x120'
        v26-160x120                   (26),    -- '160x120'
        v27-160x90                    (27),    -- '160x90'
        v28-128x96                    (28),    -- '128x96'
        v29-96x96                     (29)     -- '96x96'
    }

Enc1E44enumObj ::= TEXTUAL-CONVENTION
    STATUS current
    DESCRIPTION
    "EnumObj"
    SYNTAX INTEGER {
        v0-mpeg2-Simple               (0),    -- 'Mpeg2-Simple'
        v1-mpeg2-Main                 (1),    -- 'Mpeg2-Main'
        v2-mpeg2-422                  (2),    -- 'Mpeg2-422'
        v3-mpeg2-High                 (3),    -- 'Mpeg2-High'
        v4-h264-Baseline              (4),    -- 'H264-Baseline'
        v5-h264-Main                  (5),    -- 'H264-Main'
        v6-h264-High                  (6)     -- 'H264-High'
    }

Enc1E45enumObj ::= TEXTUAL-CONVENTION
    STATUS current
    DESCRIPTION
    "EnumObj"
    SYNTAX INTEGER {
        v0-auto                       (0),    -- 'Auto'
        v1-low                        (1),    -- 'LOW'
        v2-main                       (2),    -- 'MAIN'
        v3-422MAIN                    (3),    -- '422_MAIN'
        v4-high1440                   (4),    -- 'HIGH 1440'
        v5-high                       (5),    -- 'HIGH'
        v6-422HIGH                    (6),    -- '422 HIGH'
        v7-1                          (7),    -- '1'
        v8-11                         (8),    -- '1.1'
        v9-12                         (9),    -- '1.2'
        v10-13                        (10),    -- '1.3'
        v11-2                         (11),    -- '2'
        v12-21                        (12),    -- '2.1'
        v13-22                        (13),    -- '2.2'
        v14-3                         (14),    -- '3'
        v15-31                        (15),    -- '3.1'
        v16-32                        (16),    -- '3.2'
        v17-4                         (17),    -- '4'
        v18-41                        (18),    -- '4.1'
        v19-42                        (19),    -- '4.2'
        v20-5                         (20),    -- '5'
        v21-51                        (21)     -- '5.1'
    }

Enc1E46enumObj ::= TEXTUAL-CONVENTION
    STATUS current
    DESCRIPTION
    "EnumObj"
    SYNTAX INTEGER {
        v0-mpeg2                      (0),    -- 'Mpeg2'
        v1-h264                       (1)     -- 'H264'
    }

Enc1E47enumObj ::= TEXTUAL-CONVENTION
    STATUS current
    DESCRIPTION
    "EnumObj"
    SYNTAX INTEGER {
        v0-auto                       (0),    -- 'Auto'
        v1-frame                      (1),    -- 'Frame'
        v2-field                      (2),    -- 'Field'
        v3-mbaff                      (3)     -- 'MBAFF'
    }

Enc1E48enumObj ::= TEXTUAL-CONVENTION
    STATUS current
    DESCRIPTION
    "EnumObj"
    SYNTAX INTEGER {
        v0-420                        (0),    -- '4:2:0'
        v1-422                        (1)     -- '4:2:2'
    }

Enc1E49enumObj ::= TEXTUAL-CONVENTION
    STATUS current
    DESCRIPTION
    "EnumObj"
    SYNTAX INTEGER {
        v0-8Bit                       (0),    -- '8 Bit'
        v1-10Bit                      (1)     -- '10 Bit'
    }

Enc1E50enumObj ::= TEXTUAL-CONVENTION
    STATUS current
    DESCRIPTION
    "EnumObj"
    SYNTAX INTEGER {
        v0-cbr                        (0),    -- 'CBR'
        v1-vbr                        (1),    -- 'VBR'
        v2-capped-VBR                 (2)     -- 'Capped-VBR'
    }

Enc1E51enumObj ::= TEXTUAL-CONVENTION
    STATUS current
    DESCRIPTION
    "EnumObj"
    SYNTAX INTEGER {
        v0-150                        (0),    -- '150'
        v1-200                        (1),    -- '200'
        v2-650                        (2)     -- '650'
    }

Enc1E52enumObj ::= TEXTUAL-CONVENTION
    STATUS current
    DESCRIPTION
    "EnumObj"
    SYNTAX INTEGER {
        v0-auto-43                    (0),    -- 'Auto-4:3'
        v1-auto-169                   (1),    -- 'Auto-16:9'
        v2-43                         (2),    -- '4:3'
        v3-169                        (3)     -- '16:9'
    }

Enc1E53enumObj ::= TEXTUAL-CONVENTION
    STATUS current
    DESCRIPTION
    "EnumObj"
    SYNTAX INTEGER {
        v0-43                         (0),    -- '4:3'
        v1-169                        (1)     -- '16:9'
    }

Enc1E54enumObj ::= TEXTUAL-CONVENTION
    STATUS current
    DESCRIPTION
    "EnumObj"
    SYNTAX INTEGER {
        v0-disable                    (0),    -- 'Disable'
        v1-enable                     (1)     -- 'Enable'
    }

Enc1E55enumObj ::= TEXTUAL-CONVENTION
    STATUS current
    DESCRIPTION
    "EnumObj"
    SYNTAX INTEGER {
        v0-sdisource                  (0),    -- 'SDI Source'
        v1-controller                 (1)     -- 'Controller'
    }

Enc1E56enumObj ::= TEXTUAL-CONVENTION
    STATUS current
    DESCRIPTION
    "EnumObj"
    SYNTAX INTEGER {
        v0-i                          (0),    -- 'I'
        v1-ip                         (1),    -- 'IP'
        v2-1B                         (2),    -- '1B'
        v3-2B                         (3),    -- '2B'
        v4-3B                         (4),    -- '3B'
        v5-auto                       (5)     -- 'Auto'
    }

Enc1E57enumObj ::= TEXTUAL-CONVENTION
    STATUS current
    DESCRIPTION
    "EnumObj"
    SYNTAX INTEGER {
        v0-short025sec                (0),    -- 'Short (~0.25 sec)'
        v1-medium05sec                (1),    -- 'Medium (~0.5 sec)'
        v2-long1sec                   (2),    -- 'Long (~1 sec)'
        v3-ultraLong2sec              (3),    -- 'Ultra Long (~2 sec)'
        v4-progressiveRefresh         (4),    -- 'Progressive Refresh'
        v5-maximum300frms             (5)     -- 'Maximum (300 frms)'
    }

Enc1E58enumObj ::= TEXTUAL-CONVENTION
    STATUS current
    DESCRIPTION
    "EnumObj"
    SYNTAX INTEGER {
        v0-short025sec                (0),    -- 'Short (~0.25 sec)'
        v1-medium05sec                (1),    -- 'Medium (~0.5 sec)'
        v2-long1sec                   (2),    -- 'Long (~1 sec)'
        v3-ultraLong2sec              (3),    -- 'Ultra Long (~2 sec)'
        v4-progressiveRefresh         (4),    -- 'Progressive Refresh'
        v5-maximum300frms             (5)     -- 'Maximum (300 frms)'
    }

Enc1E59enumObj ::= TEXTUAL-CONVENTION
    STATUS current
    DESCRIPTION
    "EnumObj"
    SYNTAX INTEGER {
        v0-auto                       (0),    -- 'Auto'
        v1-none                       (1),    -- 'None'
        v2-sharp                      (2),    -- 'Sharp'
        v3-soft                       (3),    -- 'Soft'
        v4-custom                     (4)     -- 'Custom'
    }

Enc1E60enumObj ::= TEXTUAL-CONVENTION
    STATUS current
    DESCRIPTION
    "EnumObj"
    SYNTAX INTEGER {
        v0-disable                    (0),    -- 'Disable'
        v1-enable                     (1)     -- 'Enable'
    }

Enc1E61enumObj ::= TEXTUAL-CONVENTION
    STATUS current
    DESCRIPTION
    "EnumObj"
    SYNTAX INTEGER {
        v0-unknown                    (0),    -- 'Unknown'
        v1-525                        (1),    -- '525'
        v2-625                        (2),    -- '625'
        v3-720p23unsupported          (3),    -- '720p 23 unsupported'
        v4-720p24unsupported          (4),    -- '720p 24 unsupported'
        v5-720p25unsupported          (5),    -- '720p 25 unsupported'
        v6-720p29unsupported          (6),    -- '720p 29 unsupported'
        v7-720p30unsupported          (7),    -- '720p 30 unsupported'
        v8-720p50                     (8),    -- '720p 50'
        v9-720p5994                   (9),    -- '720p 59.94'
        v10-720p60unsupported         (10),    -- '720p 60 unsupported'
        v11-1035i25unsupported        (11),    -- '1035i 25 unsupported'
        v12-1035i29unsupported        (12),    -- '1035i 29 unsupported'
        v13-1035i30unsupported        (13),    -- '1035i 30 unsupported'
        v14-1080i50                   (14),    -- '1080i 50'
        v15-1080i5994                 (15),    -- '1080i 59.94'
        v16-1080i30unsupported        (16),    -- '1080i 30 unsupported'
        v17-1080p23unsupported        (17),    -- '1080p 23 unsupported'
        v18-1080p2398unsupported      (18),    -- '1080p 23.98 unsupported'
        v19-1080p24unsupported        (19),    -- '1080p 24 unsupported'
        v20-1080p24Aunsupported       (20),    -- '1080p 24_A unsupported'
        v21-1080p25unsupported        (21),    -- '1080p 25 unsupported'
        v22-1080p25295Munsupported    (22),    -- '1080p 25_295M unsupported'
        v23-1080p2997unsupported      (23),    -- '1080p 29.97 unsupported'
        v24-1080p30unsupported        (24),    -- '1080p 30 unsupported'
        v25-1080p50                   (25),    -- '1080p 50'
        v26-1080p5994                 (26)     -- '1080p 59.94'
    }

Enc1E62enumObj ::= TEXTUAL-CONVENTION
    STATUS current
    DESCRIPTION
    "EnumObj"
    SYNTAX INTEGER {
        v0-auto                       (0),    -- 'Auto'
        v1-ip                         (1),    -- 'IP'
        v2-ipb                        (2),    -- 'IPB'
        v3-ipbb                       (3),    -- 'IPBB'
        v4-ipbbb                      (4),    -- 'IPBBB'
        v5-ipbbbb                     (5),    -- 'IPBBBB'
        v6-ipbbbbb                    (6),    -- 'IPBBBBB'
        v7-ipbbbbbb                   (7),    -- 'IPBBBBBB'
        v8-ipbbbbbbb                  (8)     -- 'IPBBBBBBB'
    }

Enc1E63enumObj ::= TEXTUAL-CONVENTION
    STATUS current
    DESCRIPTION
    "EnumObj"
    SYNTAX INTEGER {
        v0-0                          (0),    -- '0'
        v1-1                          (1),    -- '1'
        v2-2                          (2),    -- '2'
        v3-3                          (3),    -- '3'
        v4-4                          (4)     -- '4'
    }

Enc1E64enumObj ::= TEXTUAL-CONVENTION
    STATUS current
    DESCRIPTION
    "EnumObj"
    SYNTAX INTEGER {
        v0-0-8Bits                    (0),    -- '0 - 8 Bits'
        v1-1-9Bits                    (1),    -- '1 - 9 Bits'
        v2-2-10Bits                   (2),    -- '2 - 10 Bits'
        v3-3-11Bits                   (3)     -- '3 - 11 Bits'
    }

Enc1E65enumObj ::= TEXTUAL-CONVENTION
    STATUS current
    DESCRIPTION
    "EnumObj"
    SYNTAX INTEGER {
        v0-linear                     (0),    -- 'Linear'
        v1-non-Linear                 (1)     -- 'Non-Linear'
    }

Enc1E66enumObj ::= TEXTUAL-CONVENTION
    STATUS current
    DESCRIPTION
    "EnumObj"
    SYNTAX INTEGER {
        v0-mpeg-1VLC                  (0),    -- 'MPEG-1 VLC'
        v1-alternateVLC               (1)     -- 'Alternate VLC'
    }

Enc1E67enumObj ::= TEXTUAL-CONVENTION
    STATUS current
    DESCRIPTION
    "EnumObj"
    SYNTAX INTEGER {
        v0-disabled                   (0),    -- 'Disabled'
        v1-enabled                    (1)     -- 'Enabled'
    }

Enc1E68enumObj ::= TEXTUAL-CONVENTION
    STATUS current
    DESCRIPTION
    "EnumObj"
    SYNTAX INTEGER {
        v0-1080                       (0),    -- '1080'
        v1-720                        (1),    -- '720'
        v2-625                        (2),    -- '625'
        v3-525                        (3)     -- '525'
    }

Enc1E69enumObj ::= TEXTUAL-CONVENTION
    STATUS current
    DESCRIPTION
    "EnumObj"
    SYNTAX INTEGER {
        v0-ready                      (0),    -- 'Ready'
        v1-unavailable                (1),    -- 'Unavailable'
        v2-loading                    (2),    -- 'Loading'
        v3-loadError                  (3),    -- 'Load Error'
        v4-wrongSize                  (4),    -- 'Wrong Size'
        v5-invalidFormat              (5),    -- 'Invalid Format'
        v6-inputMismatch              (6)     -- 'Input Mismatch'
    }

Enc1E70enumObj ::= TEXTUAL-CONVENTION
    STATUS current
    DESCRIPTION
    "EnumObj"
    SYNTAX INTEGER {
        v0-none                       (0),    -- 'None'
        v1-mute                       (1),    -- 'Mute'
        v2-tone                       (2),    -- 'Tone'
        v3-aes1                       (3),    -- 'AES 1'
        v4-aes2                       (4),    -- 'AES 2'
        v5-aes3                       (5),    -- 'AES 3'
        v6-aes4                       (6),    -- 'AES 4'
        v7-aes5                       (7),    -- 'AES 5'
        v8-aes6                       (8),    -- 'AES 6'
        v9-aes7                       (9),    -- 'AES 7'
        v10-aes8                      (10),    -- 'AES 8'
        v11-emb1A-1BG1P1              (11),    -- 'Emb 1A-1B (G1P1)'
        v12-emb2A-2BG1P2              (12),    -- 'Emb 2A-2B (G1P2)'
        v13-emb3A-3BG2P1              (13),    -- 'Emb 3A-3B (G2P1)'
        v14-emb4A-4BG2P2              (14),    -- 'Emb 4A-4B (G2P2)'
        v15-emb5A-5BG3P1              (15),    -- 'Emb 5A-5B (G3P1)'
        v16-emb6A-6BG3P2              (16),    -- 'Emb 6A-6B (G3P2)'
        v17-emb7A-7BG4P1              (17),    -- 'Emb 7A-7B (G4P1)'
        v18-emb8A-8BG4P2              (18),    -- 'Emb 8A-8B (G4P2)'
        v19-emb9A-9BG5P1              (19),    -- 'Emb 9A-9B (G5P1)'
        v20-emb10A-10BG5P2            (20),    -- 'Emb 10A-10B (G5P2)'
        v21-emb11A-11BG6P1            (21),    -- 'Emb 11A-11B (G6P1)'
        v22-emb12A-12BG6P2            (22),    -- 'Emb 12A-12B (G6P2)'
        v23-emb13A-13BG7P1            (23),    -- 'Emb 13A-13B (G7P1)'
        v24-emb14A-14BG7P2            (24),    -- 'Emb 14A-14B (G7P2)'
        v25-emb15A-15BG8P1            (25),    -- 'Emb 15A-15B (G8P1)'
        v26-emb16A-16BG8P2            (26),    -- 'Emb 16A-16B (G8P2)'
        v27-aap1Audio1A-1B            (27),    -- 'AAP 1 Audio 1A-1B'
        v28-aap1Audio2A-2B            (28),    -- 'AAP 1 Audio 2A-2B'
        v29-aap1Audio3A-3B            (29),    -- 'AAP 1 Audio 3A-3B'
        v30-aap1Audio4A-4B            (30)     -- 'AAP 1 Audio 4A-4B'
    }

Enc1E71enumObj ::= TEXTUAL-CONVENTION
    STATUS current
    DESCRIPTION
    "EnumObj"
    SYNTAX INTEGER {
        v0-none                       (0),    -- 'None'
        v1-mute                       (1),    -- 'Mute'
        v2-tone                       (2),    -- 'Tone'
        v3-aes1                       (3),    -- 'AES 1'
        v4-aes2                       (4),    -- 'AES 2'
        v5-aes3                       (5),    -- 'AES 3'
        v6-aes4                       (6),    -- 'AES 4'
        v7-aes5                       (7),    -- 'AES 5'
        v8-aes6                       (8),    -- 'AES 6'
        v9-aes7                       (9),    -- 'AES 7'
        v10-aes8                      (10),    -- 'AES 8'
        v11-emb1A-1BG1P1              (11),    -- 'Emb 1A-1B (G1P1)'
        v12-emb2A-2BG1P2              (12),    -- 'Emb 2A-2B (G1P2)'
        v13-emb3A-3BG2P1              (13),    -- 'Emb 3A-3B (G2P1)'
        v14-emb4A-4BG2P2              (14),    -- 'Emb 4A-4B (G2P2)'
        v15-emb5A-5BG3P1              (15),    -- 'Emb 5A-5B (G3P1)'
        v16-emb6A-6BG3P2              (16),    -- 'Emb 6A-6B (G3P2)'
        v17-emb7A-7BG4P1              (17),    -- 'Emb 7A-7B (G4P1)'
        v18-emb8A-8BG4P2              (18),    -- 'Emb 8A-8B (G4P2)'
        v19-emb9A-9BG5P1              (19),    -- 'Emb 9A-9B (G5P1)'
        v20-emb10A-10BG5P2            (20),    -- 'Emb 10A-10B (G5P2)'
        v21-emb11A-11BG6P1            (21),    -- 'Emb 11A-11B (G6P1)'
        v22-emb12A-12BG6P2            (22),    -- 'Emb 12A-12B (G6P2)'
        v23-emb13A-13BG7P1            (23),    -- 'Emb 13A-13B (G7P1)'
        v24-emb14A-14BG7P2            (24),    -- 'Emb 14A-14B (G7P2)'
        v25-emb15A-15BG8P1            (25),    -- 'Emb 15A-15B (G8P1)'
        v26-emb16A-16BG8P2            (26)     -- 'Emb 16A-16B (G8P2)'
    }

Enc1E72enumObj ::= TEXTUAL-CONVENTION
    STATUS current
    DESCRIPTION
    "EnumObj"
    SYNTAX INTEGER {
        v0-none                       (0)     -- 'None'
    }

Enc1E73enumObj ::= TEXTUAL-CONVENTION
    STATUS current
    DESCRIPTION
    "EnumObj"
    SYNTAX INTEGER {
        v0-mpeg-32k                   (0),    -- 'Mpeg-32k'
        v1-mpeg-48k                   (1),    -- 'Mpeg-48k'
        v2-mpeg-56k                   (2),    -- 'Mpeg-56k'
        v3-mpeg-64k                   (3),    -- 'Mpeg-64k'
        v4-mpeg-80k                   (4),    -- 'Mpeg-80k'
        v5-mpeg-96k                   (5),    -- 'Mpeg-96k'
        v6-mpeg-112k                  (6),    -- 'Mpeg-112k'
        v7-mpeg-128k                  (7),    -- 'Mpeg-128k'
        v8-mpeg-160k                  (8),    -- 'Mpeg-160k'
        v9-mpeg-192k                  (9),    -- 'Mpeg-192k'
        v10-mpeg-224k                 (10),    -- 'Mpeg-224k'
        v11-mpeg-256k                 (11),    -- 'Mpeg-256k'
        v12-mpeg-320k                 (12),    -- 'Mpeg-320k'
        v13-mpeg-384k                 (13),    -- 'Mpeg-384k'
        v14-dolbyDigital-32k          (14),    -- 'Dolby Digital-32k'
        v15-dolbyDigital-40k          (15),    -- 'Dolby Digital-40k'
        v16-dolbyDigital-48k          (16),    -- 'Dolby Digital-48k'
        v17-dolbyDigital-56k          (17),    -- 'Dolby Digital-56k'
        v18-dolbyDigital-64k          (18),    -- 'Dolby Digital-64k'
        v19-dolbyDigital-80k          (19),    -- 'Dolby Digital-80k'
        v20-dolbyDigital-96k          (20),    -- 'Dolby Digital-96k'
        v21-dolbyDigital-112k         (21),    -- 'Dolby Digital-112k'
        v22-dolbyDigital-128k         (22),    -- 'Dolby Digital-128k'
        v23-dolbyDigital-160k         (23),    -- 'Dolby Digital-160k'
        v24-dolbyDigital-192k         (24),    -- 'Dolby Digital-192k'
        v25-dolbyDigital-224k         (25),    -- 'Dolby Digital-224k'
        v26-dolbyDigital-256k         (26),    -- 'Dolby Digital-256k'
        v27-dolbyDigital-320k         (27),    -- 'Dolby Digital-320k'
        v28-dolbyDigital-384k         (28),    -- 'Dolby Digital-384k'
        v29-dolbyDigital-448k         (29),    -- 'Dolby Digital-448k'
        v30-dolbyDigital-512k         (30),    -- 'Dolby Digital-512k'
        v31-dolbyDigital-576k         (31),    -- 'Dolby Digital-576k'
        v32-dolbyDigital-640k         (32),    -- 'Dolby Digital-640k'
        v33-externallyCompressed-192k (33),    -- 'Externally Compressed-192k'
        v34-externallyCompressed-256k (34),    -- 'Externally Compressed-256k'
        v35-externallyCompressed-384k (35),    -- 'Externally Compressed-384k'
        v36-externallyCompressed-448k (36),    -- 'Externally Compressed-448k'
        v37-externallyCompressed-640k (37),    -- 'Externally Compressed-640k'
        v38-externallyCompressed-1024k(38),    -- 'Externally Compressed-1024k'
        v39-externallyCompressed-2400k(39),    -- 'Externally Compressed-2400k'
        v40-smpte302-2000k            (40),    -- 'SMPTE 302-2000k'
        v41-smpte302-2400k            (41),    -- 'SMPTE 302-2400k'
        v42-smpte302-2800k            (42),    -- 'SMPTE 302-2800k'
        v43-aaclc-56k                 (43),    -- 'AAC LC-56k'
        v44-aaclc-64k                 (44),    -- 'AAC LC-64k'
        v45-aaclc-80k                 (45),    -- 'AAC LC-80k'
        v46-aaclc-96k                 (46),    -- 'AAC LC-96k'
        v47-aaclc-112k                (47),    -- 'AAC LC-112k'
        v48-aaclc-128k                (48),    -- 'AAC LC-128k'
        v49-aaclc-160k                (49),    -- 'AAC LC-160k'
        v50-aaclc-192k                (50),    -- 'AAC LC-192k'
        v51-aaclc-224k                (51),    -- 'AAC LC-224k'
        v52-aaclc-256k                (52),    -- 'AAC LC-256k'
        v53-aaclc-280k                (53),    -- 'AAC LC-280k'
        v54-aaclc-320k                (54),    -- 'AAC LC-320k'
        v55-aaclc-384k                (55),    -- 'AAC LC-384k'
        v56-aaclc-448k                (56),    -- 'AAC LC-448k'
        v57-aaclc-512k                (57),    -- 'AAC LC-512k'
        v58-aaclc-576k                (58),    -- 'AAC LC-576k'
        v59-aaclc-640k                (59),    -- 'AAC LC-640k'
        v60-aaclc-800k                (60),    -- 'AAC LC-800k'
        v61-aache-24k                 (61),    -- 'AAC HE-24k'
        v62-aache-32k                 (62),    -- 'AAC HE-32k'
        v63-aache-40k                 (63),    -- 'AAC HE-40k'
        v64-aache-48k                 (64),    -- 'AAC HE-48k'
        v65-aache-56k                 (65),    -- 'AAC HE-56k'
        v66-aache-64k                 (66),    -- 'AAC HE-64k'
        v67-aache-80k                 (67),    -- 'AAC HE-80k'
        v68-aache-96k                 (68),    -- 'AAC HE-96k'
        v69-aache-112k                (69),    -- 'AAC HE-112k'
        v70-aache-128k                (70),    -- 'AAC HE-128k'
        v71-aache-160k                (71),    -- 'AAC HE-160k'
        v72-aache-192k                (72),    -- 'AAC HE-192k'
        v73-aache-224k                (73),    -- 'AAC HE-224k'
        v74-aache-240k                (74),    -- 'AAC HE-240k'
        v75-dolbyE-2000k              (75),    -- 'Dolby E-2000k'
        v76-dolbyE-2400k              (76),    -- 'Dolby E-2400k'
        v77-dolbyDigitalPlus-32k      (77),    -- 'Dolby Digital Plus-32k'
        v78-dolbyDigitalPlus-40k      (78),    -- 'Dolby Digital Plus-40k'
        v79-dolbyDigitalPlus-48k      (79),    -- 'Dolby Digital Plus-48k'
        v80-dolbyDigitalPlus-56k      (80),    -- 'Dolby Digital Plus-56k'
        v81-dolbyDigitalPlus-64k      (81),    -- 'Dolby Digital Plus-64k'
        v82-dolbyDigitalPlus-72k      (82),    -- 'Dolby Digital Plus-72k'
        v83-dolbyDigitalPlus-80k      (83),    -- 'Dolby Digital Plus-80k'
        v84-dolbyDigitalPlus-88k      (84),    -- 'Dolby Digital Plus-88k'
        v85-dolbyDigitalPlus-96k      (85),    -- 'Dolby Digital Plus-96k'
        v86-dolbyDigitalPlus-104k     (86),    -- 'Dolby Digital Plus-104k'
        v87-dolbyDigitalPlus-112k     (87),    -- 'Dolby Digital Plus-112k'
        v88-dolbyDigitalPlus-120k     (88),    -- 'Dolby Digital Plus-120k'
        v89-dolbyDigitalPlus-128k     (89),    -- 'Dolby Digital Plus-128k'
        v90-dolbyDigitalPlus-144k     (90),    -- 'Dolby Digital Plus-144k'
        v91-dolbyDigitalPlus-160k     (91),    -- 'Dolby Digital Plus-160k'
        v92-dolbyDigitalPlus-176k     (92),    -- 'Dolby Digital Plus-176k'
        v93-dolbyDigitalPlus-192k     (93),    -- 'Dolby Digital Plus-192k'
        v94-dolbyDigitalPlus-200k     (94),    -- 'Dolby Digital Plus-200k'
        v95-dolbyDigitalPlus-208k     (95),    -- 'Dolby Digital Plus-208k'
        v96-dolbyDigitalPlus-224k     (96),    -- 'Dolby Digital Plus-224k'
        v97-dolbyDigitalPlus-232k     (97),    -- 'Dolby Digital Plus-232k'
        v98-dolbyDigitalPlus-240k     (98),    -- 'Dolby Digital Plus-240k'
        v99-dolbyDigitalPlus-248k     (99),    -- 'Dolby Digital Plus-248k'
        v100-dolbyDigitalPlus-256k    (100),    -- 'Dolby Digital Plus-256k'
        v101-dolbyDigitalPlus-272k    (101),    -- 'Dolby Digital Plus-272k'
        v102-dolbyDigitalPlus-288k    (102),    -- 'Dolby Digital Plus-288k'
        v103-dolbyDigitalPlus-304k    (103),    -- 'Dolby Digital Plus-304k'
        v104-dolbyDigitalPlus-320k    (104),    -- 'Dolby Digital Plus-320k'
        v105-dolbyDigitalPlus-336k    (105),    -- 'Dolby Digital Plus-336k'
        v106-dolbyDigitalPlus-352k    (106),    -- 'Dolby Digital Plus-352k'
        v107-dolbyDigitalPlus-368k    (107),    -- 'Dolby Digital Plus-368k'
        v108-dolbyDigitalPlus-384k    (108),    -- 'Dolby Digital Plus-384k'
        v109-dolbyDigitalPlus-400k    (109),    -- 'Dolby Digital Plus-400k'
        v110-dolbyDigitalPlus-448k    (110),    -- 'Dolby Digital Plus-448k'
        v111-dolbyDigitalPlus-512k    (111),    -- 'Dolby Digital Plus-512k'
        v112-dolbyDigitalPlus-576k    (112),    -- 'Dolby Digital Plus-576k'
        v113-dolbyDigitalPlus-640k    (113),    -- 'Dolby Digital Plus-640k'
        v114-dolbyDigitalPlus-704k    (114),    -- 'Dolby Digital Plus-704k'
        v115-dolbyDigitalPlus-768k    (115),    -- 'Dolby Digital Plus-768k'
        v116-dolbyDigitalPlus-832k    (116),    -- 'Dolby Digital Plus-832k'
        v117-dolbyDigitalPlus-896k    (117),    -- 'Dolby Digital Plus-896k'
        v118-dolbyDigitalPlus-960k    (118),    -- 'Dolby Digital Plus-960k'
        v119-dolbyDigitalPlus-1024k   (119)     -- 'Dolby Digital Plus-1024k'
    }

Enc1E74enumObj ::= TEXTUAL-CONVENTION
    STATUS current
    DESCRIPTION
    "EnumObj"
    SYNTAX INTEGER {
        v0-aache                      (0),    -- 'AAC HE'
        v1-aaclc                      (1),    -- 'AAC LC'
        v2-dolbyDigital               (2),    -- 'Dolby Digital'
        v3-externallyCompressed       (3),    -- 'Externally Compressed'
        v4-mpeg                       (4),    -- 'Mpeg'
        v5-smpte302                   (5)     -- 'SMPTE 302'
    }

Enc1E75enumObj ::= TEXTUAL-CONVENTION
    STATUS current
    DESCRIPTION
    "EnumObj"
    SYNTAX INTEGER {
        v0-24k                        (0),    -- '24k'
        v1-32k                        (1),    -- '32k'
        v2-40k                        (2),    -- '40k'
        v3-48k                        (3),    -- '48k'
        v4-56k                        (4),    -- '56k'
        v5-64k                        (5),    -- '64k'
        v6-80k                        (6),    -- '80k'
        v7-96k                        (7),    -- '96k'
        v8-112k                       (8),    -- '112k'
        v9-128k                       (9),    -- '128k'
        v10-160k                      (10),    -- '160k'
        v11-192k                      (11),    -- '192k'
        v12-224k                      (12),    -- '224k'
        v13-240k                      (13),    -- '240k'
        v14-256k                      (14),    -- '256k'
        v15-280k                      (15),    -- '280k'
        v16-320k                      (16),    -- '320k'
        v17-384k                      (17),    -- '384k'
        v18-448k                      (18),    -- '448k'
        v19-512k                      (19),    -- '512k'
        v20-576k                      (20),    -- '576k'
        v21-640k                      (21),    -- '640k'
        v22-800k                      (22),    -- '800k'
        v23-2000k                     (23),    -- '2000k'
        v24-2400k                     (24),    -- '2400k'
        v25-2800k                     (25)     -- '2800k'
    }

Enc1E76enumObj ::= TEXTUAL-CONVENTION
    STATUS current
    DESCRIPTION
    "EnumObj"
    SYNTAX INTEGER {
        v0-auto                       (0),    -- 'Auto'
        v1-implicit                   (1),    -- 'Implicit'
        v2-explicit                   (2)     -- 'Explicit'
    }

Enc1E77enumObj ::= TEXTUAL-CONVENTION
    STATUS current
    DESCRIPTION
    "EnumObj"
    SYNTAX INTEGER {
        v0-auto                       (0),    -- 'Auto'
        v1-implicit                   (1),    -- 'Implicit'
        v2-explicitHierarchical       (2)     -- 'Explicit Hierarchical'
    }

Enc1E78enumObj ::= TEXTUAL-CONVENTION
    STATUS current
    DESCRIPTION
    "EnumObj"
    SYNTAX INTEGER {
        v0-auto                       (0),    -- 'Auto'
        v1-adts                       (1),    -- 'ADTS'
        v2-loas                       (2)     -- 'LOAS'
    }

Enc1E79enumObj ::= TEXTUAL-CONVENTION
    STATUS current
    DESCRIPTION
    "EnumObj"
    SYNTAX INTEGER {
        v0-consumer10dBV              (0),    -- 'Consumer 10 dBV'
        v1-pro18dBu                   (1),    -- 'Pro 18 dBu'
        v2-pro20dBu                   (2),    -- 'Pro 20 dBu'
        v3-pro24dBu                   (3)     -- 'Pro 24 dBu'
    }

Enc1E80enumObj ::= TEXTUAL-CONVENTION
    STATUS current
    DESCRIPTION
    "EnumObj"
    SYNTAX INTEGER {
        v0-mute                       (0),    -- 'Mute'
        v1-stop                       (1)     -- 'Stop'
    }

Enc1E81enumObj ::= TEXTUAL-CONVENTION
    STATUS current
    DESCRIPTION
    "EnumObj"
    SYNTAX INTEGER {
        v0-off                        (0),    -- 'Off'
        v1-main                       (1),    -- 'Main'
        v2-pip                        (2),    -- 'Pip'
        v3-independentMain            (3)     -- 'Independent (Main)'
    }

Enc1E82enumObj ::= TEXTUAL-CONVENTION
    STATUS current
    DESCRIPTION
    "EnumObj"
    SYNTAX INTEGER {
        v0-off                        (0),    -- 'Off'
        v1-main                       (1),    -- 'Main'
        v2-pip                        (2),    -- 'Pip'
        v3-independentMain            (3)     -- 'Independent (Main)'
    }

Enc1E83enumObj ::= TEXTUAL-CONVENTION
    STATUS current
    DESCRIPTION
    "EnumObj"
    SYNTAX INTEGER {
        v0-none                       (0),    -- 'None'
        v1-generator1                 (1),    -- 'Generator 1'
        v2-generator2                 (2),    -- 'Generator 2'
        v3-serial1                    (3),    -- 'Serial 1'
        v4-serial2                    (4),    -- 'Serial 2'
        v5-vanc                       (5),    -- 'VANC'
        v6-aap1                       (6)     -- 'AAP 1'
    }

Enc1E84enumObj ::= TEXTUAL-CONVENTION
    STATUS current
    DESCRIPTION
    "EnumObj"
    SYNTAX INTEGER {
        v0-lastReceivedorGen1         (0),    -- 'Last Received or Gen 1'
        v1-lastReceivedorGen2         (1),    -- 'Last Received or Gen 2'
        v2-generator1                 (2),    -- 'Generator 1'
        v3-generator2                 (3)     -- 'Generator 2'
    }

Enc1E85enumObj ::= TEXTUAL-CONVENTION
    STATUS current
    DESCRIPTION
    "EnumObj"
    SYNTAX INTEGER {
        v0-completeMain               (0),    -- 'Complete Main'
        v1-musicandEffects            (1),    -- 'Music and Effects'
        v2-visuallyImpaired           (2),    -- 'Visually Impaired'
        v3-hearingImpaired            (3),    -- 'Hearing Impaired'
        v4-dialogue                   (4),    -- 'Dialogue'
        v5-commentary                 (5),    -- 'Commentary'
        v6-emergency                  (6),    -- 'Emergency'
        v7-voiceoverMode1-0CorKaraoke (7)     -- 'Voiceover (Mode 1-0 C) or Karaoke'
    }

Enc1E86enumObj ::= TEXTUAL-CONVENTION
    STATUS current
    DESCRIPTION
    "EnumObj"
    SYNTAX INTEGER {
        v0-na                         (0),    -- 'NA'
        v1-1-0C                       (1),    -- '1-0 C'
        v2-2-0LR                      (2),    -- '2-0 L,R'
        v3-3-0LCR                     (3),    -- '3-0 L,C,R'
        v4-2-1LRS                     (4),    -- '2-1 L,R,S'
        v5-3-1LCRS                    (5),    -- '3-1 L,C,R,S'
        v6-2-2LRSLSR                  (6),    -- '2-2 L,R,SL,SR'
        v7-3-2LCRSLSR                 (7)     -- '3-2 L,C,R,SL,SR'
    }

Enc1E87enumObj ::= TEXTUAL-CONVENTION
    STATUS current
    DESCRIPTION
    "EnumObj"
    SYNTAX INTEGER {
        v0-neg30dB                    (0),    -- '-3.0 dB'
        v1-neg45dB                    (1),    -- '-4.5 dB'
        v2-neg60dB                    (2)     -- '-6.0 dB'
    }

Enc1E88enumObj ::= TEXTUAL-CONVENTION
    STATUS current
    DESCRIPTION
    "EnumObj"
    SYNTAX INTEGER {
        v0-neg30dB                    (0),    -- '-3.0 dB'
        v1-neg60dB                    (1),    -- '-6.0 dB'
        v2-negInfdB                   (2)     -- '-Inf dB'
    }

Enc1E89enumObj ::= TEXTUAL-CONVENTION
    STATUS current
    DESCRIPTION
    "EnumObj"
    SYNTAX INTEGER {
        v0-notIndicated               (0),    -- 'Not Indicated'
        v1-no                         (1),    -- 'No'
        v2-yes                        (2)     -- 'Yes'
    }

Enc1E90enumObj ::= TEXTUAL-CONVENTION
    STATUS current
    DESCRIPTION
    "EnumObj"
    SYNTAX INTEGER {
        v0-notIndicated               (0),    -- 'Not Indicated'
        v1-ltRtPreferred              (1),    -- 'LtRt Preferred'
        v2-loRoPreferred              (2),    -- 'LoRo Preferred'
        v3-dolbyProLogicIIPreferred   (3)     -- 'Dolby Pro Logic II Preferred'
    }

Enc1E91enumObj ::= TEXTUAL-CONVENTION
    STATUS current
    DESCRIPTION
    "EnumObj"
    SYNTAX INTEGER {
        v0-plus30dB                   (0),    -- '+3.0 dB'
        v1-plus15dB                   (1),    -- '+1.5 dB'
        v2-00dB                       (2),    -- '0.0 dB'
        v3-neg15dB                    (3),    -- '-1.5 dB'
        v4-neg30dB                    (4),    -- '-3.0 dB'
        v5-neg45dB                    (5),    -- '-4.5 dB'
        v6-neg60dB                    (6),    -- '-6.0 dB'
        v7-negInfdB                   (7)     -- '-Inf dB'
    }

Enc1E92enumObj ::= TEXTUAL-CONVENTION
    STATUS current
    DESCRIPTION
    "EnumObj"
    SYNTAX INTEGER {
        v0-plus30dB                   (0),    -- '+3.0 dB'
        v1-plus15dB                   (1),    -- '+1.5 dB'
        v2-00dB                       (2),    -- '0.0 dB'
        v3-neg15dB                    (3),    -- '-1.5 dB'
        v4-neg30dB                    (4),    -- '-3.0 dB'
        v5-neg45dB                    (5),    -- '-4.5 dB'
        v6-neg60dB                    (6),    -- '-6.0 dB'
        v7-negInfdB                   (7)     -- '-Inf dB'
    }

Enc1E93enumObj ::= TEXTUAL-CONVENTION
    STATUS current
    DESCRIPTION
    "EnumObj"
    SYNTAX INTEGER {
        v0-standard                   (0),    -- 'Standard'
        v1-hdcd                       (1)     -- 'HDCD'
    }

Enc1E94enumObj ::= TEXTUAL-CONVENTION
    STATUS current
    DESCRIPTION
    "EnumObj"
    SYNTAX INTEGER {
        v0-notIndicated               (0),    -- 'Not Indicated'
        v1-notDolbyHeadphoneEncoded   (1),    -- 'Not Dolby Headphone Encoded'
        v2-dolbyHeadphoneEncoded      (2)     -- 'Dolby Headphone Encoded'
    }

Enc1E95enumObj ::= TEXTUAL-CONVENTION
    STATUS current
    DESCRIPTION
    "EnumObj"
    SYNTAX INTEGER {
        v0-none                       (0),    -- 'None'
        v1-filmStandard               (1),    -- 'Film, Standard'
        v2-filmLight                  (2),    -- 'Film, Light'
        v3-musicStandard              (3),    -- 'Music, Standard'
        v4-musicLight                 (4),    -- 'Music, Light'
        v5-speech                     (5)     -- 'Speech'
    }

Enc1E96enumObj ::= TEXTUAL-CONVENTION
    STATUS current
    DESCRIPTION
    "EnumObj"
    SYNTAX INTEGER {
        v0-notIndicated               (0),    -- 'Not Indicated'
        v1-largeRoom                  (1),    -- 'Large Room'
        v2-smallRoom                  (2)     -- 'Small Room'
    }

Enc1E97enumObj ::= TEXTUAL-CONVENTION
    STATUS current
    DESCRIPTION
    "EnumObj"
    SYNTAX INTEGER {
        v0-program1                   (0),    -- 'Program 1'
        v1-program2                   (1),    -- 'Program 2'
        v2-program3                   (2),    -- 'Program 3'
        v3-program4                   (3),    -- 'Program 4'
        v4-program5                   (4),    -- 'Program 5'
        v5-program6                   (5),    -- 'Program 6'
        v6-program7                   (6),    -- 'Program 7'
        v7-program8                   (7)     -- 'Program 8'
    }

Enc1E98enumObj ::= TEXTUAL-CONVENTION
    STATUS current
    DESCRIPTION
    "EnumObj"
    SYNTAX INTEGER {
        v0-16                         (0),    -- '16'
        v1-20                         (1),    -- '20'
        v2-20TOFAligned               (2)     -- '20 (TOF Aligned)'
    }

Enc1E99enumObj ::= TEXTUAL-CONVENTION
    STATUS current
    DESCRIPTION
    "EnumObj"
    SYNTAX INTEGER {
        v0-none                       (0),    -- 'None'
        v1-dynamicRangeProfile        (1),    -- 'Dynamic Range Profile'
        v2-dialogueNormalization      (2),    -- 'Dialogue Normalization'
        v3-dialNormandDRProfile       (3)     -- 'Dial. Norm. and DR Profile'
    }

Enc1E100enumObj ::= TEXTUAL-CONVENTION
    STATUS current
    DESCRIPTION
    "EnumObj"
    SYNTAX INTEGER {
        v0-notPresent                 (0),    -- 'Not Present'
        v1-present                    (1),    -- 'Present'
        v2-pcmpresent                 (2),    -- 'PCM Present'
        v3-dataPresentAVLocked        (3),    -- 'Data Present, AV Locked'
        v4-dataPresentNotAVLocked     (4)     -- 'Data Present, Not AV Locked'
    }

Enc1E101enumObj ::= TEXTUAL-CONVENTION
    STATUS current
    DESCRIPTION
    "EnumObj"
    SYNTAX INTEGER {
        v0-notPresent                 (0),    -- 'Not Present'
        v1-present                    (1),    -- 'Present'
        v2-pcmpresent                 (2),    -- 'PCM Present'
        v3-dataPresent                (3)     -- 'Data Present'
    }

Enc1E102enumObj ::= TEXTUAL-CONVENTION
    STATUS current
    DESCRIPTION
    "EnumObj"
    SYNTAX INTEGER {
        v0-unknownorUnavailable       (0),    -- 'Unknown or Unavailable'
        v1-48KHz                      (1),    -- '48 KHz'
        v2-441KHz                     (2),    -- '44.1 KHz'
        v3-32KHz                      (3)     -- '32 KHz'
    }

Enc1E103enumObj ::= TEXTUAL-CONVENTION
    STATUS current
    DESCRIPTION
    "EnumObj"
    SYNTAX INTEGER {
        v0-none                       (0),    -- 'None'
        v1-serial1                    (1),    -- 'Serial 1'
        v2-serial2                    (2),    -- 'Serial 2'
        v3-lastReceived               (3),    -- 'Last Received'
        v4-internal                   (4),    -- 'Internal'
        v5-generator1                 (5),    -- 'Generator 1'
        v6-generator2                 (6),    -- 'Generator 2'
        v7-vanc                       (7),    -- 'VANC'
        v8-aap1                       (8)     -- 'AAP 1'
    }

Enc1E104enumObj ::= TEXTUAL-CONVENTION
    STATUS current
    DESCRIPTION
    "EnumObj"
    SYNTAX INTEGER {
        v0-noError                    (0),    -- 'No Error'
        v1-noExternalData             (1),    -- 'No External Data'
        v2-noMetadataPreamble         (2),    -- 'No Metadata Preamble'
        v3-parseError                 (3),    -- 'Parse Error'
        v4-acmodConfiguredModeMismatch(4),    -- 'ACMod Configured Mode Mismatch'
        v5-acmodConfiguredBitrateMismatch(5),    -- 'ACMod Configured Bitrate Mismatch'
        v6-programNotFound            (6),    -- 'Program Not Found'
        v7-programConfigNumberofChannelsMismatch(7)     -- 'Program Config Number of Channels Mismatch'
    }

Enc1E105enumObj ::= TEXTUAL-CONVENTION
    STATUS current
    DESCRIPTION
    "EnumObj"
    SYNTAX INTEGER {
        v0-48KHz                      (0),    -- '48 KHz'
        v1-32KHz                      (1)     -- '32 KHz'
    }

Enc1E106enumObj ::= TEXTUAL-CONVENTION
    STATUS current
    DESCRIPTION
    "EnumObj"
    SYNTAX INTEGER {
        v0-v1498                      (0)     -- 'V1.4.9.8'
    }

Enc1E107enumObj ::= TEXTUAL-CONVENTION
    STATUS current
    DESCRIPTION
    "EnumObj"
    SYNTAX INTEGER {
        v0-close-In                   (0),    -- 'Close-In'
        v1-close-In-Out               (1),    -- 'Close-In-Out'
        v2-close-Out                  (2),    -- 'Close-Out'
        v3-open-In                    (3),    -- 'Open-In'
        v4-open-In-Out                (4),    -- 'Open-In-Out'
        v5-open-Out                   (5)     -- 'Open-Out'
    }

Enc1E108enumObj ::= TEXTUAL-CONVENTION
    STATUS current
    DESCRIPTION
    "EnumObj"
    SYNTAX INTEGER {
        v0-none                       (0),    -- 'None'
        v1-gpi-1                      (1),    -- 'GPI-1'
        v2-gpi-2                      (2),    -- 'GPI-2'
        v3-gpi-3                      (3),    -- 'GPI-3'
        v4-gpi-4                      (4),    -- 'GPI-4'
        v5-ip                         (5),    -- 'IP'
        v6-vanc                       (6)     -- 'vanc'
    }

Enc1E109enumObj ::= TEXTUAL-CONVENTION
    STATUS current
    DESCRIPTION
    "EnumObj"
    SYNTAX INTEGER {
        v0-off                        (0),    -- 'Off'
        v1-outofNetwork               (1),    -- 'Out of Network'
        v2-intoNetwork                (2),    -- 'In to Network'
        v3-both                       (3)     -- 'Both'
    }

Enc1E110enumObj ::= TEXTUAL-CONVENTION
    STATUS current
    DESCRIPTION
    "EnumObj"
    SYNTAX INTEGER {
        v0-dual                       (0),    -- 'Dual'
        v1-etsien300472               (1),    -- 'ETSI EN 300 472'
        v2-etsien301775               (2)     -- 'ETSI EN 301 775'
    }

Enc1E111enumObj ::= TEXTUAL-CONVENTION
    STATUS current
    DESCRIPTION
    "EnumObj"
    SYNTAX INTEGER {
        v0-none                       (0),    -- 'None'
        v1-dvitcscte127               (1),    -- 'DVITC (SCTE 127)'
        v2-lossless                   (2),    -- 'Lossless'
        v3-wst                        (3),    -- 'WST'
        v4-closedCaption              (4),    -- 'Closed Caption'
        v5-wss                        (5),    -- 'WSS'
        v6-amol48SCTE127              (6),    -- 'AMOL48 (SCTE 127)'
        v7-amol96SCTE127              (7),    -- 'AMOL96 (SCTE 127)'
        v8-vps                        (8),    -- 'VPS'
        v9-invertedTeletext           (9),    -- 'Inverted Teletext'
        v10-dvitclegacy               (10)     -- 'DVITC (legacy)'
    }

Enc1E112enumObj ::= TEXTUAL-CONVENTION
    STATUS current
    DESCRIPTION
    "EnumObj"
    SYNTAX INTEGER {
        v0-none                       (0),    -- 'None'
        v1-dvitcscte127               (1),    -- 'DVITC (SCTE 127)'
        v2-lossless                   (2),    -- 'Lossless'
        v3-wst                        (3),    -- 'WST'
        v4-closedCaption              (4),    -- 'Closed Caption'
        v5-wss                        (5),    -- 'WSS'
        v6-amol48SCTE127              (6),    -- 'AMOL 48 (SCTE 127)'
        v7-amol96SCTE127              (7),    -- 'AMOL 96 (SCTE 127)'
        v8-vps                        (8),    -- 'VPS'
        v9-invertedTeletext           (9),    -- 'Inverted Teletext'
        v10-dvitclegacy               (10)     -- 'DVITC (legacy)'
    }

Enc1E113enumObj ::= TEXTUAL-CONVENTION
    STATUS current
    DESCRIPTION
    "EnumObj"
    SYNTAX INTEGER {
        v0-none                       (0),    -- 'none'
        v1-ntsc75PercentColorbars     (1),    -- 'Ntsc 75% Colorbars'
        v2-ntsc100PercentColorbars    (2),    -- 'Ntsc 100% Colorbars'
        v3-ntscCombination            (3),    -- 'Ntsc Combination'
        v4-ntscComposite              (4),    -- 'Ntsc Composite'
        v5-ntscFlat                   (5),    -- 'Ntsc Flat'
        v6-ntscRamp                   (6),    -- 'Ntsc Ramp'
        v7-ntscMatrix                 (7),    -- 'Ntsc Matrix'
        v8-ntscSinx                   (8),    -- 'Ntsc Sinx'
        v9-ntscSquare                 (9),    -- 'Ntsc Square'
        v10-palCCIR17                 (10),    -- 'Pal CCIR17'
        v11-palCCIR18                 (11),    -- 'Pal CCIR18'
        v12-palCCIR330                (12),    -- 'Pal CCIR330'
        v13-palCCIR331                (13),    -- 'Pal CCIR331'
        v14-pal75PercentColorbars     (14),    -- 'Pal 75% Colorbars'
        v15-pal100PercentColorbars    (15),    -- 'Pal 100% Colorbars'
        v16-palFlat                   (16),    -- 'Pal Flat'
        v17-palMatrix                 (17),    -- 'Pal Matrix'
        v18-palRamp                   (18),    -- 'Pal Ramp'
        v19-palSinx                   (19),    -- 'Pal Sinx'
        v20-palSquare                 (20),    -- 'Pal Square'
        v21-ntscEq                    (21),    -- 'Ntsc Eq'
        v22-ntscPll                   (22),    -- 'Ntsc Pll'
        v23-palEq                     (23),    -- 'Pal Eq'
        v24-palITS1                   (24),    -- 'Pal ITS1'
        v25-palITS2                   (25),    -- 'Pal ITS2'
        v26-palPll                    (26)     -- 'Pal Pll'
    }

Enc1E114enumObj ::= TEXTUAL-CONVENTION
    STATUS current
    DESCRIPTION
    "EnumObj"
    SYNTAX INTEGER {
        v0-none                       (0),    -- 'None'
        v1-0-AfdUnknown               (1),    -- '0-Afd Unknown'
        v2-1-Reserved                 (2),    -- '1-Reserved'
        v3-2-Box169top                (3),    -- '2-Box 16:9 (top)'
        v4-3-Box149top                (4),    -- '3-Box 14:9 (top)'
        v5-4-BoxGreaterThan169center  (5),    -- '4-Box > 16:9 (center)'
        v6-5-Reserved                 (6),    -- '5-Reserved'
        v7-6-Reserved                 (7),    -- '6-Reserved'
        v8-7-Reserved                 (8),    -- '7-Reserved'
        v9-8-Activeformatissameascodedpicture(9),    -- '8-Active format is same as coded picture'
        v10-9-43center                (10),    -- '9-4:3 (center)'
        v11-10-169center              (11),    -- '10-16:9 (center)'
        v12-11-149center              (12),    -- '11-14:9 (center)'
        v13-12-Reserved               (13),    -- '12-Reserved'
        v14-13-43withshootprotect149center(14),    -- '13-4:3 (with shoot protect 14:9 center)'
        v15-14-169withshootprotect149center(15),    -- '14-16:9 (with shoot protect 14:9 center)'
        v16-15-169withshootprotect43center(16),    -- '15-16:9 (with shoot protect 4:3 center)'
        v17-drop                      (17),    -- 'Drop'
        v18-bbc-b6                    (18)     -- 'BBC-b6'
    }

Enc1E115enumObj ::= TEXTUAL-CONVENTION
    STATUS current
    DESCRIPTION
    "EnumObj"
    SYNTAX INTEGER {
        v0-none                       (0),    -- 'None'
        v1-vanc                       (1),    -- 'VANC'
        v2-vbi                        (2),    -- 'VBI'
        v3-udp                        (3),    -- 'UDP'
        v4-serial-1                   (4),    -- 'Serial-1'
        v5-serial-2                   (5)     -- 'Serial-2'
    }

Enc1E116enumObj ::= TEXTUAL-CONVENTION
    STATUS current
    DESCRIPTION
    "EnumObj"
    SYNTAX INTEGER {
        v0-vanc                       (0),    -- 'VANC'
        v1-esd-From-Captions          (1)     -- 'ESD-From-Captions'
    }

Enc1E117enumObj ::= TEXTUAL-CONVENTION
    STATUS current
    DESCRIPTION
    "EnumObj"
    SYNTAX INTEGER {
        v0-none                       (0),    -- 'None'
        v1-udp                        (1)     -- 'UDP'
    }

Enc1E118enumObj ::= TEXTUAL-CONVENTION
    STATUS current
    DESCRIPTION
    "EnumObj"
    SYNTAX INTEGER {
        v0-always                     (0),    -- 'Always'
        v1-as-Needed                  (1),    -- 'As-Needed'
        v2-none                       (2)     -- 'None'
    }

Enc1E119enumObj ::= TEXTUAL-CONVENTION
    STATUS current
    DESCRIPTION
    "EnumObj"
    SYNTAX INTEGER {
        v0-always                     (0),    -- 'Always'
        v1-as-Needed                  (1),    -- 'As-Needed'
        v2-none                       (2)     -- 'None'
    }

Enc1E120enumObj ::= TEXTUAL-CONVENTION
    STATUS current
    DESCRIPTION
    "EnumObj"
    SYNTAX INTEGER {
        v0-608                        (0),    -- '608'
        v1-708                        (1)     -- '708'
    }

Enc1E121enumObj ::= TEXTUAL-CONVENTION
    STATUS current
    DESCRIPTION
    "EnumObj"
    SYNTAX INTEGER {
        v0-easyReaderOff              (0),    -- 'EasyReader Off'
        v1-easyReaderOn               (1)     -- 'EasyReader On'
    }

Enc1E122enumObj ::= TEXTUAL-CONVENTION
    STATUS current
    DESCRIPTION
    "EnumObj"
    SYNTAX INTEGER {
        v0-43                         (0),    -- '4:3'
        v1-169                        (1)     -- '16:9'
    }

Enc1E123enumObj ::= TEXTUAL-CONVENTION
    STATUS current
    DESCRIPTION
    "EnumObj"
    SYNTAX INTEGER {
        v0-none                       (0),    -- 'None'
        v1-udp                        (1),    -- 'UDP'
        v2-serial-1                   (2),    -- 'Serial-1'
        v3-serial-2                   (3)     -- 'Serial-2'
    }

Enc1E124enumObj ::= TEXTUAL-CONVENTION
    STATUS current
    DESCRIPTION
    "EnumObj"
    SYNTAX INTEGER {
        v0-smpte-2038                 (0),    -- 'SMPTE-2038'
        v1-rdd-11                     (1)     -- 'RDD-11'
    }

Enc1E125enumObj ::= TEXTUAL-CONVENTION
    STATUS current
    DESCRIPTION
    "EnumObj"
    SYNTAX INTEGER {
        v0-none                       (0),    -- 'None'
        v1-activeFormatDescription    (1),    -- 'Active Format Description'
        v2-ancillaryTimeCode          (2),    -- 'Ancillary Time Code'
        v3-closedCaptionsEIA-608      (3),    -- 'Closed Captions (EIA-608)'
        v4-closedCaptionsEIA-708      (4),    -- 'Closed Captions (EIA-708)'
        v5-dolbyAudioMetadata         (5),    -- 'Dolby Audio Metadata'
        v6-filmCodes                  (6),    -- 'Film Codes'
        v7-klvencodedMetadata         (7),    -- 'KLV Encoded Metadata'
        v8-payloadIdentification      (8),    -- 'Payload Identification'
        v9-programDescription         (9),    -- 'Program Description'
        v10-scte-104Splicing          (10),    -- 'SCTE-104 Splicing'
        v11-vbidata                   (11),    -- 'VBI Data'
        v12-broadcastFlag             (12),    -- 'Broadcast Flag'
        v13-broadcastAlertSystem      (13),    -- 'Broadcast Alert System'
        v14-localIDentificationInsertedAutomatically(14)     -- 'Local IDentification Inserted Automatically'
    }

Enc1E126enumObj ::= TEXTUAL-CONVENTION
    STATUS current
    DESCRIPTION
    "EnumObj"
    SYNTAX INTEGER {
        v0-ntp                        (0),    -- 'NTP'
        v1-vitc                       (1),    -- 'VITC'
        v2-vanc                       (2)     -- 'VANC'
    }

Enc1E127enumObj ::= TEXTUAL-CONVENTION
    STATUS current
    DESCRIPTION
    "EnumObj"
    SYNTAX INTEGER {
        v0-none                       (0),    -- 'None'
        v1-user-Data                  (1),    -- 'User-Data'
        v2-pid                        (2),    -- 'PID'
        v3-both                       (3)     -- 'Both'
    }

Enc1E128enumObj ::= TEXTUAL-CONVENTION
    STATUS current
    DESCRIPTION
    "EnumObj"
    SYNTAX INTEGER {
        v0-none                       (0),    -- 'None'
        v1-op47                       (1),    -- 'OP47'
        v2-smpte-2031                 (2)     -- 'SMPTE-2031'
    }

Enc1E129enumObj ::= TEXTUAL-CONVENTION
    STATUS current
    DESCRIPTION
    "EnumObj"
    SYNTAX INTEGER {
        v0-mpeg                       (0),    -- 'MPEG'
        v1-dvb                        (1),    -- 'DVB'
        v2-atsc                       (2),    -- 'ATSC'
        v3-isdb                       (3)     -- 'ISDB'
    }

Enc1E130enumObj ::= TEXTUAL-CONVENTION
    STATUS current
    DESCRIPTION
    "EnumObj"
    SYNTAX INTEGER {
        v0-none                       (0),    -- 'None'
        v1-biss                       (1),    -- 'BISS'
        v2-biss-E                     (2)     -- 'BISS-E'
    }

Enc1E131enumObj ::= TEXTUAL-CONVENTION
    STATUS current
    DESCRIPTION
    "EnumObj"
    SYNTAX INTEGER {
        v0-none                       (0),    -- 'None'
        v1-main                       (1),    -- 'Main'
        v2-pip                        (2)     -- 'PIP'
    }

Enc1E132enumObj ::= TEXTUAL-CONVENTION
    STATUS current
    DESCRIPTION
    "EnumObj"
    SYNTAX INTEGER {
        v0-off                        (0),    -- 'Off'
        v1-auto                       (1),    -- 'Auto'
        v2-10BaseT                    (2),    -- '10BaseT'
        v3-100BaseT                   (3),    -- '100BaseT'
        v4-1000BaseT                  (4)     -- '1000BaseT'
    }

Enc1E133enumObj ::= TEXTUAL-CONVENTION
    STATUS current
    DESCRIPTION
    "EnumObj"
    SYNTAX INTEGER {
        v0-present                    (0),    -- 'Present'
        v1-missing                    (1)     -- 'Missing'
    }

Enc1E134enumObj ::= TEXTUAL-CONVENTION
    STATUS current
    DESCRIPTION
    "EnumObj"
    SYNTAX INTEGER {
        v0-lost                       (0),    -- 'Lost'
        v1-neg                        (1),    -- 'Neg'
        v2-10H                        (2),    -- '10H'
        v3-10F                        (3),    -- '10F'
        v4-100H                       (4),    -- '100H'
        v5-100F                       (5),    -- '100F'
        v6-1000                       (6)     -- '1000'
    }

Enc1E135enumObj ::= TEXTUAL-CONVENTION
    STATUS current
    DESCRIPTION
    "EnumObj"
    SYNTAX INTEGER {
        v0-working                    (0),    -- 'Working'
        v1-unreachable                (1),    -- 'Unreachable'
        v2-noArp                      (2),    -- 'NoArp'
        v3-ttlexceeded                (3),    -- 'TTLExceeded'
        v4-sourceQuench               (4)     -- 'SourceQuench'
    }

Enc1E136enumObj ::= TEXTUAL-CONVENTION
    STATUS current
    DESCRIPTION
    "EnumObj"
    SYNTAX INTEGER {
        v0-sys                        (0),    -- 'Sys'
        v1-vif1                       (1),    -- 'Vif1'
        v2-vif2                       (2),    -- 'Vif2'
        v3-vif3                       (3),    -- 'Vif3'
        v4-vif4                       (4),    -- 'Vif4'
        v5-vif5                       (5),    -- 'Vif5'
        v6-vif6                       (6),    -- 'Vif6'
        v7-vif7                       (7),    -- 'Vif7'
        v8-vif8                       (8)     -- 'Vif8'
    }

Enc1E137enumObj ::= TEXTUAL-CONVENTION
    STATUS current
    DESCRIPTION
    "EnumObj"
    SYNTAX INTEGER {
        v0-tsonUDP                    (0),    -- 'TS on UDP'
        v1-tsonRTP                    (1),    -- 'TS on RTP'
        v2-rtp-RTCP                   (2)     -- 'RTP-RTCP'
    }

Enc1E138enumObj ::= TEXTUAL-CONVENTION
    STATUS current
    DESCRIPTION
    "EnumObj"
    SYNTAX INTEGER {
        v0-none                       (0),    -- 'None'
        v1-low                        (1),    -- 'Low'
        v2-medium                     (2),    -- 'Medium'
        v3-high                       (3),    -- 'High'
        v4-custom                     (4)     -- 'Custom'
    }

Enc1E139enumObj ::= TEXTUAL-CONVENTION
    STATUS current
    DESCRIPTION
    "EnumObj"
    SYNTAX INTEGER {
        v0-generic                    (0),    -- 'Generic'
        v1-nagra                      (1)     -- 'Nagra'
    }

Enc1E140enumObj ::= TEXTUAL-CONVENTION
    STATUS current
    DESCRIPTION
    "EnumObj"
    SYNTAX INTEGER {
        v0-off                        (0),    -- 'Off'
        v1-fixedKey                   (1),    -- 'Fixed Key'
        v2-simulcrypt                 (2)     -- 'Simulcrypt'
    }

Enc1E141enumObj ::= TEXTUAL-CONVENTION
    STATUS current
    DESCRIPTION
    "EnumObj"
    SYNTAX INTEGER {
        v0-nonBlockAligned            (0),    -- 'Non Block Aligned'
        v1-blockAligned               (1)     -- 'Block Aligned'
    }

Enc1E142enumObj ::= TEXTUAL-CONVENTION
    STATUS current
    DESCRIPTION
    "EnumObj"
    SYNTAX INTEGER {
        v0-both                       (0),    -- 'Both'
        v1-activeController           (1)     -- 'Active Controller'
    }

Enc1E143enumObj ::= TEXTUAL-CONVENTION
    STATUS current
    DESCRIPTION
    "EnumObj"
    SYNTAX INTEGER {
        v0-both                       (0),    -- 'Both'
        v1-activeController           (1)     -- 'Active Controller'
    }

Enc1E144enumObj ::= TEXTUAL-CONVENTION
    STATUS current
    DESCRIPTION
    "EnumObj"
    SYNTAX INTEGER {
        v0-none                       (0),    -- 'None'
        v1-m1UpMix                    (1),    -- 'M1: UpMix'
        v2-m2DownMix                  (2),    -- 'M2: DownMix'
        v3-m3MultiMerge               (3),    -- 'M3: MultiMerge'
        v4-m4LoudnessControl20        (4),    -- 'M4: Loudness Control 2.0'
        v5-m5LoudnessControl51        (5),    -- 'M5: Loudness Control 5.1'
        v6-m6LoudnessControl4x20      (6),    -- 'M6: Loudness Control 4x2.0'
        v7-m7DolbyDigitalDecodewithDownMix(7),    -- 'M7: Dolby Digital Decode with DownMix'
        v8-m8DolbyEDecode             (8),    -- 'M8: Dolby E Decode'
        v9-m9DolbyEDigitalDecodewithDownMix(9),    -- 'M9: Dolby E/Digital Decode with DownMix'
        v10-m10DolbyDigitalEncode     (10),    -- 'M10: Dolby Digital Encode'
        v11-m11DolbyEEncode           (11),    -- 'M11: Dolby E Encode'
        v12-m12MultiMergeLoudnessControl(12),    -- 'M12: MultiMerge, Loudness Control'
        v13-m13UpMixLoudnessControl   (13),    -- 'M13: UpMix, Loudness Control'
        v14-m14DownMixLoudnessControl (14),    -- 'M14: DownMix, Loudness Control'
        v15-m15LoudnessControl51Plus20(15),    -- 'M15: Loudness Control 5.1+2.0'
        v16-m16LoudnessControl2x10    (16),    -- 'M16: Loudness Control 2x1.0'
        v17-m17LoudnessControlPlusDDEncode51(17),    -- 'M17: Loudness Control + DD Encode 5.1'
        v18-m18LoudnessControlPlusDEEncode51Plus20(18),    -- 'M18: Loudness Control + DE Encode 5.1+2.0'
        v19-m19LoudnessControlPlusDEEncode4x20(19),    -- 'M19: Loudness Control + DE Encode 4x2.0'
        v20-m20DolbyDigitalDecPlusMultiMerge(20),    -- 'M20: Dolby Digital Dec + MultiMerge'
        v21-m21DolbyEDecPlusMultiMerge(21),    -- 'M21: Dolby E Dec + MultiMerge'
        v22-m22DEDDDecPlusMultiMerge  (22),    -- 'M22: DE/DD Dec + MultiMerge'
        v23-multiMergeLoudnessControlDolbyEEncode(23),    -- 'MultiMerge, Loudness Control, Dolby E Encode'
        v24-multiMergeLoudnessControlDolbyDigitalEncode(24),    -- 'MultiMerge, Loudness Control, Dolby Digital Encode'
        v25-dolbyDigitalDecodeLoudnessControlDolbyDigitalEncode(25),    -- 'Dolby Digital Decode, Loudness Control, Dolby Digital Encode'
        v26-dolbyEDecodeLoudnessControlDolbyDigitalEncode(26),    -- 'Dolby E Decode, Loudness Control, Dolby Digital Encode'
        v27-dolbyEDecodeLoudnessControlDolbyEEncode(27),    -- 'Dolby E Decode, Loudness Control, Dolby E Encode'
        v28-dolbyDigitalDecodeLoudnessControlMultiMergeDolbyDigitalEnco(28),    -- 'Dolby Digital Decode, Loudness Control, MultiMerge, Dolby Digital Encode'
        v29-dolbyEDecodeLoudnessControlMultiMergeDolbyDigitalEncode(29),    -- 'Dolby E Decode, Loudness Control, MultiMerge, Dolby Digital Encode'
        v30-dolbyEDecodeLoudnessControlMultiMergeDolbyEEncode(30),    -- 'Dolby E Decode, Loudness Control, MultiMerge, Dolby E Encode'
        v31-dolbyEDecodeSAPLoudnessControlDolbyEEncode(31)     -- 'Dolby E Decode, SAP Loudness Control, Dolby E Encode'
    }

Enc1E145enumObj ::= TEXTUAL-CONVENTION
    STATUS current
    DESCRIPTION
    "EnumObj"
    SYNTAX INTEGER {
        v0-0                          (0),    -- '0'
        v1-0                          (1),    -- '0'
        v2-0                          (2),    -- '0'
        v3-0                          (3),    -- '0'
        v4-0                          (4),    -- '0'
        v5-0                          (5),    -- '0'
        v6-0                          (6),    -- '0'
        v7-0                          (7),    -- '0'
        v8-0                          (8),    -- '0'
        v9-0                          (9),    -- '0'
        v10-0                         (10),    -- '0'
        v11-1                         (11),    -- '1'
        v12-0                         (12),    -- '0'
        v13-0                         (13),    -- '0'
        v14-0                         (14),    -- '0'
        v15-0                         (15),    -- '0'
        v16-0                         (16),    -- '0'
        v17-0                         (17),    -- '0'
        v18-1                         (18),    -- '1'
        v19-1                         (19),    -- '1'
        v20-0                         (20),    -- '0'
        v21-0                         (21),    -- '0'
        v22-0                         (22)     -- '0'
    }

Enc1E146enumObj ::= TEXTUAL-CONVENTION
    STATUS current
    DESCRIPTION
    "EnumObj"
    SYNTAX INTEGER {
        v0-0                          (0),    -- '0'
        v1-0                          (1),    -- '0'
        v2-0                          (2),    -- '0'
        v3-0                          (3),    -- '0'
        v4-0                          (4),    -- '0'
        v5-0                          (5),    -- '0'
        v6-0                          (6),    -- '0'
        v7-0                          (7),    -- '0'
        v8-1                          (8),    -- '1'
        v9-1                          (9),    -- '1'
        v10-0                         (10),    -- '0'
        v11-0                         (11),    -- '0'
        v12-0                         (12),    -- '0'
        v13-0                         (13),    -- '0'
        v14-0                         (14),    -- '0'
        v15-0                         (15),    -- '0'
        v16-0                         (16),    -- '0'
        v17-0                         (17),    -- '0'
        v18-0                         (18),    -- '0'
        v19-0                         (19),    -- '0'
        v20-0                         (20),    -- '0'
        v21-1                         (21),    -- '1'
        v22-1                         (22)     -- '1'
    }

Enc1E147enumObj ::= TEXTUAL-CONVENTION
    STATUS current
    DESCRIPTION
    "EnumObj"
    SYNTAX INTEGER {
        v0-0                          (0),    -- '0'
        v1-0                          (1),    -- '0'
        v2-0                          (2),    -- '0'
        v3-0                          (3),    -- '0'
        v4-0                          (4),    -- '0'
        v5-0                          (5),    -- '0'
        v6-0                          (6),    -- '0'
        v7-0                          (7),    -- '0'
        v8-0                          (8),    -- '0'
        v9-0                          (9),    -- '0'
        v10-1                         (10),    -- '1'
        v11-0                         (11),    -- '0'
        v12-0                         (12),    -- '0'
        v13-0                         (13),    -- '0'
        v14-0                         (14),    -- '0'
        v15-0                         (15),    -- '0'
        v16-0                         (16),    -- '0'
        v17-1                         (17),    -- '1'
        v18-0                         (18),    -- '0'
        v19-0                         (19),    -- '0'
        v20-0                         (20),    -- '0'
        v21-0                         (21),    -- '0'
        v22-0                         (22)     -- '0'
    }

Enc1E148enumObj ::= TEXTUAL-CONVENTION
    STATUS current
    DESCRIPTION
    "EnumObj"
    SYNTAX INTEGER {
        v0-0                          (0),    -- '0'
        v1-0                          (1),    -- '0'
        v2-0                          (2),    -- '0'
        v3-0                          (3),    -- '0'
        v4-0                          (4),    -- '0'
        v5-0                          (5),    -- '0'
        v6-0                          (6),    -- '0'
        v7-1                          (7),    -- '1'
        v8-0                          (8),    -- '0'
        v9-1                          (9),    -- '1'
        v10-0                         (10),    -- '0'
        v11-0                         (11),    -- '0'
        v12-0                         (12),    -- '0'
        v13-0                         (13),    -- '0'
        v14-0                         (14),    -- '0'
        v15-0                         (15),    -- '0'
        v16-0                         (16),    -- '0'
        v17-0                         (17),    -- '0'
        v18-0                         (18),    -- '0'
        v19-0                         (19),    -- '0'
        v20-1                         (20),    -- '1'
        v21-0                         (21),    -- '0'
        v22-1                         (22)     -- '1'
    }

Enc1E149enumObj ::= TEXTUAL-CONVENTION
    STATUS current
    DESCRIPTION
    "EnumObj"
    SYNTAX INTEGER {
        v0-0                          (0),    -- '0'
        v1-3                          (1),    -- '3'
        v2-3                          (2),    -- '3'
        v3-4                          (3),    -- '4'
        v4-1                          (4),    -- '1'
        v5-3                          (5),    -- '3'
        v6-4                          (6),    -- '4'
        v7-0                          (7),    -- '0'
        v8-0                          (8),    -- '0'
        v9-0                          (9),    -- '0'
        v10-0                         (10),    -- '0'
        v11-0                         (11),    -- '0'
        v12-8                         (12),    -- '8'
        v13-4                         (13),    -- '4'
        v14-4                         (14),    -- '4'
        v15-4                         (15),    -- '4'
        v16-1                         (16),    -- '1'
        v17-3                         (17),    -- '3'
        v18-4                         (18),    -- '4'
        v19-4                         (19),    -- '4'
        v20-4                         (20),    -- '4'
        v21-4                         (21),    -- '4'
        v22-4                         (22)     -- '4'
    }

Enc1E150enumObj ::= TEXTUAL-CONVENTION
    STATUS current
    DESCRIPTION
    "EnumObj"
    SYNTAX INTEGER {
        v0-0Percent                   (0),    -- '0%'
        v1-38Percent                  (1),    -- '38%'
        v2-13Percent                  (2),    -- '13%'
        v3-50Percent                  (3),    -- '50%'
        v4-14Percent                  (4),    -- '14%'
        v5-25Percent                  (5),    -- '25%'
        v6-44Percent                  (6),    -- '44%'
        v7-22Percent                  (7),    -- '22%'
        v8-35Percent                  (8),    -- '35%'
        v9-35Percent                  (9),    -- '35%'
        v10-44Percent                 (10),    -- '44%'
        v11-46Percent                 (11),    -- '46%'
        v12-71Percent                 (12),    -- '71%'
        v13-50Percent                 (13),    -- '50%'
        v14-19Percent                 (14),    -- '19%'
        v15-34Percent                 (15),    -- '34%'
        v16-20Percent                 (16),    -- '20%'
        v17-57Percent                 (17),    -- '57%'
        v18-77Percent                 (18),    -- '77%'
        v19-88Percent                 (19),    -- '88%'
        v20-88Percent                 (20),    -- '88%'
        v21-88Percent                 (21),    -- '88%'
        v22-88Percent                 (22)     -- '88%'
    }

Enc1E151enumObj ::= TEXTUAL-CONVENTION
    STATUS current
    DESCRIPTION
    "EnumObj"
    SYNTAX INTEGER {
        v0-32                         (0),    -- '32'
        v1-40                         (1),    -- '40'
        v2-48                         (2),    -- '48'
        v3-56                         (3),    -- '56'
        v4-64                         (4),    -- '64'
        v5-80                         (5),    -- '80'
        v6-96                         (6),    -- '96'
        v7-112                        (7),    -- '112'
        v8-128                        (8),    -- '128'
        v9-160                        (9),    -- '160'
        v10-192                       (10),    -- '192'
        v11-224                       (11),    -- '224'
        v12-256                       (12),    -- '256'
        v13-320                       (13),    -- '320'
        v14-384                       (14),    -- '384'
        v15-448                       (15),    -- '448'
        v16-512                       (16),    -- '512'
        v17-576                       (17),    -- '576'
        v18-640                       (18),    -- '640'
        v19-reserved                  (19),    -- 'Reserved'
        v20-reserved                  (20),    -- 'Reserved'
        v21-reserved                  (21),    -- 'Reserved'
        v22-reserved                  (22),    -- 'Reserved'
        v23-reserved                  (23),    -- 'Reserved'
        v24-reserved                  (24),    -- 'Reserved'
        v25-reserved                  (25),    -- 'Reserved'
        v26-reserved                  (26),    -- 'Reserved'
        v27-reserved                  (27),    -- 'Reserved'
        v28-reserved                  (28),    -- 'Reserved'
        v29-reserved                  (29),    -- 'Reserved'
        v30-reserved                  (30),    -- 'Reserved'
        v31-notSpecified              (31)     -- 'Not Specified'
    }

Enc1E152enumObj ::= TEXTUAL-CONVENTION
    STATUS current
    DESCRIPTION
    "EnumObj"
    SYNTAX INTEGER {
        v0-disable                    (0),    -- 'Disable'
        v1-enable                     (1)     -- 'Enable'
    }

Enc1E153enumObj ::= TEXTUAL-CONVENTION
    STATUS current
    DESCRIPTION
    "EnumObj"
    SYNTAX INTEGER {
        v0-na                         (0),    -- 'NA'
        v1-10C                        (1),    -- '1/0 (C)'
        v2-20LR                       (2),    -- '2/0 (L,R)'
        v3-30LCR                      (3),    -- '3/0 (L,C,R)'
        v4-21LRS                      (4),    -- '2/1 (L,R,S)'
        v5-31LCRS                     (5),    -- '3/1 (L,C,R,S)'
        v6-22LRLsRs                   (6),    -- '2/2 (L,R,Ls,Rs)'
        v7-32LCRLsRs                  (7)     -- '3/2 (L,C,R,Ls,Rs)'
    }

Enc1E154enumObj ::= TEXTUAL-CONVENTION
    STATUS current
    DESCRIPTION
    "EnumObj"
    SYNTAX INTEGER {
        v0-off                        (0),    -- 'Off'
        v1-on                         (1)     -- 'On'
    }

Enc1E155enumObj ::= TEXTUAL-CONVENTION
    STATUS current
    DESCRIPTION
    "EnumObj"
    SYNTAX INTEGER {
        v0-none                       (0),    -- 'None'
        v1-filmStandard               (1),    -- 'Film Standard'
        v2-filmLight                  (2),    -- 'Film Light'
        v3-musicStandard              (3),    -- 'Music Standard'
        v4-musicLight                 (4),    -- 'Music Light'
        v5-speech                     (5)     -- 'Speech'
    }

Enc1E156enumObj ::= TEXTUAL-CONVENTION
    STATUS current
    DESCRIPTION
    "EnumObj"
    SYNTAX INTEGER {
        v0-no                         (0),    -- 'No'
        v1-yes                        (1)     -- 'Yes'
    }

Enc1E157enumObj ::= TEXTUAL-CONVENTION
    STATUS current
    DESCRIPTION
    "EnumObj"
    SYNTAX INTEGER {
        v0-completeMain               (0),    -- 'Complete Main'
        v1-musicandEffects            (1),    -- 'Music and Effects'
        v2-visuallyImpaired           (2),    -- 'Visually Impaired'
        v3-hearingImpaired            (3),    -- 'Hearing Impaired'
        v4-dialogue                   (4),    -- 'Dialogue'
        v5-commentary                 (5),    -- 'Commentary'
        v6-emergency                  (6),    -- 'Emergency'
        v7-voiceOver                  (7),    -- 'Voice Over'
        v8-karaoke                    (8)     -- 'Karaoke'
    }

Enc1E158enumObj ::= TEXTUAL-CONVENTION
    STATUS current
    DESCRIPTION
    "EnumObj"
    SYNTAX INTEGER {
        v0-notIndicated               (0),    -- 'Not Indicated'
        v1-no                         (1),    -- 'No'
        v2-yes                        (2),    -- 'Yes'
        v3-reserved                   (3)     -- 'Reserved'
    }

Enc1E159enumObj ::= TEXTUAL-CONVENTION
    STATUS current
    DESCRIPTION
    "EnumObj"
    SYNTAX INTEGER {
        v0-notIndicated               (0),    -- 'Not Indicated'
        v1-no                         (1),    -- 'No'
        v2-yes                        (2),    -- 'Yes'
        v3-reserved                   (3)     -- 'Reserved'
    }

Enc1E160enumObj ::= TEXTUAL-CONVENTION
    STATUS current
    DESCRIPTION
    "EnumObj"
    SYNTAX INTEGER {
        v0-notIndicated               (0),    -- 'Not Indicated'
        v1-ltRtPreferred              (1),    -- 'LtRt Preferred'
        v2-loRoPreferred              (2),    -- 'LoRo Preferred'
        v3-reserved                   (3)     -- 'Reserved'
    }

Enc1E161enumObj ::= TEXTUAL-CONVENTION
    STATUS current
    DESCRIPTION
    "EnumObj"
    SYNTAX INTEGER {
        v0-plus3dB                    (0),    -- '+3 dB'
        v1-plus15dB                   (1),    -- '+1.5 dB'
        v2-0dB                        (2),    -- '0 dB'
        v3-neg15dB                    (3),    -- '-1.5 dB'
        v4-neg3dB                     (4),    -- '-3 dB'
        v5-neg45dB                    (5),    -- '-4.5 dB'
        v6-neg6dB                     (6),    -- '-6 dB'
        v7-negInfdB                   (7),    -- '-Inf dB'
        v8-reserved                   (8)     -- 'Reserved'
    }

Enc1E162enumObj ::= TEXTUAL-CONVENTION
    STATUS current
    DESCRIPTION
    "EnumObj"
    SYNTAX INTEGER {
        v0-na1                        (0),    -- 'NA1'
        v1-na2                        (1),    -- 'NA2'
        v2-na3                        (2),    -- 'NA3'
        v3-neg15dB                    (3),    -- '-1.5 dB'
        v4-neg3dB                     (4),    -- '-3 dB'
        v5-neg45dB                    (5),    -- '-4.5 dB'
        v6-neg6dB                     (6),    -- '-6 dB'
        v7-negInfdB                   (7),    -- '-Inf dB'
        v8-reserved                   (8)     -- 'Reserved'
    }

Enc1E163enumObj ::= TEXTUAL-CONVENTION
    STATUS current
    DESCRIPTION
    "EnumObj"
    SYNTAX INTEGER {
        v0-standard                   (0),    -- 'Standard'
        v1-hdcd                       (1)     -- 'HDCD'
    }

Enc1E164enumObj ::= TEXTUAL-CONVENTION
    STATUS current
    DESCRIPTION
    "EnumObj"
    SYNTAX INTEGER {
        v0-notIndicated               (0),    -- 'Not Indicated'
        v1-largeRoom                  (1),    -- 'Large Room'
        v2-smallRoom                  (2),    -- 'Small Room'
        v3-reserved                   (3)     -- 'Reserved'
    }

Enc1E165enumObj ::= TEXTUAL-CONVENTION
    STATUS current
    DESCRIPTION
    "EnumObj"
    SYNTAX INTEGER {
        v0-good                       (0),    -- 'Good'
        v1-notEnoughLicCredit         (1),    -- 'Not Enough Lic Credit'
        v2-notEnoughMCPS              (2),    -- 'Not Enough MCPS'
        v3-notEnoughLicandMCPSCredit  (3),    -- 'Not Enough Lic and MCPS Credit'
        v4-test5                      (4),    -- 'test 5'
        v5-test6                      (5),    -- 'test 6'
        v6-test7                      (6),    -- 'test 7'
        v7-test8                      (7),    -- 'test 8'
        v8-test9                      (8),    -- 'test 9'
        v9-test10                     (9)     -- 'test 10'
    }

Enc1E166enumObj ::= TEXTUAL-CONVENTION
    STATUS current
    DESCRIPTION
    "EnumObj"
    SYNTAX INTEGER {
        v0-notEnoughCredit            (0),    -- 'Not Enough Credit'
        v1-good                       (1)     -- 'Good'
    }

Enc1E167enumObj ::= TEXTUAL-CONVENTION
    STATUS current
    DESCRIPTION
    "EnumObj"
    SYNTAX INTEGER {
        v0-non-Dolby                  (0),    -- 'Non-Dolby'
        v1-dolbyDigital16-bit         (1),    -- 'Dolby Digital 16-bit'
        v2-dolbyDigital20-bit         (2),    -- 'Dolby Digital 20-bit'
        v3-dolbyDigital24-bit         (3),    -- 'Dolby Digital 24-bit'
        v4-non-Dolby                  (4),    -- 'Non-Dolby'
        v5-dolbyE16-bit               (5),    -- 'Dolby E 16-bit'
        v6-dolbyE20-bit               (6),    -- 'Dolby E 20-bit'
        v7-dolbyE24-bit               (7),    -- 'Dolby E 24-bit'
        v8-na                         (8),    -- 'N/A'
        v9-dolbyDigitalPlus16-bit     (9),    -- 'Dolby Digital Plus 16-bit'
        v10-dolbyDigitalPlus20-bit    (10),    -- 'Dolby Digital Plus 20-bit'
        v11-dolbyDigitalPlus24-bit    (11)     -- 'Dolby Digital Plus 24-bit'
    }

Enc1E168enumObj ::= TEXTUAL-CONVENTION
    STATUS current
    DESCRIPTION
    "EnumObj"
    SYNTAX INTEGER {
        v0-0707-301dB                 (0),    -- '0.707 (-3.01 dB)'
        v1-0595-452dB                 (1),    -- '0.595 (-4.52 dB)'
        v2-0500-602dB                 (2),    -- '0.500 (-6.02 dB)'
        v3-reserved                   (3)     -- 'Reserved'
    }

Enc1E169enumObj ::= TEXTUAL-CONVENTION
    STATUS current
    DESCRIPTION
    "EnumObj"
    SYNTAX INTEGER {
        v0-0707-301dB                 (0),    -- '0.707 (-3.01 dB)'
        v1-05-602dB                   (1),    -- '0.5 (-6.02 dB)'
        v2-0-InfdB                    (2),    -- '0 (-Inf dB)'
        v3-reserved                   (3)     -- 'Reserved'
    }

Enc1E170enumObj ::= TEXTUAL-CONVENTION
    STATUS current
    DESCRIPTION
    "EnumObj"
    SYNTAX INTEGER {
        v0-51Plus2                    (0),    -- '5.1 + 2'
        v1-51Plus2x1                  (1),    -- '5.1 + 2x1'
        v2-4Plus4                     (2),    -- '4 + 4'
        v3-4Plus2x2                   (3),    -- '4 + 2x2'
        v4-4Plus2Plus2x1              (4),    -- '4 + 2 + 2x1'
        v5-4Plus4x1                   (5),    -- '4 + 4x1'
        v6-4x2                        (6),    -- '4x2'
        v7-3x2Plus2x1                 (7),    -- '3x2 + 2x1'
        v8-2x2Plus4x1                 (8),    -- '2x2 + 4x1'
        v9-2Plus6x1                   (9),    -- '2 + 6x1'
        v10-8x1                       (10),    -- '8x1'
        v11-51                        (11),    -- '5.1'
        v12-4Plus2                    (12),    -- '4 + 2'
        v13-4Plus2x1                  (13),    -- '4 + 2x1'
        v14-3x2                       (14),    -- '3x2'
        v15-2x2Plus2x1                (15),    -- '2x2 + 2x1'
        v16-2Plus4x1                  (16),    -- '2 + 4x1'
        v17-6x1                       (17),    -- '6x1'
        v18-4                         (18),    -- '4'
        v19-2Plus2                    (19),    -- '2 + 2'
        v20-2Plus2x1                  (20),    -- '2 + 2x1'
        v21-4x1                       (21),    -- '4x1'
        v22-71                        (22),    -- '7.1'
        v23-71Screen                  (23)     -- '7.1 Screen'
    }

Enc1E171enumObj ::= TEXTUAL-CONVENTION
    STATUS current
    DESCRIPTION
    "EnumObj"
    SYNTAX INTEGER {
        v0-unknown                    (0),    -- 'Unknown'
        v1-2398Hz                     (1),    -- '23.98 Hz'
        v2-24Hz                       (2),    -- '24 Hz'
        v3-25Hz                       (3),    -- '25 Hz'
        v4-2997Hz                     (4),    -- '29.97 Hz'
        v5-30Hz                       (5),    -- '30 Hz'
        v6-50Hz                       (6),    -- '50 Hz'
        v7-5994Hz                     (7),    -- '59.94 Hz'
        v8-60Hz                       (8)     -- '60 Hz'
    }

Enc1E172enumObj ::= TEXTUAL-CONVENTION
    STATUS current
    DESCRIPTION
    "EnumObj"
    SYNTAX INTEGER {
        v0-uninitialized              (0),    -- 'Uninitialized'
        v1-running                    (1),    -- 'Running'
        v2-functionBypassed           (2),    -- 'Function Bypassed'
        v3-outputMuted                (3),    -- 'Output Muted'
        v4-bypassed                   (4)     -- 'Bypassed'
    }

Enc1E173enumObj ::= TEXTUAL-CONVENTION
    STATUS current
    DESCRIPTION
    "EnumObj"
    SYNTAX INTEGER {
        v0-selectpreset               (0),    -- '(select preset)'
        v1-ultraLight                 (1),    -- 'Ultra Light'
        v2-light                      (2),    -- 'Light'
        v3-medium                     (3),    -- 'Medium'
        v4-aggressive                 (4)     -- 'Aggressive'
    }

Enc1E174enumObj ::= TEXTUAL-CONVENTION
    STATUS current
    DESCRIPTION
    "EnumObj"
    SYNTAX INTEGER {
        v0-enable                     (0),    -- 'Enable'
        v1-bypass                     (1)     -- 'Bypass'
    }

Enc1E175enumObj ::= TEXTUAL-CONVENTION
    STATUS current
    DESCRIPTION
    "EnumObj"
    SYNTAX INTEGER {
        v0-nlm                        (0),    -- 'NLM'
        v1-leq1770                    (1)     -- 'LEQ 1770'
    }

Enc1E176enumObj ::= TEXTUAL-CONVENTION
    STATUS current
    DESCRIPTION
    "EnumObj"
    SYNTAX INTEGER {
        v0-notSpecified               (0),    -- 'Not Specified'
        v1-2997Hz                     (1),    -- '29.97 Hz'
        v2-30Hz                       (2),    -- '30 Hz'
        v3-25Hz                       (3),    -- '25 Hz'
        v4-5994Hz                     (4),    -- '59.94 Hz'
        v5-50Hz                       (5),    -- '50 Hz'
        v6-24Hz                       (6),    -- '24 Hz'
        v7-2398Hz                     (7),    -- '23.98 Hz'
        v8-60Hz                       (8)     -- '60 Hz'
    }

Enc1E177enumObj ::= TEXTUAL-CONVENTION
    STATUS current
    DESCRIPTION
    "EnumObj"
    SYNTAX INTEGER {
        v0-program1                   (0),    -- 'Program 1'
        v1-program2                   (1),    -- 'Program 2'
        v2-program3                   (2),    -- 'Program 3'
        v3-program4                   (3),    -- 'Program 4'
        v4-program5                   (4),    -- 'Program 5'
        v5-program6                   (5),    -- 'Program 6'
        v6-program7                   (6),    -- 'Program 7'
        v7-program8                   (7)     -- 'Program 8'
    }

Enc1E178enumObj ::= TEXTUAL-CONVENTION
    STATUS current
    DESCRIPTION
    "EnumObj"
    SYNTAX INTEGER {
        v0-notPresent                 (0),    -- 'Not Present'
        v1-1080p25                    (1),    -- '1080p/25'
        v2-720p5994                   (2),    -- '720p/59.94'
        v3-720p60                     (3),    -- '720p/60'
        v4-1080p2398                  (4),    -- '1080p/23.98'
        v5-1080p24                    (5),    -- '1080p/24'
        v6-1080p2997                  (6),    -- '1080p/29.97'
        v7-1080p30                    (7),    -- '1080p/30'
        v8-na                         (8),    -- 'N/A'
        v9-1080i50                    (9),    -- '1080i/50'
        v10-1035i2997                 (10),    -- '1035i/29.97'
        v11-1035i30                   (11),    -- '1035i/30'
        v12-pal-M                     (12),    -- 'PAL-M'
        v13-1080i50-295               (13),    -- '1080i/50-295'
        v14-1080i5994                 (14),    -- '1080i/59.94'
        v15-1080i60                   (15),    -- '1080i/60'
        v16-525                       (16),    -- '525'
        v17-625                       (17),    -- '625'
        v18-ntsc                      (18),    -- 'NTSC'
        v19-720p50                    (19),    -- '720p/50'
        v20-1080PsF2398               (20),    -- '1080PsF/23.98'
        v21-1080PsF24                 (21),    -- '1080PsF/24'
        v22-720p2997                  (22),    -- '720p/29.97'
        v23-720p30                    (23),    -- '720p/30'
        v24-pal-B                     (24),    -- 'PAL-B'
        v25-720p25                    (25),    -- '720p/25'
        v26-720p2398                  (26),    -- '720p/23.98'
        v27-720p24                    (27),    -- '720p/24'
        v28-1080PsF2997               (28),    -- '1080PsF/29.97'
        v29-1080PsF30                 (29),    -- '1080PsF/30'
        v30-secam                     (30),    -- 'SECAM'
        v31-1080PsF25                 (31),    -- '1080PsF/25'
        v32-na6                       (32),    -- 'N/A_6'
        v33-1080p50                   (33),    -- '1080p/50'
        v34-na7                       (34),    -- 'N/A_7'
        v35-na8                       (35),    -- 'N/A_8'
        v36-na9                       (36),    -- 'N/A_9'
        v37-na10                      (37),    -- 'N/A_10'
        v38-1080p5994                 (38),    -- '1080p/59.94'
        v39-1080p60                   (39),    -- '1080p/60'
        v40-1080p50DL                 (40),    -- '1080p/50 DL'
        v41-na11                      (41),    -- 'N/A_11'
        v42-na12                      (42),    -- 'N/A_12'
        v43-na13                      (43),    -- 'N/A_13'
        v44-na14                      (44),    -- 'N/A_14'
        v45-1080p5994DL               (45),    -- '1080p/59.94 DL'
        v46-1080p60DL                 (46)     -- '1080p/60 DL'
    }

Enc1E179enumObj ::= TEXTUAL-CONVENTION
    STATUS current
    DESCRIPTION
    "EnumObj"
    SYNTAX INTEGER {
        v0-multichannel51Plus         (0),    -- 'Multichannel (5.1+)'
        v1-monoLeft                   (1),    -- 'Mono (Left)'
        v2-parametricStereo           (2),    -- 'Parametric Stereo'
        v3-stereo                     (3),    -- 'Stereo'
        v4-dualMono1Plus1             (4),    -- 'Dual Mono (1+1)'
        v5-monoRight                  (5)     -- 'Mono (Right)'
    }

Enc1E180enumObj ::= TEXTUAL-CONVENTION
    STATUS current
    DESCRIPTION
    "EnumObj"
    SYNTAX INTEGER {
        v0-51Plus2                    (0),    -- '5.1 + 2'
        v1-51Plus2x1                  (1),    -- '5.1 + 2x1'
        v2-4Plus4                     (2),    -- '4 + 4'
        v3-4Plus2x2                   (3),    -- '4 + 2x2'
        v4-4Plus2Plus2x1              (4),    -- '4 + 2 + 2x1'
        v5-4Plus4x1                   (5),    -- '4 + 4x1'
        v6-4x2                        (6),    -- '4x2'
        v7-3x2Plus2x1                 (7),    -- '3x2 + 2x1'
        v8-2x2Plus4x1                 (8),    -- '2x2 + 4x1'
        v9-2Plus6x1                   (9),    -- '2 + 6x1'
        v10-8x1                       (10),    -- '8x1'
        v11-51                        (11),    -- '5.1'
        v12-4Plus2                    (12),    -- '4 + 2'
        v13-4Plus2x1                  (13),    -- '4 + 2x1'
        v14-3x2                       (14),    -- '3x2'
        v15-2x2Plus2x1                (15),    -- '2x2 + 2x1'
        v16-2Plus4x1                  (16),    -- '2 + 4x1'
        v17-6x1                       (17),    -- '6x1'
        v18-4                         (18),    -- '4'
        v19-2Plus2                    (19),    -- '2 + 2'
        v20-2Plus2x1                  (20),    -- '2 + 2x1'
        v21-4x1                       (21),    -- '4x1'
        v22-71                        (22),    -- '7.1'
        v23-71Screen                  (23)     -- '7.1 Screen'
    }

Enc1E181enumObj ::= TEXTUAL-CONVENTION
    STATUS current
    DESCRIPTION
    "EnumObj"
    SYNTAX INTEGER {
        v0-standardunaligned          (0),    -- 'Standard (unaligned)'
        v1-compatibilityalignedlowfidelity(1)     -- 'Compatibility (aligned, low fidelity)'
    }

Enc1E182enumObj ::= TEXTUAL-CONVENTION
    STATUS current
    DESCRIPTION
    "EnumObj"
    SYNTAX INTEGER {
        v0-multichannel51Plus         (0),    -- 'Multichannel (5.1+)'
        v1-monoLeft                   (1),    -- 'Mono (Left)'
        v2-parametricStereo           (2),    -- 'Parametric Stereo'
        v3-stereo                     (3),    -- 'Stereo'
        v4-dualMono1Plus1             (4),    -- 'Dual Mono (1+1)'
        v5-monoRight                  (5)     -- 'Mono (Right)'
    }

Enc1E183enumObj ::= TEXTUAL-CONVENTION
    STATUS current
    DESCRIPTION
    "EnumObj"
    SYNTAX INTEGER {
        v0-51Plus2                    (0),    -- '5.1 + 2'
        v1-51Plus2x1                  (1),    -- '5.1 + 2x1'
        v2-4Plus4                     (2),    -- '4 + 4'
        v3-4Plus2x2                   (3),    -- '4 + 2x2'
        v4-4Plus2Plus2x1              (4),    -- '4 + 2 + 2x1'
        v5-4Plus4x1                   (5),    -- '4 + 4x1'
        v6-4x2                        (6),    -- '4x2'
        v7-3x2Plus2x1                 (7),    -- '3x2 + 2x1'
        v8-2x2Plus4x1                 (8),    -- '2x2 + 4x1'
        v9-2Plus6x1                   (9),    -- '2 + 6x1'
        v10-8x1                       (10),    -- '8x1'
        v11-51                        (11),    -- '5.1'
        v12-4Plus2                    (12),    -- '4 + 2'
        v13-4Plus2x1                  (13),    -- '4 + 2x1'
        v14-3x2                       (14),    -- '3x2'
        v15-2x2Plus2x1                (15),    -- '2x2 + 2x1'
        v16-2Plus4x1                  (16),    -- '2 + 4x1'
        v17-6x1                       (17),    -- '6x1'
        v18-4                         (18),    -- '4'
        v19-2Plus2                    (19),    -- '2 + 2'
        v20-2Plus2x1                  (20),    -- '2 + 2x1'
        v21-4x1                       (21),    -- '4x1'
        v22-71                        (22),    -- '7.1'
        v23-71Screen                  (23)     -- '7.1 Screen'
    }

Enc1E184enumObj ::= TEXTUAL-CONVENTION
    STATUS current
    DESCRIPTION
    "EnumObj"
    SYNTAX INTEGER {
        v0-standardunaligned          (0),    -- 'Standard (unaligned)'
        v1-compatibilityalignedlowfidelity(1)     -- 'Compatibility (aligned, low fidelity)'
    }

Enc1E185enumObj ::= TEXTUAL-CONVENTION
    STATUS current
    DESCRIPTION
    "EnumObj"
    SYNTAX INTEGER {
        v0-multichannel51Plus         (0),    -- 'Multichannel (5.1+)'
        v1-monoLeft                   (1),    -- 'Mono (Left)'
        v2-parametricStereo           (2),    -- 'Parametric Stereo'
        v3-stereo                     (3),    -- 'Stereo'
        v4-dualMono1Plus1             (4),    -- 'Dual Mono (1+1)'
        v5-monoRight                  (5)     -- 'Mono (Right)'
    }

Enc1E186enumObj ::= TEXTUAL-CONVENTION
    STATUS current
    DESCRIPTION
    "EnumObj"
    SYNTAX INTEGER {
        v0-51Plus2                    (0),    -- '5.1 + 2'
        v1-51Plus2x1                  (1),    -- '5.1 + 2x1'
        v2-4Plus4                     (2),    -- '4 + 4'
        v3-4Plus2x2                   (3),    -- '4 + 2x2'
        v4-4Plus2Plus2x1              (4),    -- '4 + 2 + 2x1'
        v5-4Plus4x1                   (5),    -- '4 + 4x1'
        v6-4x2                        (6),    -- '4x2'
        v7-3x2Plus2x1                 (7),    -- '3x2 + 2x1'
        v8-2x2Plus4x1                 (8),    -- '2x2 + 4x1'
        v9-2Plus6x1                   (9),    -- '2 + 6x1'
        v10-8x1                       (10),    -- '8x1'
        v11-51                        (11),    -- '5.1'
        v12-4Plus2                    (12),    -- '4 + 2'
        v13-4Plus2x1                  (13),    -- '4 + 2x1'
        v14-3x2                       (14),    -- '3x2'
        v15-2x2Plus2x1                (15),    -- '2x2 + 2x1'
        v16-2Plus4x1                  (16),    -- '2 + 4x1'
        v17-6x1                       (17),    -- '6x1'
        v18-4                         (18),    -- '4'
        v19-2Plus2                    (19),    -- '2 + 2'
        v20-2Plus2x1                  (20),    -- '2 + 2x1'
        v21-4x1                       (21),    -- '4x1'
        v22-71                        (22),    -- '7.1'
        v23-71Screen                  (23)     -- '7.1 Screen'
    }

Enc1E187enumObj ::= TEXTUAL-CONVENTION
    STATUS current
    DESCRIPTION
    "EnumObj"
    SYNTAX INTEGER {
        v0-standardunaligned          (0),    -- 'Standard (unaligned)'
        v1-compatibilityalignedlowfidelity(1)     -- 'Compatibility (aligned, low fidelity)'
    }

Enc1E188enumObj ::= TEXTUAL-CONVENTION
    STATUS current
    DESCRIPTION
    "EnumObj"
    SYNTAX INTEGER {
        v0-multichannel51Plus         (0),    -- 'Multichannel (5.1+)'
        v1-monoLeft                   (1),    -- 'Mono (Left)'
        v2-parametricStereo           (2),    -- 'Parametric Stereo'
        v3-stereo                     (3),    -- 'Stereo'
        v4-dualMono1Plus1             (4),    -- 'Dual Mono (1+1)'
        v5-monoRight                  (5)     -- 'Mono (Right)'
    }

Enc1E189enumObj ::= TEXTUAL-CONVENTION
    STATUS current
    DESCRIPTION
    "EnumObj"
    SYNTAX INTEGER {
        v0-51Plus2                    (0),    -- '5.1 + 2'
        v1-51Plus2x1                  (1),    -- '5.1 + 2x1'
        v2-4Plus4                     (2),    -- '4 + 4'
        v3-4Plus2x2                   (3),    -- '4 + 2x2'
        v4-4Plus2Plus2x1              (4),    -- '4 + 2 + 2x1'
        v5-4Plus4x1                   (5),    -- '4 + 4x1'
        v6-4x2                        (6),    -- '4x2'
        v7-3x2Plus2x1                 (7),    -- '3x2 + 2x1'
        v8-2x2Plus4x1                 (8),    -- '2x2 + 4x1'
        v9-2Plus6x1                   (9),    -- '2 + 6x1'
        v10-8x1                       (10),    -- '8x1'
        v11-51                        (11),    -- '5.1'
        v12-4Plus2                    (12),    -- '4 + 2'
        v13-4Plus2x1                  (13),    -- '4 + 2x1'
        v14-3x2                       (14),    -- '3x2'
        v15-2x2Plus2x1                (15),    -- '2x2 + 2x1'
        v16-2Plus4x1                  (16),    -- '2 + 4x1'
        v17-6x1                       (17),    -- '6x1'
        v18-4                         (18),    -- '4'
        v19-2Plus2                    (19),    -- '2 + 2'
        v20-2Plus2x1                  (20),    -- '2 + 2x1'
        v21-4x1                       (21),    -- '4x1'
        v22-71                        (22),    -- '7.1'
        v23-71Screen                  (23)     -- '7.1 Screen'
    }

Enc1E190enumObj ::= TEXTUAL-CONVENTION
    STATUS current
    DESCRIPTION
    "EnumObj"
    SYNTAX INTEGER {
        v0-standardunaligned          (0),    -- 'Standard (unaligned)'
        v1-compatibilityalignedlowfidelity(1)     -- 'Compatibility (aligned, low fidelity)'
    }

Enc1E191enumObj ::= TEXTUAL-CONVENTION
    STATUS current
    DESCRIPTION
    "EnumObj"
    SYNTAX INTEGER {
        v0-multichannel51Plus         (0),    -- 'Multichannel (5.1+)'
        v1-monoLeft                   (1),    -- 'Mono (Left)'
        v2-parametricStereo           (2),    -- 'Parametric Stereo'
        v3-stereo                     (3),    -- 'Stereo'
        v4-dualMono1Plus1             (4),    -- 'Dual Mono (1+1)'
        v5-monoRight                  (5)     -- 'Mono (Right)'
    }

Enc1E192enumObj ::= TEXTUAL-CONVENTION
    STATUS current
    DESCRIPTION
    "EnumObj"
    SYNTAX INTEGER {
        v0-51Plus2                    (0),    -- '5.1 + 2'
        v1-51Plus2x1                  (1),    -- '5.1 + 2x1'
        v2-4Plus4                     (2),    -- '4 + 4'
        v3-4Plus2x2                   (3),    -- '4 + 2x2'
        v4-4Plus2Plus2x1              (4),    -- '4 + 2 + 2x1'
        v5-4Plus4x1                   (5),    -- '4 + 4x1'
        v6-4x2                        (6),    -- '4x2'
        v7-3x2Plus2x1                 (7),    -- '3x2 + 2x1'
        v8-2x2Plus4x1                 (8),    -- '2x2 + 4x1'
        v9-2Plus6x1                   (9),    -- '2 + 6x1'
        v10-8x1                       (10),    -- '8x1'
        v11-51                        (11),    -- '5.1'
        v12-4Plus2                    (12),    -- '4 + 2'
        v13-4Plus2x1                  (13),    -- '4 + 2x1'
        v14-3x2                       (14),    -- '3x2'
        v15-2x2Plus2x1                (15),    -- '2x2 + 2x1'
        v16-2Plus4x1                  (16),    -- '2 + 4x1'
        v17-6x1                       (17),    -- '6x1'
        v18-4                         (18),    -- '4'
        v19-2Plus2                    (19),    -- '2 + 2'
        v20-2Plus2x1                  (20),    -- '2 + 2x1'
        v21-4x1                       (21),    -- '4x1'
        v22-71                        (22),    -- '7.1'
        v23-71Screen                  (23)     -- '7.1 Screen'
    }

Enc1E193enumObj ::= TEXTUAL-CONVENTION
    STATUS current
    DESCRIPTION
    "EnumObj"
    SYNTAX INTEGER {
        v0-standardunaligned          (0),    -- 'Standard (unaligned)'
        v1-compatibilityalignedlowfidelity(1)     -- 'Compatibility (aligned, low fidelity)'
    }

Enc1E194enumObj ::= TEXTUAL-CONVENTION
    STATUS current
    DESCRIPTION
    "EnumObj"
    SYNTAX INTEGER {
        v0-multichannel51Plus         (0),    -- 'Multichannel (5.1+)'
        v1-monoLeft                   (1),    -- 'Mono (Left)'
        v2-parametricStereo           (2),    -- 'Parametric Stereo'
        v3-stereo                     (3),    -- 'Stereo'
        v4-dualMono1Plus1             (4),    -- 'Dual Mono (1+1)'
        v5-monoRight                  (5)     -- 'Mono (Right)'
    }

Enc1E195enumObj ::= TEXTUAL-CONVENTION
    STATUS current
    DESCRIPTION
    "EnumObj"
    SYNTAX INTEGER {
        v0-51Plus2                    (0),    -- '5.1 + 2'
        v1-51Plus2x1                  (1),    -- '5.1 + 2x1'
        v2-4Plus4                     (2),    -- '4 + 4'
        v3-4Plus2x2                   (3),    -- '4 + 2x2'
        v4-4Plus2Plus2x1              (4),    -- '4 + 2 + 2x1'
        v5-4Plus4x1                   (5),    -- '4 + 4x1'
        v6-4x2                        (6),    -- '4x2'
        v7-3x2Plus2x1                 (7),    -- '3x2 + 2x1'
        v8-2x2Plus4x1                 (8),    -- '2x2 + 4x1'
        v9-2Plus6x1                   (9),    -- '2 + 6x1'
        v10-8x1                       (10),    -- '8x1'
        v11-51                        (11),    -- '5.1'
        v12-4Plus2                    (12),    -- '4 + 2'
        v13-4Plus2x1                  (13),    -- '4 + 2x1'
        v14-3x2                       (14),    -- '3x2'
        v15-2x2Plus2x1                (15),    -- '2x2 + 2x1'
        v16-2Plus4x1                  (16),    -- '2 + 4x1'
        v17-6x1                       (17),    -- '6x1'
        v18-4                         (18),    -- '4'
        v19-2Plus2                    (19),    -- '2 + 2'
        v20-2Plus2x1                  (20),    -- '2 + 2x1'
        v21-4x1                       (21),    -- '4x1'
        v22-71                        (22),    -- '7.1'
        v23-71Screen                  (23)     -- '7.1 Screen'
    }

Enc1E196enumObj ::= TEXTUAL-CONVENTION
    STATUS current
    DESCRIPTION
    "EnumObj"
    SYNTAX INTEGER {
        v0-standardunaligned          (0),    -- 'Standard (unaligned)'
        v1-compatibilityalignedlowfidelity(1)     -- 'Compatibility (aligned, low fidelity)'
    }

Enc1E197enumObj ::= TEXTUAL-CONVENTION
    STATUS current
    DESCRIPTION
    "EnumObj"
    SYNTAX INTEGER {
        v0-multichannel51Plus         (0),    -- 'Multichannel (5.1+)'
        v1-monoLeft                   (1),    -- 'Mono (Left)'
        v2-parametricStereo           (2),    -- 'Parametric Stereo'
        v3-stereo                     (3),    -- 'Stereo'
        v4-dualMono1Plus1             (4),    -- 'Dual Mono (1+1)'
        v5-monoRight                  (5)     -- 'Mono (Right)'
    }

Enc1E198enumObj ::= TEXTUAL-CONVENTION
    STATUS current
    DESCRIPTION
    "EnumObj"
    SYNTAX INTEGER {
        v0-51Plus2                    (0),    -- '5.1 + 2'
        v1-51Plus2x1                  (1),    -- '5.1 + 2x1'
        v2-4Plus4                     (2),    -- '4 + 4'
        v3-4Plus2x2                   (3),    -- '4 + 2x2'
        v4-4Plus2Plus2x1              (4),    -- '4 + 2 + 2x1'
        v5-4Plus4x1                   (5),    -- '4 + 4x1'
        v6-4x2                        (6),    -- '4x2'
        v7-3x2Plus2x1                 (7),    -- '3x2 + 2x1'
        v8-2x2Plus4x1                 (8),    -- '2x2 + 4x1'
        v9-2Plus6x1                   (9),    -- '2 + 6x1'
        v10-8x1                       (10),    -- '8x1'
        v11-51                        (11),    -- '5.1'
        v12-4Plus2                    (12),    -- '4 + 2'
        v13-4Plus2x1                  (13),    -- '4 + 2x1'
        v14-3x2                       (14),    -- '3x2'
        v15-2x2Plus2x1                (15),    -- '2x2 + 2x1'
        v16-2Plus4x1                  (16),    -- '2 + 4x1'
        v17-6x1                       (17),    -- '6x1'
        v18-4                         (18),    -- '4'
        v19-2Plus2                    (19),    -- '2 + 2'
        v20-2Plus2x1                  (20),    -- '2 + 2x1'
        v21-4x1                       (21),    -- '4x1'
        v22-71                        (22),    -- '7.1'
        v23-71Screen                  (23)     -- '7.1 Screen'
    }

Enc1E199enumObj ::= TEXTUAL-CONVENTION
    STATUS current
    DESCRIPTION
    "EnumObj"
    SYNTAX INTEGER {
        v0-standardunaligned          (0),    -- 'Standard (unaligned)'
        v1-compatibilityalignedlowfidelity(1)     -- 'Compatibility (aligned, low fidelity)'
    }

Enc1E200enumObj ::= TEXTUAL-CONVENTION
    STATUS current
    DESCRIPTION
    "EnumObj"
    SYNTAX INTEGER {
        v0-multichannel51Plus         (0),    -- 'Multichannel (5.1+)'
        v1-monoLeft                   (1),    -- 'Mono (Left)'
        v2-parametricStereo           (2),    -- 'Parametric Stereo'
        v3-stereo                     (3),    -- 'Stereo'
        v4-dualMono1Plus1             (4),    -- 'Dual Mono (1+1)'
        v5-monoRight                  (5)     -- 'Mono (Right)'
    }

Enc1E201enumObj ::= TEXTUAL-CONVENTION
    STATUS current
    DESCRIPTION
    "EnumObj"
    SYNTAX INTEGER {
        v0-51Plus2                    (0),    -- '5.1 + 2'
        v1-51Plus2x1                  (1),    -- '5.1 + 2x1'
        v2-4Plus4                     (2),    -- '4 + 4'
        v3-4Plus2x2                   (3),    -- '4 + 2x2'
        v4-4Plus2Plus2x1              (4),    -- '4 + 2 + 2x1'
        v5-4Plus4x1                   (5),    -- '4 + 4x1'
        v6-4x2                        (6),    -- '4x2'
        v7-3x2Plus2x1                 (7),    -- '3x2 + 2x1'
        v8-2x2Plus4x1                 (8),    -- '2x2 + 4x1'
        v9-2Plus6x1                   (9),    -- '2 + 6x1'
        v10-8x1                       (10),    -- '8x1'
        v11-51                        (11),    -- '5.1'
        v12-4Plus2                    (12),    -- '4 + 2'
        v13-4Plus2x1                  (13),    -- '4 + 2x1'
        v14-3x2                       (14),    -- '3x2'
        v15-2x2Plus2x1                (15),    -- '2x2 + 2x1'
        v16-2Plus4x1                  (16),    -- '2 + 4x1'
        v17-6x1                       (17),    -- '6x1'
        v18-4                         (18),    -- '4'
        v19-2Plus2                    (19),    -- '2 + 2'
        v20-2Plus2x1                  (20),    -- '2 + 2x1'
        v21-4x1                       (21),    -- '4x1'
        v22-71                        (22),    -- '7.1'
        v23-71Screen                  (23)     -- '7.1 Screen'
    }

Enc1E202enumObj ::= TEXTUAL-CONVENTION
    STATUS current
    DESCRIPTION
    "EnumObj"
    SYNTAX INTEGER {
        v0-standardunaligned          (0),    -- 'Standard (unaligned)'
        v1-compatibilityalignedlowfidelity(1)     -- 'Compatibility (aligned, low fidelity)'
    }

Enc1E203enumObj ::= TEXTUAL-CONVENTION
    STATUS current
    DESCRIPTION
    "EnumObj"
    SYNTAX INTEGER {
        v0-initializing               (0),    -- 'Initializing'
        v1-running                    (1),    -- 'Running'
        v2-notRunningbyrequest        (2),    -- 'Not Running (by request)'
        v3-notRunningerror            (3),    -- 'Not Running (error)'
        v4-unknown                    (4),    -- 'Unknown'
        v5-locked                     (5)     -- 'Locked'
    }


-- Parameter Definitions
enc1P1ipaddressTable OBJECT-TYPE
    SYNTAX SEQUENCE OF Enc1P1ipaddressEntry
    MAX-ACCESS not-accessible
    STATUS     current
    DESCRIPTION
    "
    Name      : IP Address
    Menu Path : /Control/IP LANs/Primary Data IP LAN
    Details   : Specifies module primary IP address.
    "
::= { enc1Params 1 }

enc1P1ipaddressEntry OBJECT-TYPE
    SYNTAX Enc1P1ipaddressEntry
    MAX-ACCESS not-accessible
    STATUS     current
    DESCRIPTION
    "Table Entry for IP Address"
    INDEX { slotId }
::= { enc1P1ipaddressTable 1 }

Enc1P1ipaddressEntry ::= SEQUENCE {
    enc1P1ipaddressValue    DisplayString
}

enc1P1ipaddressValue OBJECT-TYPE
    SYNTAX     DisplayString
    MAX-ACCESS read-write
    STATUS     current
    DESCRIPTION
    "Specifies module primary IP address."
::= { enc1P1ipaddressEntry 1 }

enc1P2ipmaskTable OBJECT-TYPE
    SYNTAX SEQUENCE OF Enc1P2ipmaskEntry
    MAX-ACCESS not-accessible
    STATUS     current
    DESCRIPTION
    "
    Name      : IP Mask
    Menu Path : /Control/IP LANs/Primary Data IP LAN
    Details   : Specifies module primary IP mask.
    "
::= { enc1Params 2 }

enc1P2ipmaskEntry OBJECT-TYPE
    SYNTAX Enc1P2ipmaskEntry
    MAX-ACCESS not-accessible
    STATUS     current
    DESCRIPTION
    "Table Entry for IP Mask"
    INDEX { slotId }
::= { enc1P2ipmaskTable 1 }

Enc1P2ipmaskEntry ::= SEQUENCE {
    enc1P2ipmaskValue    DisplayString
}

enc1P2ipmaskValue OBJECT-TYPE
    SYNTAX     DisplayString
    MAX-ACCESS read-write
    STATUS     current
    DESCRIPTION
    "Specifies module primary IP mask."
::= { enc1P2ipmaskEntry 1 }

enc1P3ipgatewayTable OBJECT-TYPE
    SYNTAX SEQUENCE OF Enc1P3ipgatewayEntry
    MAX-ACCESS not-accessible
    STATUS     current
    DESCRIPTION
    "
    Name      : IP Gateway
    Menu Path : /Control/IP LANs/Primary Data IP LAN
    Details   : Specifies module primary IP gateway.
    "
::= { enc1Params 3 }

enc1P3ipgatewayEntry OBJECT-TYPE
    SYNTAX Enc1P3ipgatewayEntry
    MAX-ACCESS not-accessible
    STATUS     current
    DESCRIPTION
    "Table Entry for IP Gateway"
    INDEX { slotId }
::= { enc1P3ipgatewayTable 1 }

Enc1P3ipgatewayEntry ::= SEQUENCE {
    enc1P3ipgatewayValue    DisplayString
}

enc1P3ipgatewayValue OBJECT-TYPE
    SYNTAX     DisplayString
    MAX-ACCESS read-write
    STATUS     current
    DESCRIPTION
    "Specifies module primary IP gateway."
::= { enc1P3ipgatewayEntry 1 }

enc1P4vlanidTable OBJECT-TYPE
    SYNTAX SEQUENCE OF Enc1P4vlanidEntry
    MAX-ACCESS not-accessible
    STATUS     current
    DESCRIPTION
    "
    Name      : VLAN ID
    Menu Path : /Control/IP LANs/Primary Data IP LAN
    Units     : 
    Precision : 0
    Low Range : 0
    High Range: 4094
    Details   : Specifies module primary VLAN ID.

     NOTE: Precision/Units/Ranges represent the state of the
           parameter during the MIB generation, and does not
           neccessary reflect the current state of the parameter
    "
::= { enc1Params 4 }

enc1P4vlanidEntry OBJECT-TYPE
    SYNTAX Enc1P4vlanidEntry
    MAX-ACCESS not-accessible
    STATUS     current
    DESCRIPTION
    "Table Entry for VLAN ID"
    INDEX { slotId }
::= { enc1P4vlanidTable 1 }

Enc1P4vlanidEntry ::= SEQUENCE {
    enc1P4vlanidValue    INTEGER
}

enc1P4vlanidValue OBJECT-TYPE
    SYNTAX     INTEGER
    MAX-ACCESS read-write
    STATUS     current
    DESCRIPTION
    "Specifies module primary VLAN ID."
::= { enc1P4vlanidEntry 1 }

enc1P5applyTable OBJECT-TYPE
    SYNTAX SEQUENCE OF Enc1P5applyEntry
    MAX-ACCESS not-accessible
    STATUS     current
    DESCRIPTION
    "
    Name      : Apply
    Menu Path : /Control/IP LANs/Primary Data IP LAN
    Details   : Applies the changes to primary ethernet interface.
    "
::= { enc1Params 5 }

enc1P5applyEntry OBJECT-TYPE
    SYNTAX Enc1P5applyEntry
    MAX-ACCESS not-accessible
    STATUS     current
    DESCRIPTION
    "Table Entry for Apply"
    INDEX { slotId }
::= { enc1P5applyTable 1 }

Enc1P5applyEntry ::= SEQUENCE {
    enc1P5applyValue    Enc1E20enumObj
}

enc1P5applyValue OBJECT-TYPE
    SYNTAX     Enc1E20enumObj
    MAX-ACCESS read-write
    STATUS     current
    DESCRIPTION
    "Applies the changes to primary ethernet interface."
::= { enc1P5applyEntry 1 }

enc1P6ipaddressTable OBJECT-TYPE
    SYNTAX SEQUENCE OF Enc1P6ipaddressEntry
    MAX-ACCESS not-accessible
    STATUS     current
    DESCRIPTION
    "
    Name      : IP Address
    Menu Path : /Control/IP LANs/Secondary Data IP LAN
    Details   : Specifies module secondary IP address.
    "
::= { enc1Params 6 }

enc1P6ipaddressEntry OBJECT-TYPE
    SYNTAX Enc1P6ipaddressEntry
    MAX-ACCESS not-accessible
    STATUS     current
    DESCRIPTION
    "Table Entry for IP Address"
    INDEX { slotId }
::= { enc1P6ipaddressTable 1 }

Enc1P6ipaddressEntry ::= SEQUENCE {
    enc1P6ipaddressValue    DisplayString
}

enc1P6ipaddressValue OBJECT-TYPE
    SYNTAX     DisplayString
    MAX-ACCESS read-write
    STATUS     current
    DESCRIPTION
    "Specifies module secondary IP address."
::= { enc1P6ipaddressEntry 1 }

enc1P7ipmaskTable OBJECT-TYPE
    SYNTAX SEQUENCE OF Enc1P7ipmaskEntry
    MAX-ACCESS not-accessible
    STATUS     current
    DESCRIPTION
    "
    Name      : IP Mask
    Menu Path : /Control/IP LANs/Secondary Data IP LAN
    Details   : Specifies module secondary IP mask.
    "
::= { enc1Params 7 }

enc1P7ipmaskEntry OBJECT-TYPE
    SYNTAX Enc1P7ipmaskEntry
    MAX-ACCESS not-accessible
    STATUS     current
    DESCRIPTION
    "Table Entry for IP Mask"
    INDEX { slotId }
::= { enc1P7ipmaskTable 1 }

Enc1P7ipmaskEntry ::= SEQUENCE {
    enc1P7ipmaskValue    DisplayString
}

enc1P7ipmaskValue OBJECT-TYPE
    SYNTAX     DisplayString
    MAX-ACCESS read-write
    STATUS     current
    DESCRIPTION
    "Specifies module secondary IP mask."
::= { enc1P7ipmaskEntry 1 }

enc1P8ipgatewayTable OBJECT-TYPE
    SYNTAX SEQUENCE OF Enc1P8ipgatewayEntry
    MAX-ACCESS not-accessible
    STATUS     current
    DESCRIPTION
    "
    Name      : IP Gateway
    Menu Path : /Control/IP LANs/Secondary Data IP LAN
    Details   : Specifies module secondary IP gateway.
    "
::= { enc1Params 8 }

enc1P8ipgatewayEntry OBJECT-TYPE
    SYNTAX Enc1P8ipgatewayEntry
    MAX-ACCESS not-accessible
    STATUS     current
    DESCRIPTION
    "Table Entry for IP Gateway"
    INDEX { slotId }
::= { enc1P8ipgatewayTable 1 }

Enc1P8ipgatewayEntry ::= SEQUENCE {
    enc1P8ipgatewayValue    DisplayString
}

enc1P8ipgatewayValue OBJECT-TYPE
    SYNTAX     DisplayString
    MAX-ACCESS read-write
    STATUS     current
    DESCRIPTION
    "Specifies module secondary IP gateway."
::= { enc1P8ipgatewayEntry 1 }

enc1P9vlanidTable OBJECT-TYPE
    SYNTAX SEQUENCE OF Enc1P9vlanidEntry
    MAX-ACCESS not-accessible
    STATUS     current
    DESCRIPTION
    "
    Name      : VLAN ID
    Menu Path : /Control/IP LANs/Secondary Data IP LAN
    Units     : 
    Precision : 0
    Low Range : 0
    High Range: 4094
    Details   : Specifies module secondary VLAN ID.

     NOTE: Precision/Units/Ranges represent the state of the
           parameter during the MIB generation, and does not
           neccessary reflect the current state of the parameter
    "
::= { enc1Params 9 }

enc1P9vlanidEntry OBJECT-TYPE
    SYNTAX Enc1P9vlanidEntry
    MAX-ACCESS not-accessible
    STATUS     current
    DESCRIPTION
    "Table Entry for VLAN ID"
    INDEX { slotId }
::= { enc1P9vlanidTable 1 }

Enc1P9vlanidEntry ::= SEQUENCE {
    enc1P9vlanidValue    INTEGER
}

enc1P9vlanidValue OBJECT-TYPE
    SYNTAX     INTEGER
    MAX-ACCESS read-write
    STATUS     current
    DESCRIPTION
    "Specifies module secondary VLAN ID."
::= { enc1P9vlanidEntry 1 }

enc1P10applyTable OBJECT-TYPE
    SYNTAX SEQUENCE OF Enc1P10applyEntry
    MAX-ACCESS not-accessible
    STATUS     current
    DESCRIPTION
    "
    Name      : Apply
    Menu Path : /Control/IP LANs/Secondary Data IP LAN
    Details   : Applies the changes to secondary ethernet interface.
    "
::= { enc1Params 10 }

enc1P10applyEntry OBJECT-TYPE
    SYNTAX Enc1P10applyEntry
    MAX-ACCESS not-accessible
    STATUS     current
    DESCRIPTION
    "Table Entry for Apply"
    INDEX { slotId }
::= { enc1P10applyTable 1 }

Enc1P10applyEntry ::= SEQUENCE {
    enc1P10applyValue    Enc1E20enumObj
}

enc1P10applyValue OBJECT-TYPE
    SYNTAX     Enc1E20enumObj
    MAX-ACCESS read-write
    STATUS     current
    DESCRIPTION
    "Applies the changes to secondary ethernet interface."
::= { enc1P10applyEntry 1 }

enc1P11gpi1FunctionTable OBJECT-TYPE
    SYNTAX SEQUENCE OF Enc1P11gpi1FunctionEntry
    MAX-ACCESS not-accessible
    STATUS     current
    DESCRIPTION
    "
    Name      : GPI 1 Function
    Menu Path : /Control/GPI/GPI Input 1
    Details   : Specifies the GPI function.
    "
::= { enc1Params 11 }

enc1P11gpi1FunctionEntry OBJECT-TYPE
    SYNTAX Enc1P11gpi1FunctionEntry
    MAX-ACCESS not-accessible
    STATUS     current
    DESCRIPTION
    "Table Entry for GPI 1 Function"
    INDEX { slotId }
::= { enc1P11gpi1FunctionTable 1 }

Enc1P11gpi1FunctionEntry ::= SEQUENCE {
    enc1P11gpi1FunctionValue    Enc1E19enumObj
}

enc1P11gpi1FunctionValue OBJECT-TYPE
    SYNTAX     Enc1E19enumObj
    MAX-ACCESS read-write
    STATUS     current
    DESCRIPTION
    "Specifies the GPI function."
::= { enc1P11gpi1FunctionEntry 1 }

enc1P12gpi2FunctionTable OBJECT-TYPE
    SYNTAX SEQUENCE OF Enc1P12gpi2FunctionEntry
    MAX-ACCESS not-accessible
    STATUS     current
    DESCRIPTION
    "
    Name      : GPI 2 Function
    Menu Path : /Control/GPI/GPI Input 2
    Details   : Specifies the GPI function.
    "
::= { enc1Params 12 }

enc1P12gpi2FunctionEntry OBJECT-TYPE
    SYNTAX Enc1P12gpi2FunctionEntry
    MAX-ACCESS not-accessible
    STATUS     current
    DESCRIPTION
    "Table Entry for GPI 2 Function"
    INDEX { slotId }
::= { enc1P12gpi2FunctionTable 1 }

Enc1P12gpi2FunctionEntry ::= SEQUENCE {
    enc1P12gpi2FunctionValue    Enc1E19enumObj
}

enc1P12gpi2FunctionValue OBJECT-TYPE
    SYNTAX     Enc1E19enumObj
    MAX-ACCESS read-write
    STATUS     current
    DESCRIPTION
    "Specifies the GPI function."
::= { enc1P12gpi2FunctionEntry 1 }

enc1P13gpi3FunctionTable OBJECT-TYPE
    SYNTAX SEQUENCE OF Enc1P13gpi3FunctionEntry
    MAX-ACCESS not-accessible
    STATUS     current
    DESCRIPTION
    "
    Name      : GPI 3 Function
    Menu Path : /Control/GPI/GPI Input 3
    Details   : Specifies the GPI function.
    "
::= { enc1Params 13 }

enc1P13gpi3FunctionEntry OBJECT-TYPE
    SYNTAX Enc1P13gpi3FunctionEntry
    MAX-ACCESS not-accessible
    STATUS     current
    DESCRIPTION
    "Table Entry for GPI 3 Function"
    INDEX { slotId }
::= { enc1P13gpi3FunctionTable 1 }

Enc1P13gpi3FunctionEntry ::= SEQUENCE {
    enc1P13gpi3FunctionValue    Enc1E19enumObj
}

enc1P13gpi3FunctionValue OBJECT-TYPE
    SYNTAX     Enc1E19enumObj
    MAX-ACCESS read-write
    STATUS     current
    DESCRIPTION
    "Specifies the GPI function."
::= { enc1P13gpi3FunctionEntry 1 }

enc1P14gpi4FunctionTable OBJECT-TYPE
    SYNTAX SEQUENCE OF Enc1P14gpi4FunctionEntry
    MAX-ACCESS not-accessible
    STATUS     current
    DESCRIPTION
    "
    Name      : GPI 4 Function
    Menu Path : /Control/GPI/GPI Input 4
    Details   : Specifies the GPI function.
    "
::= { enc1Params 14 }

enc1P14gpi4FunctionEntry OBJECT-TYPE
    SYNTAX Enc1P14gpi4FunctionEntry
    MAX-ACCESS not-accessible
    STATUS     current
    DESCRIPTION
    "Table Entry for GPI 4 Function"
    INDEX { slotId }
::= { enc1P14gpi4FunctionTable 1 }

Enc1P14gpi4FunctionEntry ::= SEQUENCE {
    enc1P14gpi4FunctionValue    Enc1E19enumObj
}

enc1P14gpi4FunctionValue OBJECT-TYPE
    SYNTAX     Enc1E19enumObj
    MAX-ACCESS read-write
    STATUS     current
    DESCRIPTION
    "Specifies the GPI function."
::= { enc1P14gpi4FunctionEntry 1 }

enc1P15baudRateTable OBJECT-TYPE
    SYNTAX SEQUENCE OF Enc1P15baudRateEntry
    MAX-ACCESS not-accessible
    STATUS     current
    DESCRIPTION
    "
    Name      : Baud Rate
    Menu Path : /Control/Serial/Serial 1
    Details   : Specifies serial port baud rate.
    "
::= { enc1Params 15 }

enc1P15baudRateEntry OBJECT-TYPE
    SYNTAX Enc1P15baudRateEntry
    MAX-ACCESS not-accessible
    STATUS     current
    DESCRIPTION
    "Table Entry for Baud Rate"
    INDEX { slotId }
::= { enc1P15baudRateTable 1 }

Enc1P15baudRateEntry ::= SEQUENCE {
    enc1P15baudRateValue    Enc1E17enumObj
}

enc1P15baudRateValue OBJECT-TYPE
    SYNTAX     Enc1E17enumObj
    MAX-ACCESS read-write
    STATUS     current
    DESCRIPTION
    "Specifies serial port baud rate."
::= { enc1P15baudRateEntry 1 }

enc1P16serial1TypeSelectTable OBJECT-TYPE
    SYNTAX SEQUENCE OF Enc1P16serial1TypeSelectEntry
    MAX-ACCESS not-accessible
    STATUS     current
    DESCRIPTION
    "
    Name      : Serial 1 Type Select
    Menu Path : /Control/Serial/Serial 1
    Details   : Specifies serial port's interface mode (RS-232 or RS-422).
    "
::= { enc1Params 16 }

enc1P16serial1TypeSelectEntry OBJECT-TYPE
    SYNTAX Enc1P16serial1TypeSelectEntry
    MAX-ACCESS not-accessible
    STATUS     current
    DESCRIPTION
    "Table Entry for Serial 1 Type Select"
    INDEX { slotId }
::= { enc1P16serial1TypeSelectTable 1 }

Enc1P16serial1TypeSelectEntry ::= SEQUENCE {
    enc1P16serial1TypeSelectValue    Enc1E16enumObj
}

enc1P16serial1TypeSelectValue OBJECT-TYPE
    SYNTAX     Enc1E16enumObj
    MAX-ACCESS read-write
    STATUS     current
    DESCRIPTION
    "Specifies serial port's interface mode (RS-232 or RS-422)."
::= { enc1P16serial1TypeSelectEntry 1 }

enc1P17baudRateTable OBJECT-TYPE
    SYNTAX SEQUENCE OF Enc1P17baudRateEntry
    MAX-ACCESS not-accessible
    STATUS     current
    DESCRIPTION
    "
    Name      : Baud Rate
    Menu Path : /Control/Serial/Serial 2
    Details   : Specifies serial port baud rate.
    "
::= { enc1Params 17 }

enc1P17baudRateEntry OBJECT-TYPE
    SYNTAX Enc1P17baudRateEntry
    MAX-ACCESS not-accessible
    STATUS     current
    DESCRIPTION
    "Table Entry for Baud Rate"
    INDEX { slotId }
::= { enc1P17baudRateTable 1 }

Enc1P17baudRateEntry ::= SEQUENCE {
    enc1P17baudRateValue    Enc1E17enumObj
}

enc1P17baudRateValue OBJECT-TYPE
    SYNTAX     Enc1E17enumObj
    MAX-ACCESS read-write
    STATUS     current
    DESCRIPTION
    "Specifies serial port baud rate."
::= { enc1P17baudRateEntry 1 }

enc1P18serial2TypeSelectTable OBJECT-TYPE
    SYNTAX SEQUENCE OF Enc1P18serial2TypeSelectEntry
    MAX-ACCESS not-accessible
    STATUS     current
    DESCRIPTION
    "
    Name      : Serial 2 Type Select
    Menu Path : /Control/Serial/Serial 2
    Details   : Specifies serial port's interface mode (RS-232 or RS-422).
    "
::= { enc1Params 18 }

enc1P18serial2TypeSelectEntry OBJECT-TYPE
    SYNTAX Enc1P18serial2TypeSelectEntry
    MAX-ACCESS not-accessible
    STATUS     current
    DESCRIPTION
    "Table Entry for Serial 2 Type Select"
    INDEX { slotId }
::= { enc1P18serial2TypeSelectTable 1 }

Enc1P18serial2TypeSelectEntry ::= SEQUENCE {
    enc1P18serial2TypeSelectValue    Enc1E16enumObj
}

enc1P18serial2TypeSelectValue OBJECT-TYPE
    SYNTAX     Enc1E16enumObj
    MAX-ACCESS read-write
    STATUS     current
    DESCRIPTION
    "Specifies serial port's interface mode (RS-232 or RS-422)."
::= { enc1P18serial2TypeSelectEntry 1 }

enc1P19txpacketsTable OBJECT-TYPE
    SYNTAX SEQUENCE OF Enc1P19txpacketsEntry
    MAX-ACCESS not-accessible
    STATUS     current
    DESCRIPTION
    "
    Name      : TX Packets
    Menu Path : /Control/IP LANs/Primary Data IP LAN
    Units     : 
    Precision : 0
    Low Range : 0
    High Range: -1
    Details   : Count of transmitted packets.

     NOTE: Precision/Units/Ranges represent the state of the
           parameter during the MIB generation, and does not
           neccessary reflect the current state of the parameter
    "
::= { enc1Params 19 }

enc1P19txpacketsEntry OBJECT-TYPE
    SYNTAX Enc1P19txpacketsEntry
    MAX-ACCESS not-accessible
    STATUS     current
    DESCRIPTION
    "Table Entry for TX Packets"
    INDEX { slotId }
::= { enc1P19txpacketsTable 1 }

Enc1P19txpacketsEntry ::= SEQUENCE {
    enc1P19txpacketsValue    INTEGER
}

enc1P19txpacketsValue OBJECT-TYPE
    SYNTAX     INTEGER
    MAX-ACCESS read-only
    STATUS     current
    DESCRIPTION
    "Count of transmitted packets."
::= { enc1P19txpacketsEntry 1 }

enc1P20txpacketsTable OBJECT-TYPE
    SYNTAX SEQUENCE OF Enc1P20txpacketsEntry
    MAX-ACCESS not-accessible
    STATUS     current
    DESCRIPTION
    "
    Name      : TX Packets
    Menu Path : /Control/IP LANs/Secondary Data IP LAN
    Units     : 
    Precision : 0
    Low Range : 0
    High Range: -1
    Details   : Count of transmitted packets.

     NOTE: Precision/Units/Ranges represent the state of the
           parameter during the MIB generation, and does not
           neccessary reflect the current state of the parameter
    "
::= { enc1Params 20 }

enc1P20txpacketsEntry OBJECT-TYPE
    SYNTAX Enc1P20txpacketsEntry
    MAX-ACCESS not-accessible
    STATUS     current
    DESCRIPTION
    "Table Entry for TX Packets"
    INDEX { slotId }
::= { enc1P20txpacketsTable 1 }

Enc1P20txpacketsEntry ::= SEQUENCE {
    enc1P20txpacketsValue    INTEGER
}

enc1P20txpacketsValue OBJECT-TYPE
    SYNTAX     INTEGER
    MAX-ACCESS read-only
    STATUS     current
    DESCRIPTION
    "Count of transmitted packets."
::= { enc1P20txpacketsEntry 1 }

enc1P21gpi1StateTable OBJECT-TYPE
    SYNTAX SEQUENCE OF Enc1P21gpi1StateEntry
    MAX-ACCESS not-accessible
    STATUS     current
    DESCRIPTION
    "
    Name      : GPI 1 State
    Menu Path : /Control/GPI/GPI Input 1
    Details   : Current state of the GPI.
    "
::= { enc1Params 21 }

enc1P21gpi1StateEntry OBJECT-TYPE
    SYNTAX Enc1P21gpi1StateEntry
    MAX-ACCESS not-accessible
    STATUS     current
    DESCRIPTION
    "Table Entry for GPI 1 State"
    INDEX { slotId }
::= { enc1P21gpi1StateTable 1 }

Enc1P21gpi1StateEntry ::= SEQUENCE {
    enc1P21gpi1StateValue    Enc1E14enumObj
}

enc1P21gpi1StateValue OBJECT-TYPE
    SYNTAX     Enc1E14enumObj
    MAX-ACCESS read-only
    STATUS     current
    DESCRIPTION
    "Current state of the GPI."
::= { enc1P21gpi1StateEntry 1 }

enc1P22gpi2StateTable OBJECT-TYPE
    SYNTAX SEQUENCE OF Enc1P22gpi2StateEntry
    MAX-ACCESS not-accessible
    STATUS     current
    DESCRIPTION
    "
    Name      : GPI 2 State
    Menu Path : /Control/GPI/GPI Input 2
    Details   : Current state of the GPI.
    "
::= { enc1Params 22 }

enc1P22gpi2StateEntry OBJECT-TYPE
    SYNTAX Enc1P22gpi2StateEntry
    MAX-ACCESS not-accessible
    STATUS     current
    DESCRIPTION
    "Table Entry for GPI 2 State"
    INDEX { slotId }
::= { enc1P22gpi2StateTable 1 }

Enc1P22gpi2StateEntry ::= SEQUENCE {
    enc1P22gpi2StateValue    Enc1E14enumObj
}

enc1P22gpi2StateValue OBJECT-TYPE
    SYNTAX     Enc1E14enumObj
    MAX-ACCESS read-only
    STATUS     current
    DESCRIPTION
    "Current state of the GPI."
::= { enc1P22gpi2StateEntry 1 }

enc1P23gpi3StateTable OBJECT-TYPE
    SYNTAX SEQUENCE OF Enc1P23gpi3StateEntry
    MAX-ACCESS not-accessible
    STATUS     current
    DESCRIPTION
    "
    Name      : GPI 3 State
    Menu Path : /Control/GPI/GPI Input 3
    Details   : Current state of the GPI.
    "
::= { enc1Params 23 }

enc1P23gpi3StateEntry OBJECT-TYPE
    SYNTAX Enc1P23gpi3StateEntry
    MAX-ACCESS not-accessible
    STATUS     current
    DESCRIPTION
    "Table Entry for GPI 3 State"
    INDEX { slotId }
::= { enc1P23gpi3StateTable 1 }

Enc1P23gpi3StateEntry ::= SEQUENCE {
    enc1P23gpi3StateValue    Enc1E14enumObj
}

enc1P23gpi3StateValue OBJECT-TYPE
    SYNTAX     Enc1E14enumObj
    MAX-ACCESS read-only
    STATUS     current
    DESCRIPTION
    "Current state of the GPI."
::= { enc1P23gpi3StateEntry 1 }

enc1P24gpi4StateTable OBJECT-TYPE
    SYNTAX SEQUENCE OF Enc1P24gpi4StateEntry
    MAX-ACCESS not-accessible
    STATUS     current
    DESCRIPTION
    "
    Name      : GPI 4 State
    Menu Path : /Control/GPI/GPI Input 4
    Details   : Current state of the GPI.
    "
::= { enc1Params 24 }

enc1P24gpi4StateEntry OBJECT-TYPE
    SYNTAX Enc1P24gpi4StateEntry
    MAX-ACCESS not-accessible
    STATUS     current
    DESCRIPTION
    "Table Entry for GPI 4 State"
    INDEX { slotId }
::= { enc1P24gpi4StateTable 1 }

Enc1P24gpi4StateEntry ::= SEQUENCE {
    enc1P24gpi4StateValue    Enc1E14enumObj
}

enc1P24gpi4StateValue OBJECT-TYPE
    SYNTAX     Enc1E14enumObj
    MAX-ACCESS read-only
    STATUS     current
    DESCRIPTION
    "Current state of the GPI."
::= { enc1P24gpi4StateEntry 1 }

enc1P25simodeTable OBJECT-TYPE
    SYNTAX SEQUENCE OF Enc1P25simodeEntry
    MAX-ACCESS not-accessible
    STATUS     current
    DESCRIPTION
    "
    Name      : SI Mode
    Menu Path : /TS Mux
    Details   : Specifies the SI Mode for the program. It must be one of MPEG, ATSC, DVB, or ISDB.
    "
::= { enc1Params 25 }

enc1P25simodeEntry OBJECT-TYPE
    SYNTAX Enc1P25simodeEntry
    MAX-ACCESS not-accessible
    STATUS     current
    DESCRIPTION
    "Table Entry for SI Mode"
    INDEX { slotId }
::= { enc1P25simodeTable 1 }

Enc1P25simodeEntry ::= SEQUENCE {
    enc1P25simodeValue    Enc1E129enumObj
}

enc1P25simodeValue OBJECT-TYPE
    SYNTAX     Enc1E129enumObj
    MAX-ACCESS read-write
    STATUS     current
    DESCRIPTION
    "Specifies the SI Mode for the program. It must be one of MPEG, ATSC, DVB, or ISDB."
::= { enc1P25simodeEntry 1 }

enc1P26nameTable OBJECT-TYPE
    SYNTAX SEQUENCE OF Enc1P26nameEntry
    MAX-ACCESS not-accessible
    STATUS     current
    DESCRIPTION
    "
    Name      : Name
    Menu Path : /TS Mux
    Details   : Specifies the program name. It is normally inserted into the SDT.
    "
::= { enc1Params 26 }

enc1P26nameEntry OBJECT-TYPE
    SYNTAX Enc1P26nameEntry
    MAX-ACCESS not-accessible
    STATUS     current
    DESCRIPTION
    "Table Entry for Name"
    INDEX { slotId }
::= { enc1P26nameTable 1 }

Enc1P26nameEntry ::= SEQUENCE {
    enc1P26nameValue    DisplayString
}

enc1P26nameValue OBJECT-TYPE
    SYNTAX     DisplayString
    MAX-ACCESS read-write
    STATUS     current
    DESCRIPTION
    "Specifies the program name. It is normally inserted into the SDT."
::= { enc1P26nameEntry 1 }

enc1P27tagTable OBJECT-TYPE
    SYNTAX SEQUENCE OF Enc1P27tagEntry
    MAX-ACCESS not-accessible
    STATUS     current
    DESCRIPTION
    "
    Name      : Tag
    Menu Path : /TS Mux
    Details   : Specifies the encoder tag.
    "
::= { enc1Params 27 }

enc1P27tagEntry OBJECT-TYPE
    SYNTAX Enc1P27tagEntry
    MAX-ACCESS not-accessible
    STATUS     current
    DESCRIPTION
    "Table Entry for Tag"
    INDEX { slotId }
::= { enc1P27tagTable 1 }

Enc1P27tagEntry ::= SEQUENCE {
    enc1P27tagValue    DisplayString
}

enc1P27tagValue OBJECT-TYPE
    SYNTAX     DisplayString
    MAX-ACCESS read-write
    STATUS     current
    DESCRIPTION
    "Specifies the encoder tag."
::= { enc1P27tagEntry 1 }

enc1P28encryptionModeTable OBJECT-TYPE
    SYNTAX SEQUENCE OF Enc1P28encryptionModeEntry
    MAX-ACCESS not-accessible
    STATUS     current
    DESCRIPTION
    "
    Name      : Encryption Mode
    Menu Path : /TS Mux/BISS
    Details   : Specifies whether encryption is to be used for the program and if it is what type of encryption.
    "
::= { enc1Params 28 }

enc1P28encryptionModeEntry OBJECT-TYPE
    SYNTAX Enc1P28encryptionModeEntry
    MAX-ACCESS not-accessible
    STATUS     current
    DESCRIPTION
    "Table Entry for Encryption Mode"
    INDEX { slotId }
::= { enc1P28encryptionModeTable 1 }

Enc1P28encryptionModeEntry ::= SEQUENCE {
    enc1P28encryptionModeValue    Enc1E130enumObj
}

enc1P28encryptionModeValue OBJECT-TYPE
    SYNTAX     Enc1E130enumObj
    MAX-ACCESS read-write
    STATUS     current
    DESCRIPTION
    "Specifies whether encryption is to be used for the program and if it is what type of encryption."
::= { enc1P28encryptionModeEntry 1 }

enc1P29clearSessionWordTable OBJECT-TYPE
    SYNTAX SEQUENCE OF Enc1P29clearSessionWordEntry
    MAX-ACCESS not-accessible
    STATUS     current
    DESCRIPTION
    "
    Name      : Clear Session Word
    Menu Path : /TS Mux/BISS
    Details   : Specifies BISS Session Word for the program. Enter as a 12 digit hexadecimal string.
    "
::= { enc1Params 29 }

enc1P29clearSessionWordEntry OBJECT-TYPE
    SYNTAX Enc1P29clearSessionWordEntry
    MAX-ACCESS not-accessible
    STATUS     current
    DESCRIPTION
    "Table Entry for Clear Session Word"
    INDEX { slotId }
::= { enc1P29clearSessionWordTable 1 }

Enc1P29clearSessionWordEntry ::= SEQUENCE {
    enc1P29clearSessionWordValue    DisplayString
}

enc1P29clearSessionWordValue OBJECT-TYPE
    SYNTAX     DisplayString
    MAX-ACCESS read-write
    STATUS     current
    DESCRIPTION
    "Specifies BISS Session Word for the program. Enter as a 12 digit hexadecimal string."
::= { enc1P29clearSessionWordEntry 1 }

enc1P30totalTSRateTable OBJECT-TYPE
    SYNTAX SEQUENCE OF Enc1P30totalTSRateEntry
    MAX-ACCESS not-accessible
    STATUS     current
    DESCRIPTION
    "
    Name      : Total TS Rate
    Menu Path : /TS Mux
    Units     : Mbits/sec
    Precision : 6
    Low Range : 100000
    High Range: 60000000
    Details   : Total transport stream rate for the program (Units: Mbits/sec)

     NOTE: Precision/Units/Ranges represent the state of the
           parameter during the MIB generation, and does not
           neccessary reflect the current state of the parameter
    "
::= { enc1Params 30 }

enc1P30totalTSRateEntry OBJECT-TYPE
    SYNTAX Enc1P30totalTSRateEntry
    MAX-ACCESS not-accessible
    STATUS     current
    DESCRIPTION
    "Table Entry for Total TS Rate"
    INDEX { slotId }
::= { enc1P30totalTSRateTable 1 }

Enc1P30totalTSRateEntry ::= SEQUENCE {
    enc1P30totalTSRateValue    INTEGER
}

enc1P30totalTSRateValue OBJECT-TYPE
    SYNTAX     INTEGER
    MAX-ACCESS read-write
    STATUS     current
    DESCRIPTION
    "Total transport stream rate for the program (Units: Mbits/sec)"
::= { enc1P30totalTSRateEntry 1 }

enc1P31pipTable OBJECT-TYPE
    SYNTAX SEQUENCE OF Enc1P31pipEntry
    MAX-ACCESS not-accessible
    STATUS     current
    DESCRIPTION
    "
    Name      : PIP
    Menu Path : /TS Mux
    Details   : Specifies whether PIP encoding is on or off.
    "
::= { enc1Params 31 }

enc1P31pipEntry OBJECT-TYPE
    SYNTAX Enc1P31pipEntry
    MAX-ACCESS not-accessible
    STATUS     current
    DESCRIPTION
    "Table Entry for PIP"
    INDEX { slotId }
::= { enc1P31pipTable 1 }

Enc1P31pipEntry ::= SEQUENCE {
    enc1P31pipValue    Enc1E27enumObj
}

enc1P31pipValue OBJECT-TYPE
    SYNTAX     Enc1E27enumObj
    MAX-ACCESS read-write
    STATUS     current
    DESCRIPTION
    "Specifies whether PIP encoding is on or off."
::= { enc1P31pipEntry 1 }

enc1P32transportStreamIDTable OBJECT-TYPE
    SYNTAX SEQUENCE OF Enc1P32transportStreamIDEntry
    MAX-ACCESS not-accessible
    STATUS     current
    DESCRIPTION
    "
    Name      : Transport Stream ID
    Menu Path : /TS Mux/MPEG Parameters/Main Program
    Units     : 
    Precision : 0
    Low Range : 1
    High Range: 65535
    Details   : Specifies the transport stream ID (TSID) for the output stream.

     NOTE: Precision/Units/Ranges represent the state of the
           parameter during the MIB generation, and does not
           neccessary reflect the current state of the parameter
    "
::= { enc1Params 32 }

enc1P32transportStreamIDEntry OBJECT-TYPE
    SYNTAX Enc1P32transportStreamIDEntry
    MAX-ACCESS not-accessible
    STATUS     current
    DESCRIPTION
    "Table Entry for Transport Stream ID"
    INDEX { slotId }
::= { enc1P32transportStreamIDTable 1 }

Enc1P32transportStreamIDEntry ::= SEQUENCE {
    enc1P32transportStreamIDValue    INTEGER
}

enc1P32transportStreamIDValue OBJECT-TYPE
    SYNTAX     INTEGER
    MAX-ACCESS read-write
    STATUS     current
    DESCRIPTION
    "Specifies the transport stream ID (TSID) for the output stream."
::= { enc1P32transportStreamIDEntry 1 }

enc1P33networkIDTable OBJECT-TYPE
    SYNTAX SEQUENCE OF Enc1P33networkIDEntry
    MAX-ACCESS not-accessible
    STATUS     current
    DESCRIPTION
    "
    Name      : Network ID
    Menu Path : /TS Mux/MPEG Parameters/Main Program
    Units     : 
    Precision : 0
    Low Range : 0
    High Range: 65535
    Details   : Specifies the Network ID for the output stream.

     NOTE: Precision/Units/Ranges represent the state of the
           parameter during the MIB generation, and does not
           neccessary reflect the current state of the parameter
    "
::= { enc1Params 33 }

enc1P33networkIDEntry OBJECT-TYPE
    SYNTAX Enc1P33networkIDEntry
    MAX-ACCESS not-accessible
    STATUS     current
    DESCRIPTION
    "Table Entry for Network ID"
    INDEX { slotId }
::= { enc1P33networkIDTable 1 }

Enc1P33networkIDEntry ::= SEQUENCE {
    enc1P33networkIDValue    INTEGER
}

enc1P33networkIDValue OBJECT-TYPE
    SYNTAX     INTEGER
    MAX-ACCESS read-write
    STATUS     current
    DESCRIPTION
    "Specifies the Network ID for the output stream."
::= { enc1P33networkIDEntry 1 }

enc1P34programNumberTable OBJECT-TYPE
    SYNTAX SEQUENCE OF Enc1P34programNumberEntry
    MAX-ACCESS not-accessible
    STATUS     current
    DESCRIPTION
    "
    Name      : Program Number
    Menu Path : /TS Mux/MPEG Parameters/Main Program
    Units     : 
    Precision : 0
    Low Range : 1
    High Range: 65535
    Details   : Specifies the program number for the program in the PAT.

     NOTE: Precision/Units/Ranges represent the state of the
           parameter during the MIB generation, and does not
           neccessary reflect the current state of the parameter
    "
::= { enc1Params 34 }

enc1P34programNumberEntry OBJECT-TYPE
    SYNTAX Enc1P34programNumberEntry
    MAX-ACCESS not-accessible
    STATUS     current
    DESCRIPTION
    "Table Entry for Program Number"
    INDEX { slotId }
::= { enc1P34programNumberTable 1 }

Enc1P34programNumberEntry ::= SEQUENCE {
    enc1P34programNumberValue    INTEGER
}

enc1P34programNumberValue OBJECT-TYPE
    SYNTAX     INTEGER
    MAX-ACCESS read-write
    STATUS     current
    DESCRIPTION
    "Specifies the program number for the program in the PAT."
::= { enc1P34programNumberEntry 1 }

enc1P35pmtpidTable OBJECT-TYPE
    SYNTAX SEQUENCE OF Enc1P35pmtpidEntry
    MAX-ACCESS not-accessible
    STATUS     current
    DESCRIPTION
    "
    Name      : PMT PID
    Menu Path : /TS Mux/MPEG Parameters/Main Program
    Units     : 
    Precision : 0
    Low Range : 16
    High Range: 8190
    Details   : Specifies the PMT PID for the program.

     NOTE: Precision/Units/Ranges represent the state of the
           parameter during the MIB generation, and does not
           neccessary reflect the current state of the parameter
    "
::= { enc1Params 35 }

enc1P35pmtpidEntry OBJECT-TYPE
    SYNTAX Enc1P35pmtpidEntry
    MAX-ACCESS not-accessible
    STATUS     current
    DESCRIPTION
    "Table Entry for PMT PID"
    INDEX { slotId }
::= { enc1P35pmtpidTable 1 }

Enc1P35pmtpidEntry ::= SEQUENCE {
    enc1P35pmtpidValue    INTEGER
}

enc1P35pmtpidValue OBJECT-TYPE
    SYNTAX     INTEGER
    MAX-ACCESS read-write
    STATUS     current
    DESCRIPTION
    "Specifies the PMT PID for the program."
::= { enc1P35pmtpidEntry 1 }

enc1P36pcrpidTable OBJECT-TYPE
    SYNTAX SEQUENCE OF Enc1P36pcrpidEntry
    MAX-ACCESS not-accessible
    STATUS     current
    DESCRIPTION
    "
    Name      : PCR PID
    Menu Path : /TS Mux/MPEG Parameters/Main Program
    Units     : 
    Precision : 0
    Low Range : 16
    High Range: 8190
    Details   : Specifies the PCR PID for the program.

     NOTE: Precision/Units/Ranges represent the state of the
           parameter during the MIB generation, and does not
           neccessary reflect the current state of the parameter
    "
::= { enc1Params 36 }

enc1P36pcrpidEntry OBJECT-TYPE
    SYNTAX Enc1P36pcrpidEntry
    MAX-ACCESS not-accessible
    STATUS     current
    DESCRIPTION
    "Table Entry for PCR PID"
    INDEX { slotId }
::= { enc1P36pcrpidTable 1 }

Enc1P36pcrpidEntry ::= SEQUENCE {
    enc1P36pcrpidValue    INTEGER
}

enc1P36pcrpidValue OBJECT-TYPE
    SYNTAX     INTEGER
    MAX-ACCESS read-write
    STATUS     current
    DESCRIPTION
    "Specifies the PCR PID for the program."
::= { enc1P36pcrpidEntry 1 }

enc1P37videoPIDTable OBJECT-TYPE
    SYNTAX SEQUENCE OF Enc1P37videoPIDEntry
    MAX-ACCESS not-accessible
    STATUS     current
    DESCRIPTION
    "
    Name      : Video PID
    Menu Path : /TS Mux/MPEG Parameters/Main Program
    Units     : 
    Precision : 0
    Low Range : 16
    High Range: 8190
    Details   : Specifies the Video PID for the program.

     NOTE: Precision/Units/Ranges represent the state of the
           parameter during the MIB generation, and does not
           neccessary reflect the current state of the parameter
    "
::= { enc1Params 37 }

enc1P37videoPIDEntry OBJECT-TYPE
    SYNTAX Enc1P37videoPIDEntry
    MAX-ACCESS not-accessible
    STATUS     current
    DESCRIPTION
    "Table Entry for Video PID"
    INDEX { slotId }
::= { enc1P37videoPIDTable 1 }

Enc1P37videoPIDEntry ::= SEQUENCE {
    enc1P37videoPIDValue    INTEGER
}

enc1P37videoPIDValue OBJECT-TYPE
    SYNTAX     INTEGER
    MAX-ACCESS read-write
    STATUS     current
    DESCRIPTION
    "Specifies the Video PID for the program."
::= { enc1P37videoPIDEntry 1 }

enc1P38audio1PIDTable OBJECT-TYPE
    SYNTAX SEQUENCE OF Enc1P38audio1PIDEntry
    MAX-ACCESS not-accessible
    STATUS     current
    DESCRIPTION
    "
    Name      : Audio 1 PID
    Menu Path : /TS Mux/MPEG Parameters/Main Program
    Units     : 
    Precision : 0
    Low Range : 16
    High Range: 8190
    Details   : Specifies the Audio1 PID for the program.

     NOTE: Precision/Units/Ranges represent the state of the
           parameter during the MIB generation, and does not
           neccessary reflect the current state of the parameter
    "
::= { enc1Params 38 }

enc1P38audio1PIDEntry OBJECT-TYPE
    SYNTAX Enc1P38audio1PIDEntry
    MAX-ACCESS not-accessible
    STATUS     current
    DESCRIPTION
    "Table Entry for Audio 1 PID"
    INDEX { slotId }
::= { enc1P38audio1PIDTable 1 }

Enc1P38audio1PIDEntry ::= SEQUENCE {
    enc1P38audio1PIDValue    INTEGER
}

enc1P38audio1PIDValue OBJECT-TYPE
    SYNTAX     INTEGER
    MAX-ACCESS read-write
    STATUS     current
    DESCRIPTION
    "Specifies the Audio1 PID for the program."
::= { enc1P38audio1PIDEntry 1 }

enc1P39audio2PIDTable OBJECT-TYPE
    SYNTAX SEQUENCE OF Enc1P39audio2PIDEntry
    MAX-ACCESS not-accessible
    STATUS     current
    DESCRIPTION
    "
    Name      : Audio 2 PID
    Menu Path : /TS Mux/MPEG Parameters/Main Program
    Units     : 
    Precision : 0
    Low Range : 16
    High Range: 8190
    Details   : Specifies the Audio2 PID for the program.

     NOTE: Precision/Units/Ranges represent the state of the
           parameter during the MIB generation, and does not
           neccessary reflect the current state of the parameter
    "
::= { enc1Params 39 }

enc1P39audio2PIDEntry OBJECT-TYPE
    SYNTAX Enc1P39audio2PIDEntry
    MAX-ACCESS not-accessible
    STATUS     current
    DESCRIPTION
    "Table Entry for Audio 2 PID"
    INDEX { slotId }
::= { enc1P39audio2PIDTable 1 }

Enc1P39audio2PIDEntry ::= SEQUENCE {
    enc1P39audio2PIDValue    INTEGER
}

enc1P39audio2PIDValue OBJECT-TYPE
    SYNTAX     INTEGER
    MAX-ACCESS read-write
    STATUS     current
    DESCRIPTION
    "Specifies the Audio2 PID for the program."
::= { enc1P39audio2PIDEntry 1 }

enc1P40audio3PIDTable OBJECT-TYPE
    SYNTAX SEQUENCE OF Enc1P40audio3PIDEntry
    MAX-ACCESS not-accessible
    STATUS     current
    DESCRIPTION
    "
    Name      : Audio 3 PID
    Menu Path : /TS Mux/MPEG Parameters/Main Program
    Units     : 
    Precision : 0
    Low Range : 16
    High Range: 8190
    Details   : Specifies the Audio3 PID for the program.

     NOTE: Precision/Units/Ranges represent the state of the
           parameter during the MIB generation, and does not
           neccessary reflect the current state of the parameter
    "
::= { enc1Params 40 }

enc1P40audio3PIDEntry OBJECT-TYPE
    SYNTAX Enc1P40audio3PIDEntry
    MAX-ACCESS not-accessible
    STATUS     current
    DESCRIPTION
    "Table Entry for Audio 3 PID"
    INDEX { slotId }
::= { enc1P40audio3PIDTable 1 }

Enc1P40audio3PIDEntry ::= SEQUENCE {
    enc1P40audio3PIDValue    INTEGER
}

enc1P40audio3PIDValue OBJECT-TYPE
    SYNTAX     INTEGER
    MAX-ACCESS read-write
    STATUS     current
    DESCRIPTION
    "Specifies the Audio3 PID for the program."
::= { enc1P40audio3PIDEntry 1 }

enc1P41audio4PIDTable OBJECT-TYPE
    SYNTAX SEQUENCE OF Enc1P41audio4PIDEntry
    MAX-ACCESS not-accessible
    STATUS     current
    DESCRIPTION
    "
    Name      : Audio 4 PID
    Menu Path : /TS Mux/MPEG Parameters/Main Program
    Units     : 
    Precision : 0
    Low Range : 16
    High Range: 8190
    Details   : Specifies the Audio4 PID for the program.

     NOTE: Precision/Units/Ranges represent the state of the
           parameter during the MIB generation, and does not
           neccessary reflect the current state of the parameter
    "
::= { enc1Params 41 }

enc1P41audio4PIDEntry OBJECT-TYPE
    SYNTAX Enc1P41audio4PIDEntry
    MAX-ACCESS not-accessible
    STATUS     current
    DESCRIPTION
    "Table Entry for Audio 4 PID"
    INDEX { slotId }
::= { enc1P41audio4PIDTable 1 }

Enc1P41audio4PIDEntry ::= SEQUENCE {
    enc1P41audio4PIDValue    INTEGER
}

enc1P41audio4PIDValue OBJECT-TYPE
    SYNTAX     INTEGER
    MAX-ACCESS read-write
    STATUS     current
    DESCRIPTION
    "Specifies the Audio4 PID for the program."
::= { enc1P41audio4PIDEntry 1 }

enc1P42audio5PIDTable OBJECT-TYPE
    SYNTAX SEQUENCE OF Enc1P42audio5PIDEntry
    MAX-ACCESS not-accessible
    STATUS     current
    DESCRIPTION
    "
    Name      : Audio 5 PID
    Menu Path : /TS Mux/MPEG Parameters/Main Program
    Units     : 
    Precision : 0
    Low Range : 16
    High Range: 8190
    Details   : Specifies the Audio5 PID for the program.

     NOTE: Precision/Units/Ranges represent the state of the
           parameter during the MIB generation, and does not
           neccessary reflect the current state of the parameter
    "
::= { enc1Params 42 }

enc1P42audio5PIDEntry OBJECT-TYPE
    SYNTAX Enc1P42audio5PIDEntry
    MAX-ACCESS not-accessible
    STATUS     current
    DESCRIPTION
    "Table Entry for Audio 5 PID"
    INDEX { slotId }
::= { enc1P42audio5PIDTable 1 }

Enc1P42audio5PIDEntry ::= SEQUENCE {
    enc1P42audio5PIDValue    INTEGER
}

enc1P42audio5PIDValue OBJECT-TYPE
    SYNTAX     INTEGER
    MAX-ACCESS read-write
    STATUS     current
    DESCRIPTION
    "Specifies the Audio5 PID for the program."
::= { enc1P42audio5PIDEntry 1 }

enc1P43audio6PIDTable OBJECT-TYPE
    SYNTAX SEQUENCE OF Enc1P43audio6PIDEntry
    MAX-ACCESS not-accessible
    STATUS     current
    DESCRIPTION
    "
    Name      : Audio 6 PID
    Menu Path : /TS Mux/MPEG Parameters/Main Program
    Units     : 
    Precision : 0
    Low Range : 16
    High Range: 8190
    Details   : Specifies the Audio6 PID for the program.

     NOTE: Precision/Units/Ranges represent the state of the
           parameter during the MIB generation, and does not
           neccessary reflect the current state of the parameter
    "
::= { enc1Params 43 }

enc1P43audio6PIDEntry OBJECT-TYPE
    SYNTAX Enc1P43audio6PIDEntry
    MAX-ACCESS not-accessible
    STATUS     current
    DESCRIPTION
    "Table Entry for Audio 6 PID"
    INDEX { slotId }
::= { enc1P43audio6PIDTable 1 }

Enc1P43audio6PIDEntry ::= SEQUENCE {
    enc1P43audio6PIDValue    INTEGER
}

enc1P43audio6PIDValue OBJECT-TYPE
    SYNTAX     INTEGER
    MAX-ACCESS read-write
    STATUS     current
    DESCRIPTION
    "Specifies the Audio6 PID for the program."
::= { enc1P43audio6PIDEntry 1 }

enc1P44audio7PIDTable OBJECT-TYPE
    SYNTAX SEQUENCE OF Enc1P44audio7PIDEntry
    MAX-ACCESS not-accessible
    STATUS     current
    DESCRIPTION
    "
    Name      : Audio 7 PID
    Menu Path : /TS Mux/MPEG Parameters/Main Program
    Units     : 
    Precision : 0
    Low Range : 16
    High Range: 8190
    Details   : Specifies the Audio7 PID for the program.

     NOTE: Precision/Units/Ranges represent the state of the
           parameter during the MIB generation, and does not
           neccessary reflect the current state of the parameter
    "
::= { enc1Params 44 }

enc1P44audio7PIDEntry OBJECT-TYPE
    SYNTAX Enc1P44audio7PIDEntry
    MAX-ACCESS not-accessible
    STATUS     current
    DESCRIPTION
    "Table Entry for Audio 7 PID"
    INDEX { slotId }
::= { enc1P44audio7PIDTable 1 }

Enc1P44audio7PIDEntry ::= SEQUENCE {
    enc1P44audio7PIDValue    INTEGER
}

enc1P44audio7PIDValue OBJECT-TYPE
    SYNTAX     INTEGER
    MAX-ACCESS read-write
    STATUS     current
    DESCRIPTION
    "Specifies the Audio7 PID for the program."
::= { enc1P44audio7PIDEntry 1 }

enc1P45audio8PIDTable OBJECT-TYPE
    SYNTAX SEQUENCE OF Enc1P45audio8PIDEntry
    MAX-ACCESS not-accessible
    STATUS     current
    DESCRIPTION
    "
    Name      : Audio 8 PID
    Menu Path : /TS Mux/MPEG Parameters/Main Program
    Units     : 
    Precision : 0
    Low Range : 16
    High Range: 8190
    Details   : Specifies the Audio8 PID for the program.

     NOTE: Precision/Units/Ranges represent the state of the
           parameter during the MIB generation, and does not
           neccessary reflect the current state of the parameter
    "
::= { enc1Params 45 }

enc1P45audio8PIDEntry OBJECT-TYPE
    SYNTAX Enc1P45audio8PIDEntry
    MAX-ACCESS not-accessible
    STATUS     current
    DESCRIPTION
    "Table Entry for Audio 8 PID"
    INDEX { slotId }
::= { enc1P45audio8PIDTable 1 }

Enc1P45audio8PIDEntry ::= SEQUENCE {
    enc1P45audio8PIDValue    INTEGER
}

enc1P45audio8PIDValue OBJECT-TYPE
    SYNTAX     INTEGER
    MAX-ACCESS read-write
    STATUS     current
    DESCRIPTION
    "Specifies the Audio8 PID for the program."
::= { enc1P45audio8PIDEntry 1 }

enc1P46vbipidTable OBJECT-TYPE
    SYNTAX SEQUENCE OF Enc1P46vbipidEntry
    MAX-ACCESS not-accessible
    STATUS     current
    DESCRIPTION
    "
    Name      : VBI PID
    Menu Path : /TS Mux/MPEG Parameters/Main Program
    Units     : 
    Precision : 0
    Low Range : 16
    High Range: 8190
    Details   : Specifies the PID used for VBI data.

     NOTE: Precision/Units/Ranges represent the state of the
           parameter during the MIB generation, and does not
           neccessary reflect the current state of the parameter
    "
::= { enc1Params 46 }

enc1P46vbipidEntry OBJECT-TYPE
    SYNTAX Enc1P46vbipidEntry
    MAX-ACCESS not-accessible
    STATUS     current
    DESCRIPTION
    "Table Entry for VBI PID"
    INDEX { slotId }
::= { enc1P46vbipidTable 1 }

Enc1P46vbipidEntry ::= SEQUENCE {
    enc1P46vbipidValue    INTEGER
}

enc1P46vbipidValue OBJECT-TYPE
    SYNTAX     INTEGER
    MAX-ACCESS read-write
    STATUS     current
    DESCRIPTION
    "Specifies the PID used for VBI data."
::= { enc1P46vbipidEntry 1 }

enc1P47teletextPIDTable OBJECT-TYPE
    SYNTAX SEQUENCE OF Enc1P47teletextPIDEntry
    MAX-ACCESS not-accessible
    STATUS     current
    DESCRIPTION
    "
    Name      : Teletext PID
    Menu Path : /TS Mux/MPEG Parameters/Main Program
    Units     : 
    Precision : 0
    Low Range : 16
    High Range: 8190
    Details   : Specifies the PID used for TTX data.

     NOTE: Precision/Units/Ranges represent the state of the
           parameter during the MIB generation, and does not
           neccessary reflect the current state of the parameter
    "
::= { enc1Params 47 }

enc1P47teletextPIDEntry OBJECT-TYPE
    SYNTAX Enc1P47teletextPIDEntry
    MAX-ACCESS not-accessible
    STATUS     current
    DESCRIPTION
    "Table Entry for Teletext PID"
    INDEX { slotId }
::= { enc1P47teletextPIDTable 1 }

Enc1P47teletextPIDEntry ::= SEQUENCE {
    enc1P47teletextPIDValue    INTEGER
}

enc1P47teletextPIDValue OBJECT-TYPE
    SYNTAX     INTEGER
    MAX-ACCESS read-write
    STATUS     current
    DESCRIPTION
    "Specifies the PID used for TTX data."
::= { enc1P47teletextPIDEntry 1 }

enc1P48vancpidTable OBJECT-TYPE
    SYNTAX SEQUENCE OF Enc1P48vancpidEntry
    MAX-ACCESS not-accessible
    STATUS     current
    DESCRIPTION
    "
    Name      : VANC PID
    Menu Path : /TS Mux/MPEG Parameters/Main Program
    Units     : 
    Precision : 0
    Low Range : 16
    High Range: 8190
    Details   : Specifies the PID used for VANC data.

     NOTE: Precision/Units/Ranges represent the state of the
           parameter during the MIB generation, and does not
           neccessary reflect the current state of the parameter
    "
::= { enc1Params 48 }

enc1P48vancpidEntry OBJECT-TYPE
    SYNTAX Enc1P48vancpidEntry
    MAX-ACCESS not-accessible
    STATUS     current
    DESCRIPTION
    "Table Entry for VANC PID"
    INDEX { slotId }
::= { enc1P48vancpidTable 1 }

Enc1P48vancpidEntry ::= SEQUENCE {
    enc1P48vancpidValue    INTEGER
}

enc1P48vancpidValue OBJECT-TYPE
    SYNTAX     INTEGER
    MAX-ACCESS read-write
    STATUS     current
    DESCRIPTION
    "Specifies the PID used for VANC data."
::= { enc1P48vancpidEntry 1 }

enc1P49klvpidTable OBJECT-TYPE
    SYNTAX SEQUENCE OF Enc1P49klvpidEntry
    MAX-ACCESS not-accessible
    STATUS     current
    DESCRIPTION
    "
    Name      : KLV PID
    Menu Path : /TS Mux/MPEG Parameters/Main Program
    Units     : 
    Precision : 0
    Low Range : 16
    High Range: 8190
    Details   : Specifies the PID used for KLV data.

     NOTE: Precision/Units/Ranges represent the state of the
           parameter during the MIB generation, and does not
           neccessary reflect the current state of the parameter
    "
::= { enc1Params 49 }

enc1P49klvpidEntry OBJECT-TYPE
    SYNTAX Enc1P49klvpidEntry
    MAX-ACCESS not-accessible
    STATUS     current
    DESCRIPTION
    "Table Entry for KLV PID"
    INDEX { slotId }
::= { enc1P49klvpidTable 1 }

Enc1P49klvpidEntry ::= SEQUENCE {
    enc1P49klvpidValue    INTEGER
}

enc1P49klvpidValue OBJECT-TYPE
    SYNTAX     INTEGER
    MAX-ACCESS read-write
    STATUS     current
    DESCRIPTION
    "Specifies the PID used for KLV data."
::= { enc1P49klvpidEntry 1 }

enc1P50dataPIDTable OBJECT-TYPE
    SYNTAX SEQUENCE OF Enc1P50dataPIDEntry
    MAX-ACCESS not-accessible
    STATUS     current
    DESCRIPTION
    "
    Name      : Data PID
    Menu Path : /TS Mux/MPEG Parameters/Main Program
    Units     : 
    Precision : 0
    Low Range : 16
    High Range: 8190
    Details   : Specifies the PID used for out of band data.

     NOTE: Precision/Units/Ranges represent the state of the
           parameter during the MIB generation, and does not
           neccessary reflect the current state of the parameter
    "
::= { enc1Params 50 }

enc1P50dataPIDEntry OBJECT-TYPE
    SYNTAX Enc1P50dataPIDEntry
    MAX-ACCESS not-accessible
    STATUS     current
    DESCRIPTION
    "Table Entry for Data PID"
    INDEX { slotId }
::= { enc1P50dataPIDTable 1 }

Enc1P50dataPIDEntry ::= SEQUENCE {
    enc1P50dataPIDValue    INTEGER
}

enc1P50dataPIDValue OBJECT-TYPE
    SYNTAX     INTEGER
    MAX-ACCESS read-write
    STATUS     current
    DESCRIPTION
    "Specifies the PID used for out of band data."
::= { enc1P50dataPIDEntry 1 }

enc1P51splicePIDTable OBJECT-TYPE
    SYNTAX SEQUENCE OF Enc1P51splicePIDEntry
    MAX-ACCESS not-accessible
    STATUS     current
    DESCRIPTION
    "
    Name      : Splice PID
    Menu Path : /TS Mux/MPEG Parameters/Main Program
    Units     : 
    Precision : 0
    Low Range : 16
    High Range: 8190
    Details   : Specifies the PID used for Splice data.

     NOTE: Precision/Units/Ranges represent the state of the
           parameter during the MIB generation, and does not
           neccessary reflect the current state of the parameter
    "
::= { enc1Params 51 }

enc1P51splicePIDEntry OBJECT-TYPE
    SYNTAX Enc1P51splicePIDEntry
    MAX-ACCESS not-accessible
    STATUS     current
    DESCRIPTION
    "Table Entry for Splice PID"
    INDEX { slotId }
::= { enc1P51splicePIDTable 1 }

Enc1P51splicePIDEntry ::= SEQUENCE {
    enc1P51splicePIDValue    INTEGER
}

enc1P51splicePIDValue OBJECT-TYPE
    SYNTAX     INTEGER
    MAX-ACCESS read-write
    STATUS     current
    DESCRIPTION
    "Specifies the PID used for Splice data."
::= { enc1P51splicePIDEntry 1 }

enc1P52transportStreamIDTable OBJECT-TYPE
    SYNTAX SEQUENCE OF Enc1P52transportStreamIDEntry
    MAX-ACCESS not-accessible
    STATUS     current
    DESCRIPTION
    "
    Name      : Transport Stream ID
    Menu Path : /TS Mux/MPEG Parameters/Pip Program
    Units     : 
    Precision : 0
    Low Range : 1
    High Range: 65535
    Details   : Specifies the transport stream ID (TSID) for the PIP output transport stream.

     NOTE: Precision/Units/Ranges represent the state of the
           parameter during the MIB generation, and does not
           neccessary reflect the current state of the parameter
    "
::= { enc1Params 52 }

enc1P52transportStreamIDEntry OBJECT-TYPE
    SYNTAX Enc1P52transportStreamIDEntry
    MAX-ACCESS not-accessible
    STATUS     current
    DESCRIPTION
    "Table Entry for Transport Stream ID"
    INDEX { slotId }
::= { enc1P52transportStreamIDTable 1 }

Enc1P52transportStreamIDEntry ::= SEQUENCE {
    enc1P52transportStreamIDValue    INTEGER
}

enc1P52transportStreamIDValue OBJECT-TYPE
    SYNTAX     INTEGER
    MAX-ACCESS read-write
    STATUS     current
    DESCRIPTION
    "Specifies the transport stream ID (TSID) for the PIP output transport stream."
::= { enc1P52transportStreamIDEntry 1 }

enc1P53programNumberTable OBJECT-TYPE
    SYNTAX SEQUENCE OF Enc1P53programNumberEntry
    MAX-ACCESS not-accessible
    STATUS     current
    DESCRIPTION
    "
    Name      : Program Number
    Menu Path : /TS Mux/MPEG Parameters/Pip Program
    Units     : 
    Precision : 0
    Low Range : 1
    High Range: 65535
    Details   : Specifies the program number for the PIP program in the PAT.

     NOTE: Precision/Units/Ranges represent the state of the
           parameter during the MIB generation, and does not
           neccessary reflect the current state of the parameter
    "
::= { enc1Params 53 }

enc1P53programNumberEntry OBJECT-TYPE
    SYNTAX Enc1P53programNumberEntry
    MAX-ACCESS not-accessible
    STATUS     current
    DESCRIPTION
    "Table Entry for Program Number"
    INDEX { slotId }
::= { enc1P53programNumberTable 1 }

Enc1P53programNumberEntry ::= SEQUENCE {
    enc1P53programNumberValue    INTEGER
}

enc1P53programNumberValue OBJECT-TYPE
    SYNTAX     INTEGER
    MAX-ACCESS read-write
    STATUS     current
    DESCRIPTION
    "Specifies the program number for the PIP program in the PAT."
::= { enc1P53programNumberEntry 1 }

enc1P54pmtpidTable OBJECT-TYPE
    SYNTAX SEQUENCE OF Enc1P54pmtpidEntry
    MAX-ACCESS not-accessible
    STATUS     current
    DESCRIPTION
    "
    Name      : PMT PID
    Menu Path : /TS Mux/MPEG Parameters/Pip Program
    Units     : 
    Precision : 0
    Low Range : 16
    High Range: 8190
    Details   : Specifies the PMT PID for the PIP program.

     NOTE: Precision/Units/Ranges represent the state of the
           parameter during the MIB generation, and does not
           neccessary reflect the current state of the parameter
    "
::= { enc1Params 54 }

enc1P54pmtpidEntry OBJECT-TYPE
    SYNTAX Enc1P54pmtpidEntry
    MAX-ACCESS not-accessible
    STATUS     current
    DESCRIPTION
    "Table Entry for PMT PID"
    INDEX { slotId }
::= { enc1P54pmtpidTable 1 }

Enc1P54pmtpidEntry ::= SEQUENCE {
    enc1P54pmtpidValue    INTEGER
}

enc1P54pmtpidValue OBJECT-TYPE
    SYNTAX     INTEGER
    MAX-ACCESS read-write
    STATUS     current
    DESCRIPTION
    "Specifies the PMT PID for the PIP program."
::= { enc1P54pmtpidEntry 1 }

enc1P55pcrpidTable OBJECT-TYPE
    SYNTAX SEQUENCE OF Enc1P55pcrpidEntry
    MAX-ACCESS not-accessible
    STATUS     current
    DESCRIPTION
    "
    Name      : PCR PID
    Menu Path : /TS Mux/MPEG Parameters/Pip Program
    Units     : 
    Precision : 0
    Low Range : 16
    High Range: 8190
    Details   : Specifies the PCR PID for the PIP program.

     NOTE: Precision/Units/Ranges represent the state of the
           parameter during the MIB generation, and does not
           neccessary reflect the current state of the parameter
    "
::= { enc1Params 55 }

enc1P55pcrpidEntry OBJECT-TYPE
    SYNTAX Enc1P55pcrpidEntry
    MAX-ACCESS not-accessible
    STATUS     current
    DESCRIPTION
    "Table Entry for PCR PID"
    INDEX { slotId }
::= { enc1P55pcrpidTable 1 }

Enc1P55pcrpidEntry ::= SEQUENCE {
    enc1P55pcrpidValue    INTEGER
}

enc1P55pcrpidValue OBJECT-TYPE
    SYNTAX     INTEGER
    MAX-ACCESS read-write
    STATUS     current
    DESCRIPTION
    "Specifies the PCR PID for the PIP program."
::= { enc1P55pcrpidEntry 1 }

enc1P56videoPIDTable OBJECT-TYPE
    SYNTAX SEQUENCE OF Enc1P56videoPIDEntry
    MAX-ACCESS not-accessible
    STATUS     current
    DESCRIPTION
    "
    Name      : Video PID
    Menu Path : /TS Mux/MPEG Parameters/Pip Program
    Units     : 
    Precision : 0
    Low Range : 16
    High Range: 8190
    Details   : Specifies the video PID for the PIP program.

     NOTE: Precision/Units/Ranges represent the state of the
           parameter during the MIB generation, and does not
           neccessary reflect the current state of the parameter
    "
::= { enc1Params 56 }

enc1P56videoPIDEntry OBJECT-TYPE
    SYNTAX Enc1P56videoPIDEntry
    MAX-ACCESS not-accessible
    STATUS     current
    DESCRIPTION
    "Table Entry for Video PID"
    INDEX { slotId }
::= { enc1P56videoPIDTable 1 }

Enc1P56videoPIDEntry ::= SEQUENCE {
    enc1P56videoPIDValue    INTEGER
}

enc1P56videoPIDValue OBJECT-TYPE
    SYNTAX     INTEGER
    MAX-ACCESS read-write
    STATUS     current
    DESCRIPTION
    "Specifies the video PID for the PIP program."
::= { enc1P56videoPIDEntry 1 }

enc1P57audio1PIDTable OBJECT-TYPE
    SYNTAX SEQUENCE OF Enc1P57audio1PIDEntry
    MAX-ACCESS not-accessible
    STATUS     current
    DESCRIPTION
    "
    Name      : Audio 1 PID
    Menu Path : /TS Mux/MPEG Parameters/Pip Program
    Units     : 
    Precision : 0
    Low Range : 16
    High Range: 8190
    Details   : Specifies the Audio1 PID for the PIP program.

     NOTE: Precision/Units/Ranges represent the state of the
           parameter during the MIB generation, and does not
           neccessary reflect the current state of the parameter
    "
::= { enc1Params 57 }

enc1P57audio1PIDEntry OBJECT-TYPE
    SYNTAX Enc1P57audio1PIDEntry
    MAX-ACCESS not-accessible
    STATUS     current
    DESCRIPTION
    "Table Entry for Audio 1 PID"
    INDEX { slotId }
::= { enc1P57audio1PIDTable 1 }

Enc1P57audio1PIDEntry ::= SEQUENCE {
    enc1P57audio1PIDValue    INTEGER
}

enc1P57audio1PIDValue OBJECT-TYPE
    SYNTAX     INTEGER
    MAX-ACCESS read-write
    STATUS     current
    DESCRIPTION
    "Specifies the Audio1 PID for the PIP program."
::= { enc1P57audio1PIDEntry 1 }

enc1P58audio2PIDTable OBJECT-TYPE
    SYNTAX SEQUENCE OF Enc1P58audio2PIDEntry
    MAX-ACCESS not-accessible
    STATUS     current
    DESCRIPTION
    "
    Name      : Audio 2 PID
    Menu Path : /TS Mux/MPEG Parameters/Pip Program
    Units     : 
    Precision : 0
    Low Range : 16
    High Range: 8190
    Details   : Specifies the Audio2 PID for the PIP program.

     NOTE: Precision/Units/Ranges represent the state of the
           parameter during the MIB generation, and does not
           neccessary reflect the current state of the parameter
    "
::= { enc1Params 58 }

enc1P58audio2PIDEntry OBJECT-TYPE
    SYNTAX Enc1P58audio2PIDEntry
    MAX-ACCESS not-accessible
    STATUS     current
    DESCRIPTION
    "Table Entry for Audio 2 PID"
    INDEX { slotId }
::= { enc1P58audio2PIDTable 1 }

Enc1P58audio2PIDEntry ::= SEQUENCE {
    enc1P58audio2PIDValue    INTEGER
}

enc1P58audio2PIDValue OBJECT-TYPE
    SYNTAX     INTEGER
    MAX-ACCESS read-write
    STATUS     current
    DESCRIPTION
    "Specifies the Audio2 PID for the PIP program."
::= { enc1P58audio2PIDEntry 1 }

enc1P59audio3PIDTable OBJECT-TYPE
    SYNTAX SEQUENCE OF Enc1P59audio3PIDEntry
    MAX-ACCESS not-accessible
    STATUS     current
    DESCRIPTION
    "
    Name      : Audio 3 PID
    Menu Path : /TS Mux/MPEG Parameters/Pip Program
    Units     : 
    Precision : 0
    Low Range : 16
    High Range: 8190
    Details   : Specifies the Audio3 PID for the PIP program.

     NOTE: Precision/Units/Ranges represent the state of the
           parameter during the MIB generation, and does not
           neccessary reflect the current state of the parameter
    "
::= { enc1Params 59 }

enc1P59audio3PIDEntry OBJECT-TYPE
    SYNTAX Enc1P59audio3PIDEntry
    MAX-ACCESS not-accessible
    STATUS     current
    DESCRIPTION
    "Table Entry for Audio 3 PID"
    INDEX { slotId }
::= { enc1P59audio3PIDTable 1 }

Enc1P59audio3PIDEntry ::= SEQUENCE {
    enc1P59audio3PIDValue    INTEGER
}

enc1P59audio3PIDValue OBJECT-TYPE
    SYNTAX     INTEGER
    MAX-ACCESS read-write
    STATUS     current
    DESCRIPTION
    "Specifies the Audio3 PID for the PIP program."
::= { enc1P59audio3PIDEntry 1 }

enc1P60audio4PIDTable OBJECT-TYPE
    SYNTAX SEQUENCE OF Enc1P60audio4PIDEntry
    MAX-ACCESS not-accessible
    STATUS     current
    DESCRIPTION
    "
    Name      : Audio 4 PID
    Menu Path : /TS Mux/MPEG Parameters/Pip Program
    Units     : 
    Precision : 0
    Low Range : 16
    High Range: 8190
    Details   : Specifies the Audio4 PID for the PIP program.

     NOTE: Precision/Units/Ranges represent the state of the
           parameter during the MIB generation, and does not
           neccessary reflect the current state of the parameter
    "
::= { enc1Params 60 }

enc1P60audio4PIDEntry OBJECT-TYPE
    SYNTAX Enc1P60audio4PIDEntry
    MAX-ACCESS not-accessible
    STATUS     current
    DESCRIPTION
    "Table Entry for Audio 4 PID"
    INDEX { slotId }
::= { enc1P60audio4PIDTable 1 }

Enc1P60audio4PIDEntry ::= SEQUENCE {
    enc1P60audio4PIDValue    INTEGER
}

enc1P60audio4PIDValue OBJECT-TYPE
    SYNTAX     INTEGER
    MAX-ACCESS read-write
    STATUS     current
    DESCRIPTION
    "Specifies the Audio4 PID for the PIP program."
::= { enc1P60audio4PIDEntry 1 }

enc1P61audio5PIDTable OBJECT-TYPE
    SYNTAX SEQUENCE OF Enc1P61audio5PIDEntry
    MAX-ACCESS not-accessible
    STATUS     current
    DESCRIPTION
    "
    Name      : Audio 5 PID
    Menu Path : /TS Mux/MPEG Parameters/Pip Program
    Units     : 
    Precision : 0
    Low Range : 16
    High Range: 8190
    Details   : Specifies the Audio5 PID for the PIP program.

     NOTE: Precision/Units/Ranges represent the state of the
           parameter during the MIB generation, and does not
           neccessary reflect the current state of the parameter
    "
::= { enc1Params 61 }

enc1P61audio5PIDEntry OBJECT-TYPE
    SYNTAX Enc1P61audio5PIDEntry
    MAX-ACCESS not-accessible
    STATUS     current
    DESCRIPTION
    "Table Entry for Audio 5 PID"
    INDEX { slotId }
::= { enc1P61audio5PIDTable 1 }

Enc1P61audio5PIDEntry ::= SEQUENCE {
    enc1P61audio5PIDValue    INTEGER
}

enc1P61audio5PIDValue OBJECT-TYPE
    SYNTAX     INTEGER
    MAX-ACCESS read-write
    STATUS     current
    DESCRIPTION
    "Specifies the Audio5 PID for the PIP program."
::= { enc1P61audio5PIDEntry 1 }

enc1P62audio6PIDTable OBJECT-TYPE
    SYNTAX SEQUENCE OF Enc1P62audio6PIDEntry
    MAX-ACCESS not-accessible
    STATUS     current
    DESCRIPTION
    "
    Name      : Audio 6 PID
    Menu Path : /TS Mux/MPEG Parameters/Pip Program
    Units     : 
    Precision : 0
    Low Range : 16
    High Range: 8190
    Details   : Specifies the Audio6 PID for the PIP program.

     NOTE: Precision/Units/Ranges represent the state of the
           parameter during the MIB generation, and does not
           neccessary reflect the current state of the parameter
    "
::= { enc1Params 62 }

enc1P62audio6PIDEntry OBJECT-TYPE
    SYNTAX Enc1P62audio6PIDEntry
    MAX-ACCESS not-accessible
    STATUS     current
    DESCRIPTION
    "Table Entry for Audio 6 PID"
    INDEX { slotId }
::= { enc1P62audio6PIDTable 1 }

Enc1P62audio6PIDEntry ::= SEQUENCE {
    enc1P62audio6PIDValue    INTEGER
}

enc1P62audio6PIDValue OBJECT-TYPE
    SYNTAX     INTEGER
    MAX-ACCESS read-write
    STATUS     current
    DESCRIPTION
    "Specifies the Audio6 PID for the PIP program."
::= { enc1P62audio6PIDEntry 1 }

enc1P63audio7PIDTable OBJECT-TYPE
    SYNTAX SEQUENCE OF Enc1P63audio7PIDEntry
    MAX-ACCESS not-accessible
    STATUS     current
    DESCRIPTION
    "
    Name      : Audio 7 PID
    Menu Path : /TS Mux/MPEG Parameters/Pip Program
    Units     : 
    Precision : 0
    Low Range : 16
    High Range: 8190
    Details   : Specifies the Audio7 PID for the PIP program.

     NOTE: Precision/Units/Ranges represent the state of the
           parameter during the MIB generation, and does not
           neccessary reflect the current state of the parameter
    "
::= { enc1Params 63 }

enc1P63audio7PIDEntry OBJECT-TYPE
    SYNTAX Enc1P63audio7PIDEntry
    MAX-ACCESS not-accessible
    STATUS     current
    DESCRIPTION
    "Table Entry for Audio 7 PID"
    INDEX { slotId }
::= { enc1P63audio7PIDTable 1 }

Enc1P63audio7PIDEntry ::= SEQUENCE {
    enc1P63audio7PIDValue    INTEGER
}

enc1P63audio7PIDValue OBJECT-TYPE
    SYNTAX     INTEGER
    MAX-ACCESS read-write
    STATUS     current
    DESCRIPTION
    "Specifies the Audio7 PID for the PIP program."
::= { enc1P63audio7PIDEntry 1 }

enc1P64audio8PIDTable OBJECT-TYPE
    SYNTAX SEQUENCE OF Enc1P64audio8PIDEntry
    MAX-ACCESS not-accessible
    STATUS     current
    DESCRIPTION
    "
    Name      : Audio 8 PID
    Menu Path : /TS Mux/MPEG Parameters/Pip Program
    Units     : 
    Precision : 0
    Low Range : 16
    High Range: 8190
    Details   : Specifies the Audio8 PID for the PIP program.

     NOTE: Precision/Units/Ranges represent the state of the
           parameter during the MIB generation, and does not
           neccessary reflect the current state of the parameter
    "
::= { enc1Params 64 }

enc1P64audio8PIDEntry OBJECT-TYPE
    SYNTAX Enc1P64audio8PIDEntry
    MAX-ACCESS not-accessible
    STATUS     current
    DESCRIPTION
    "Table Entry for Audio 8 PID"
    INDEX { slotId }
::= { enc1P64audio8PIDTable 1 }

Enc1P64audio8PIDEntry ::= SEQUENCE {
    enc1P64audio8PIDValue    INTEGER
}

enc1P64audio8PIDValue OBJECT-TYPE
    SYNTAX     INTEGER
    MAX-ACCESS read-write
    STATUS     current
    DESCRIPTION
    "Specifies the Audio8 PID for the PIP program."
::= { enc1P64audio8PIDEntry 1 }

enc1P65serviceProviderNameTable OBJECT-TYPE
    SYNTAX SEQUENCE OF Enc1P65serviceProviderNameEntry
    MAX-ACCESS not-accessible
    STATUS     current
    DESCRIPTION
    "
    Name      : Service Provider Name
    Menu Path : /TS Mux/SI Parameters
    Details   : Specifies the service provider name. It is used in the service descriptor of the SDT table.
    "
::= { enc1Params 65 }

enc1P65serviceProviderNameEntry OBJECT-TYPE
    SYNTAX Enc1P65serviceProviderNameEntry
    MAX-ACCESS not-accessible
    STATUS     current
    DESCRIPTION
    "Table Entry for Service Provider Name"
    INDEX { slotId }
::= { enc1P65serviceProviderNameTable 1 }

Enc1P65serviceProviderNameEntry ::= SEQUENCE {
    enc1P65serviceProviderNameValue    DisplayString
}

enc1P65serviceProviderNameValue OBJECT-TYPE
    SYNTAX     DisplayString
    MAX-ACCESS read-write
    STATUS     current
    DESCRIPTION
    "Specifies the service provider name. It is used in the service descriptor of the SDT table."
::= { enc1P65serviceProviderNameEntry 1 }

enc1P66parentalRatingTable OBJECT-TYPE
    SYNTAX SEQUENCE OF Enc1P66parentalRatingEntry
    MAX-ACCESS not-accessible
    STATUS     current
    DESCRIPTION
    "
    Name      : Parental Rating
    Menu Path : /TS Mux/SI Parameters
    Units     : 
    Precision : 0
    Low Range : 0
    High Range: 127
    Details   : In ISDB mode, specifies parental rating for program. A value of zero means the descriptor is not inserted.

     NOTE: Precision/Units/Ranges represent the state of the
           parameter during the MIB generation, and does not
           neccessary reflect the current state of the parameter
    "
::= { enc1Params 66 }

enc1P66parentalRatingEntry OBJECT-TYPE
    SYNTAX Enc1P66parentalRatingEntry
    MAX-ACCESS not-accessible
    STATUS     current
    DESCRIPTION
    "Table Entry for Parental Rating"
    INDEX { slotId }
::= { enc1P66parentalRatingTable 1 }

Enc1P66parentalRatingEntry ::= SEQUENCE {
    enc1P66parentalRatingValue    INTEGER
}

enc1P66parentalRatingValue OBJECT-TYPE
    SYNTAX     INTEGER
    MAX-ACCESS read-write
    STATUS     current
    DESCRIPTION
    "In ISDB mode, specifies parental rating for program. A value of zero means the descriptor is not inserted."
::= { enc1P66parentalRatingEntry 1 }

enc1P67countryTable OBJECT-TYPE
    SYNTAX SEQUENCE OF Enc1P67countryEntry
    MAX-ACCESS not-accessible
    STATUS     current
    DESCRIPTION
    "
    Name      : Country
    Menu Path : /TS Mux/SI Parameters
    Details   : Specifies a 3 character country code ISO 3166-1. This value is used in the ISDB parental rating descriptor of the PMT.
    "
::= { enc1Params 67 }

enc1P67countryEntry OBJECT-TYPE
    SYNTAX Enc1P67countryEntry
    MAX-ACCESS not-accessible
    STATUS     current
    DESCRIPTION
    "Table Entry for Country"
    INDEX { slotId }
::= { enc1P67countryTable 1 }

Enc1P67countryEntry ::= SEQUENCE {
    enc1P67countryValue    DisplayString
}

enc1P67countryValue OBJECT-TYPE
    SYNTAX     DisplayString
    MAX-ACCESS read-write
    STATUS     current
    DESCRIPTION
    "Specifies a 3 character country code ISO 3166-1. This value is used in the ISDB parental rating descriptor of the PMT."
::= { enc1P67countryEntry 1 }

enc1P68ttxdesc1LanguageTable OBJECT-TYPE
    SYNTAX SEQUENCE OF Enc1P68ttxdesc1LanguageEntry
    MAX-ACCESS not-accessible
    STATUS     current
    DESCRIPTION
    "
    Name      : TTX Desc 1 Language
    Menu Path : /TS Mux/SI Parameters
    Details   : Specifies the teletext descriptor language code.
    "
::= { enc1Params 68 }

enc1P68ttxdesc1LanguageEntry OBJECT-TYPE
    SYNTAX Enc1P68ttxdesc1LanguageEntry
    MAX-ACCESS not-accessible
    STATUS     current
    DESCRIPTION
    "Table Entry for TTX Desc 1 Language"
    INDEX { slotId }
::= { enc1P68ttxdesc1LanguageTable 1 }

Enc1P68ttxdesc1LanguageEntry ::= SEQUENCE {
    enc1P68ttxdesc1LanguageValue    DisplayString
}

enc1P68ttxdesc1LanguageValue OBJECT-TYPE
    SYNTAX     DisplayString
    MAX-ACCESS read-write
    STATUS     current
    DESCRIPTION
    "Specifies the teletext descriptor language code."
::= { enc1P68ttxdesc1LanguageEntry 1 }

enc1P69ttxdesc1TypeTable OBJECT-TYPE
    SYNTAX SEQUENCE OF Enc1P69ttxdesc1TypeEntry
    MAX-ACCESS not-accessible
    STATUS     current
    DESCRIPTION
    "
    Name      : TTX Desc 1 Type
    Menu Path : /TS Mux/SI Parameters
    Units     : 
    Precision : 0
    Low Range : 0
    High Range: 31
    Details   : Specifies teletext descriptor type.

     NOTE: Precision/Units/Ranges represent the state of the
           parameter during the MIB generation, and does not
           neccessary reflect the current state of the parameter
    "
::= { enc1Params 69 }

enc1P69ttxdesc1TypeEntry OBJECT-TYPE
    SYNTAX Enc1P69ttxdesc1TypeEntry
    MAX-ACCESS not-accessible
    STATUS     current
    DESCRIPTION
    "Table Entry for TTX Desc 1 Type"
    INDEX { slotId }
::= { enc1P69ttxdesc1TypeTable 1 }

Enc1P69ttxdesc1TypeEntry ::= SEQUENCE {
    enc1P69ttxdesc1TypeValue    INTEGER
}

enc1P69ttxdesc1TypeValue OBJECT-TYPE
    SYNTAX     INTEGER
    MAX-ACCESS read-write
    STATUS     current
    DESCRIPTION
    "Specifies teletext descriptor type."
::= { enc1P69ttxdesc1TypeEntry 1 }

enc1P70ttxdesc1MagazineNumberTable OBJECT-TYPE
    SYNTAX SEQUENCE OF Enc1P70ttxdesc1MagazineNumberEntry
    MAX-ACCESS not-accessible
    STATUS     current
    DESCRIPTION
    "
    Name      : TTX Desc 1 Magazine Number
    Menu Path : /TS Mux/SI Parameters
    Units     : 
    Precision : 0
    Low Range : 1
    High Range: 8
    Details   : Specifies teletext magazine number.

     NOTE: Precision/Units/Ranges represent the state of the
           parameter during the MIB generation, and does not
           neccessary reflect the current state of the parameter
    "
::= { enc1Params 70 }

enc1P70ttxdesc1MagazineNumberEntry OBJECT-TYPE
    SYNTAX Enc1P70ttxdesc1MagazineNumberEntry
    MAX-ACCESS not-accessible
    STATUS     current
    DESCRIPTION
    "Table Entry for TTX Desc 1 Magazine Number"
    INDEX { slotId }
::= { enc1P70ttxdesc1MagazineNumberTable 1 }

Enc1P70ttxdesc1MagazineNumberEntry ::= SEQUENCE {
    enc1P70ttxdesc1MagazineNumberValue    INTEGER
}

enc1P70ttxdesc1MagazineNumberValue OBJECT-TYPE
    SYNTAX     INTEGER
    MAX-ACCESS read-write
    STATUS     current
    DESCRIPTION
    "Specifies teletext magazine number."
::= { enc1P70ttxdesc1MagazineNumberEntry 1 }

enc1P71ttxdesc1PageNumberTable OBJECT-TYPE
    SYNTAX SEQUENCE OF Enc1P71ttxdesc1PageNumberEntry
    MAX-ACCESS not-accessible
    STATUS     current
    DESCRIPTION
    "
    Name      : TTX Desc 1 Page Number
    Menu Path : /TS Mux/SI Parameters
    Units     : 
    Precision : 0
    Low Range : 0
    High Range: 255
    Details   : Specifies teletext page number.

     NOTE: Precision/Units/Ranges represent the state of the
           parameter during the MIB generation, and does not
           neccessary reflect the current state of the parameter
    "
::= { enc1Params 71 }

enc1P71ttxdesc1PageNumberEntry OBJECT-TYPE
    SYNTAX Enc1P71ttxdesc1PageNumberEntry
    MAX-ACCESS not-accessible
    STATUS     current
    DESCRIPTION
    "Table Entry for TTX Desc 1 Page Number"
    INDEX { slotId }
::= { enc1P71ttxdesc1PageNumberTable 1 }

Enc1P71ttxdesc1PageNumberEntry ::= SEQUENCE {
    enc1P71ttxdesc1PageNumberValue    INTEGER
}

enc1P71ttxdesc1PageNumberValue OBJECT-TYPE
    SYNTAX     INTEGER
    MAX-ACCESS read-write
    STATUS     current
    DESCRIPTION
    "Specifies teletext page number."
::= { enc1P71ttxdesc1PageNumberEntry 1 }

enc1P72ttxdesc2LanguageTable OBJECT-TYPE
    SYNTAX SEQUENCE OF Enc1P72ttxdesc2LanguageEntry
    MAX-ACCESS not-accessible
    STATUS     current
    DESCRIPTION
    "
    Name      : TTX Desc 2 Language
    Menu Path : /TS Mux/SI Parameters
    Details   : Specifies teletext descriptor language code.
    "
::= { enc1Params 72 }

enc1P72ttxdesc2LanguageEntry OBJECT-TYPE
    SYNTAX Enc1P72ttxdesc2LanguageEntry
    MAX-ACCESS not-accessible
    STATUS     current
    DESCRIPTION
    "Table Entry for TTX Desc 2 Language"
    INDEX { slotId }
::= { enc1P72ttxdesc2LanguageTable 1 }

Enc1P72ttxdesc2LanguageEntry ::= SEQUENCE {
    enc1P72ttxdesc2LanguageValue    DisplayString
}

enc1P72ttxdesc2LanguageValue OBJECT-TYPE
    SYNTAX     DisplayString
    MAX-ACCESS read-write
    STATUS     current
    DESCRIPTION
    "Specifies teletext descriptor language code."
::= { enc1P72ttxdesc2LanguageEntry 1 }

enc1P73ttxdesc2TypeTable OBJECT-TYPE
    SYNTAX SEQUENCE OF Enc1P73ttxdesc2TypeEntry
    MAX-ACCESS not-accessible
    STATUS     current
    DESCRIPTION
    "
    Name      : TTX Desc 2 Type
    Menu Path : /TS Mux/SI Parameters
    Units     : 
    Precision : 0
    Low Range : 0
    High Range: 31
    Details   : Specifies teletext descriptor type.

     NOTE: Precision/Units/Ranges represent the state of the
           parameter during the MIB generation, and does not
           neccessary reflect the current state of the parameter
    "
::= { enc1Params 73 }

enc1P73ttxdesc2TypeEntry OBJECT-TYPE
    SYNTAX Enc1P73ttxdesc2TypeEntry
    MAX-ACCESS not-accessible
    STATUS     current
    DESCRIPTION
    "Table Entry for TTX Desc 2 Type"
    INDEX { slotId }
::= { enc1P73ttxdesc2TypeTable 1 }

Enc1P73ttxdesc2TypeEntry ::= SEQUENCE {
    enc1P73ttxdesc2TypeValue    INTEGER
}

enc1P73ttxdesc2TypeValue OBJECT-TYPE
    SYNTAX     INTEGER
    MAX-ACCESS read-write
    STATUS     current
    DESCRIPTION
    "Specifies teletext descriptor type."
::= { enc1P73ttxdesc2TypeEntry 1 }

enc1P74ttxdesc2MagazineNumberTable OBJECT-TYPE
    SYNTAX SEQUENCE OF Enc1P74ttxdesc2MagazineNumberEntry
    MAX-ACCESS not-accessible
    STATUS     current
    DESCRIPTION
    "
    Name      : TTX Desc 2 Magazine Number
    Menu Path : /TS Mux/SI Parameters
    Units     : 
    Precision : 0
    Low Range : 1
    High Range: 8
    Details   : Specifies teletext magazine number.

     NOTE: Precision/Units/Ranges represent the state of the
           parameter during the MIB generation, and does not
           neccessary reflect the current state of the parameter
    "
::= { enc1Params 74 }

enc1P74ttxdesc2MagazineNumberEntry OBJECT-TYPE
    SYNTAX Enc1P74ttxdesc2MagazineNumberEntry
    MAX-ACCESS not-accessible
    STATUS     current
    DESCRIPTION
    "Table Entry for TTX Desc 2 Magazine Number"
    INDEX { slotId }
::= { enc1P74ttxdesc2MagazineNumberTable 1 }

Enc1P74ttxdesc2MagazineNumberEntry ::= SEQUENCE {
    enc1P74ttxdesc2MagazineNumberValue    INTEGER
}

enc1P74ttxdesc2MagazineNumberValue OBJECT-TYPE
    SYNTAX     INTEGER
    MAX-ACCESS read-write
    STATUS     current
    DESCRIPTION
    "Specifies teletext magazine number."
::= { enc1P74ttxdesc2MagazineNumberEntry 1 }

enc1P75ttxdesc2PageNumberTable OBJECT-TYPE
    SYNTAX SEQUENCE OF Enc1P75ttxdesc2PageNumberEntry
    MAX-ACCESS not-accessible
    STATUS     current
    DESCRIPTION
    "
    Name      : TTX Desc 2 Page Number
    Menu Path : /TS Mux/SI Parameters
    Units     : 
    Precision : 0
    Low Range : 0
    High Range: 255
    Details   : Specifies teletext page number.

     NOTE: Precision/Units/Ranges represent the state of the
           parameter during the MIB generation, and does not
           neccessary reflect the current state of the parameter
    "
::= { enc1Params 75 }

enc1P75ttxdesc2PageNumberEntry OBJECT-TYPE
    SYNTAX Enc1P75ttxdesc2PageNumberEntry
    MAX-ACCESS not-accessible
    STATUS     current
    DESCRIPTION
    "Table Entry for TTX Desc 2 Page Number"
    INDEX { slotId }
::= { enc1P75ttxdesc2PageNumberTable 1 }

Enc1P75ttxdesc2PageNumberEntry ::= SEQUENCE {
    enc1P75ttxdesc2PageNumberValue    INTEGER
}

enc1P75ttxdesc2PageNumberValue OBJECT-TYPE
    SYNTAX     INTEGER
    MAX-ACCESS read-write
    STATUS     current
    DESCRIPTION
    "Specifies teletext page number."
::= { enc1P75ttxdesc2PageNumberEntry 1 }

enc1P76ttxdesc3LanguageTable OBJECT-TYPE
    SYNTAX SEQUENCE OF Enc1P76ttxdesc3LanguageEntry
    MAX-ACCESS not-accessible
    STATUS     current
    DESCRIPTION
    "
    Name      : TTX Desc 3 Language
    Menu Path : /TS Mux/SI Parameters
    Details   : Specifies teletext descriptor language code.
    "
::= { enc1Params 76 }

enc1P76ttxdesc3LanguageEntry OBJECT-TYPE
    SYNTAX Enc1P76ttxdesc3LanguageEntry
    MAX-ACCESS not-accessible
    STATUS     current
    DESCRIPTION
    "Table Entry for TTX Desc 3 Language"
    INDEX { slotId }
::= { enc1P76ttxdesc3LanguageTable 1 }

Enc1P76ttxdesc3LanguageEntry ::= SEQUENCE {
    enc1P76ttxdesc3LanguageValue    DisplayString
}

enc1P76ttxdesc3LanguageValue OBJECT-TYPE
    SYNTAX     DisplayString
    MAX-ACCESS read-write
    STATUS     current
    DESCRIPTION
    "Specifies teletext descriptor language code."
::= { enc1P76ttxdesc3LanguageEntry 1 }

enc1P77ttxdesc3TypeTable OBJECT-TYPE
    SYNTAX SEQUENCE OF Enc1P77ttxdesc3TypeEntry
    MAX-ACCESS not-accessible
    STATUS     current
    DESCRIPTION
    "
    Name      : TTX Desc 3 Type
    Menu Path : /TS Mux/SI Parameters
    Units     : 
    Precision : 0
    Low Range : 0
    High Range: 31
    Details   : Specifies teletext descriptor type.

     NOTE: Precision/Units/Ranges represent the state of the
           parameter during the MIB generation, and does not
           neccessary reflect the current state of the parameter
    "
::= { enc1Params 77 }

enc1P77ttxdesc3TypeEntry OBJECT-TYPE
    SYNTAX Enc1P77ttxdesc3TypeEntry
    MAX-ACCESS not-accessible
    STATUS     current
    DESCRIPTION
    "Table Entry for TTX Desc 3 Type"
    INDEX { slotId }
::= { enc1P77ttxdesc3TypeTable 1 }

Enc1P77ttxdesc3TypeEntry ::= SEQUENCE {
    enc1P77ttxdesc3TypeValue    INTEGER
}

enc1P77ttxdesc3TypeValue OBJECT-TYPE
    SYNTAX     INTEGER
    MAX-ACCESS read-write
    STATUS     current
    DESCRIPTION
    "Specifies teletext descriptor type."
::= { enc1P77ttxdesc3TypeEntry 1 }

enc1P78ttxdesc3MagazineNumberTable OBJECT-TYPE
    SYNTAX SEQUENCE OF Enc1P78ttxdesc3MagazineNumberEntry
    MAX-ACCESS not-accessible
    STATUS     current
    DESCRIPTION
    "
    Name      : TTX Desc 3 Magazine Number
    Menu Path : /TS Mux/SI Parameters
    Units     : 
    Precision : 0
    Low Range : 1
    High Range: 8
    Details   : Specifies teletext magazine number.

     NOTE: Precision/Units/Ranges represent the state of the
           parameter during the MIB generation, and does not
           neccessary reflect the current state of the parameter
    "
::= { enc1Params 78 }

enc1P78ttxdesc3MagazineNumberEntry OBJECT-TYPE
    SYNTAX Enc1P78ttxdesc3MagazineNumberEntry
    MAX-ACCESS not-accessible
    STATUS     current
    DESCRIPTION
    "Table Entry for TTX Desc 3 Magazine Number"
    INDEX { slotId }
::= { enc1P78ttxdesc3MagazineNumberTable 1 }

Enc1P78ttxdesc3MagazineNumberEntry ::= SEQUENCE {
    enc1P78ttxdesc3MagazineNumberValue    INTEGER
}

enc1P78ttxdesc3MagazineNumberValue OBJECT-TYPE
    SYNTAX     INTEGER
    MAX-ACCESS read-write
    STATUS     current
    DESCRIPTION
    "Specifies teletext magazine number."
::= { enc1P78ttxdesc3MagazineNumberEntry 1 }

enc1P79ttxdesc3PageNumberTable OBJECT-TYPE
    SYNTAX SEQUENCE OF Enc1P79ttxdesc3PageNumberEntry
    MAX-ACCESS not-accessible
    STATUS     current
    DESCRIPTION
    "
    Name      : TTX Desc 3 Page Number
    Menu Path : /TS Mux/SI Parameters
    Units     : 
    Precision : 0
    Low Range : 0
    High Range: 255
    Details   : Specifies teletext page number.

     NOTE: Precision/Units/Ranges represent the state of the
           parameter during the MIB generation, and does not
           neccessary reflect the current state of the parameter
    "
::= { enc1Params 79 }

enc1P79ttxdesc3PageNumberEntry OBJECT-TYPE
    SYNTAX Enc1P79ttxdesc3PageNumberEntry
    MAX-ACCESS not-accessible
    STATUS     current
    DESCRIPTION
    "Table Entry for TTX Desc 3 Page Number"
    INDEX { slotId }
::= { enc1P79ttxdesc3PageNumberTable 1 }

Enc1P79ttxdesc3PageNumberEntry ::= SEQUENCE {
    enc1P79ttxdesc3PageNumberValue    INTEGER
}

enc1P79ttxdesc3PageNumberValue OBJECT-TYPE
    SYNTAX     INTEGER
    MAX-ACCESS read-write
    STATUS     current
    DESCRIPTION
    "Specifies teletext page number."
::= { enc1P79ttxdesc3PageNumberEntry 1 }

enc1P80ttxdesc4LanguageTable OBJECT-TYPE
    SYNTAX SEQUENCE OF Enc1P80ttxdesc4LanguageEntry
    MAX-ACCESS not-accessible
    STATUS     current
    DESCRIPTION
    "
    Name      : TTX Desc 4 Language
    Menu Path : /TS Mux/SI Parameters
    Details   : Specifies teletext descriptor language code.
    "
::= { enc1Params 80 }

enc1P80ttxdesc4LanguageEntry OBJECT-TYPE
    SYNTAX Enc1P80ttxdesc4LanguageEntry
    MAX-ACCESS not-accessible
    STATUS     current
    DESCRIPTION
    "Table Entry for TTX Desc 4 Language"
    INDEX { slotId }
::= { enc1P80ttxdesc4LanguageTable 1 }

Enc1P80ttxdesc4LanguageEntry ::= SEQUENCE {
    enc1P80ttxdesc4LanguageValue    DisplayString
}

enc1P80ttxdesc4LanguageValue OBJECT-TYPE
    SYNTAX     DisplayString
    MAX-ACCESS read-write
    STATUS     current
    DESCRIPTION
    "Specifies teletext descriptor language code."
::= { enc1P80ttxdesc4LanguageEntry 1 }

enc1P81ttxdesc4TypeTable OBJECT-TYPE
    SYNTAX SEQUENCE OF Enc1P81ttxdesc4TypeEntry
    MAX-ACCESS not-accessible
    STATUS     current
    DESCRIPTION
    "
    Name      : TTX Desc 4 Type
    Menu Path : /TS Mux/SI Parameters
    Units     : 
    Precision : 0
    Low Range : 0
    High Range: 31
    Details   : Specifies teletext descriptor type.

     NOTE: Precision/Units/Ranges represent the state of the
           parameter during the MIB generation, and does not
           neccessary reflect the current state of the parameter
    "
::= { enc1Params 81 }

enc1P81ttxdesc4TypeEntry OBJECT-TYPE
    SYNTAX Enc1P81ttxdesc4TypeEntry
    MAX-ACCESS not-accessible
    STATUS     current
    DESCRIPTION
    "Table Entry for TTX Desc 4 Type"
    INDEX { slotId }
::= { enc1P81ttxdesc4TypeTable 1 }

Enc1P81ttxdesc4TypeEntry ::= SEQUENCE {
    enc1P81ttxdesc4TypeValue    INTEGER
}

enc1P81ttxdesc4TypeValue OBJECT-TYPE
    SYNTAX     INTEGER
    MAX-ACCESS read-write
    STATUS     current
    DESCRIPTION
    "Specifies teletext descriptor type."
::= { enc1P81ttxdesc4TypeEntry 1 }

enc1P82ttxdesc4MagazineNumberTable OBJECT-TYPE
    SYNTAX SEQUENCE OF Enc1P82ttxdesc4MagazineNumberEntry
    MAX-ACCESS not-accessible
    STATUS     current
    DESCRIPTION
    "
    Name      : TTX Desc 4 Magazine Number
    Menu Path : /TS Mux/SI Parameters
    Units     : 
    Precision : 0
    Low Range : 1
    High Range: 8
    Details   : Specifies teletext magazine number.

     NOTE: Precision/Units/Ranges represent the state of the
           parameter during the MIB generation, and does not
           neccessary reflect the current state of the parameter
    "
::= { enc1Params 82 }

enc1P82ttxdesc4MagazineNumberEntry OBJECT-TYPE
    SYNTAX Enc1P82ttxdesc4MagazineNumberEntry
    MAX-ACCESS not-accessible
    STATUS     current
    DESCRIPTION
    "Table Entry for TTX Desc 4 Magazine Number"
    INDEX { slotId }
::= { enc1P82ttxdesc4MagazineNumberTable 1 }

Enc1P82ttxdesc4MagazineNumberEntry ::= SEQUENCE {
    enc1P82ttxdesc4MagazineNumberValue    INTEGER
}

enc1P82ttxdesc4MagazineNumberValue OBJECT-TYPE
    SYNTAX     INTEGER
    MAX-ACCESS read-write
    STATUS     current
    DESCRIPTION
    "Specifies teletext magazine number."
::= { enc1P82ttxdesc4MagazineNumberEntry 1 }

enc1P83ttxdesc4PageNumberTable OBJECT-TYPE
    SYNTAX SEQUENCE OF Enc1P83ttxdesc4PageNumberEntry
    MAX-ACCESS not-accessible
    STATUS     current
    DESCRIPTION
    "
    Name      : TTX Desc 4 Page Number
    Menu Path : /TS Mux/SI Parameters
    Units     : 
    Precision : 0
    Low Range : 0
    High Range: 255
    Details   : Specifies teletext page number.

     NOTE: Precision/Units/Ranges represent the state of the
           parameter during the MIB generation, and does not
           neccessary reflect the current state of the parameter
    "
::= { enc1Params 83 }

enc1P83ttxdesc4PageNumberEntry OBJECT-TYPE
    SYNTAX Enc1P83ttxdesc4PageNumberEntry
    MAX-ACCESS not-accessible
    STATUS     current
    DESCRIPTION
    "Table Entry for TTX Desc 4 Page Number"
    INDEX { slotId }
::= { enc1P83ttxdesc4PageNumberTable 1 }

Enc1P83ttxdesc4PageNumberEntry ::= SEQUENCE {
    enc1P83ttxdesc4PageNumberValue    INTEGER
}

enc1P83ttxdesc4PageNumberValue OBJECT-TYPE
    SYNTAX     INTEGER
    MAX-ACCESS read-write
    STATUS     current
    DESCRIPTION
    "Specifies teletext page number."
::= { enc1P83ttxdesc4PageNumberEntry 1 }

enc1P84ttxdesc5LanguageTable OBJECT-TYPE
    SYNTAX SEQUENCE OF Enc1P84ttxdesc5LanguageEntry
    MAX-ACCESS not-accessible
    STATUS     current
    DESCRIPTION
    "
    Name      : TTX Desc 5 Language
    Menu Path : /TS Mux/SI Parameters
    Details   : Specifies teletext descriptor language code.
    "
::= { enc1Params 84 }

enc1P84ttxdesc5LanguageEntry OBJECT-TYPE
    SYNTAX Enc1P84ttxdesc5LanguageEntry
    MAX-ACCESS not-accessible
    STATUS     current
    DESCRIPTION
    "Table Entry for TTX Desc 5 Language"
    INDEX { slotId }
::= { enc1P84ttxdesc5LanguageTable 1 }

Enc1P84ttxdesc5LanguageEntry ::= SEQUENCE {
    enc1P84ttxdesc5LanguageValue    DisplayString
}

enc1P84ttxdesc5LanguageValue OBJECT-TYPE
    SYNTAX     DisplayString
    MAX-ACCESS read-write
    STATUS     current
    DESCRIPTION
    "Specifies teletext descriptor language code."
::= { enc1P84ttxdesc5LanguageEntry 1 }

enc1P85ttxdesc5TypeTable OBJECT-TYPE
    SYNTAX SEQUENCE OF Enc1P85ttxdesc5TypeEntry
    MAX-ACCESS not-accessible
    STATUS     current
    DESCRIPTION
    "
    Name      : TTX Desc 5 Type
    Menu Path : /TS Mux/SI Parameters
    Units     : 
    Precision : 0
    Low Range : 0
    High Range: 31
    Details   : Specifies teletext descriptor type.

     NOTE: Precision/Units/Ranges represent the state of the
           parameter during the MIB generation, and does not
           neccessary reflect the current state of the parameter
    "
::= { enc1Params 85 }

enc1P85ttxdesc5TypeEntry OBJECT-TYPE
    SYNTAX Enc1P85ttxdesc5TypeEntry
    MAX-ACCESS not-accessible
    STATUS     current
    DESCRIPTION
    "Table Entry for TTX Desc 5 Type"
    INDEX { slotId }
::= { enc1P85ttxdesc5TypeTable 1 }

Enc1P85ttxdesc5TypeEntry ::= SEQUENCE {
    enc1P85ttxdesc5TypeValue    INTEGER
}

enc1P85ttxdesc5TypeValue OBJECT-TYPE
    SYNTAX     INTEGER
    MAX-ACCESS read-write
    STATUS     current
    DESCRIPTION
    "Specifies teletext descriptor type."
::= { enc1P85ttxdesc5TypeEntry 1 }

enc1P86ttxdesc5MagazineNumberTable OBJECT-TYPE
    SYNTAX SEQUENCE OF Enc1P86ttxdesc5MagazineNumberEntry
    MAX-ACCESS not-accessible
    STATUS     current
    DESCRIPTION
    "
    Name      : TTX Desc 5 Magazine Number
    Menu Path : /TS Mux/SI Parameters
    Units     : 
    Precision : 0
    Low Range : 1
    High Range: 8
    Details   : Specifies teletext magazine number.

     NOTE: Precision/Units/Ranges represent the state of the
           parameter during the MIB generation, and does not
           neccessary reflect the current state of the parameter
    "
::= { enc1Params 86 }

enc1P86ttxdesc5MagazineNumberEntry OBJECT-TYPE
    SYNTAX Enc1P86ttxdesc5MagazineNumberEntry
    MAX-ACCESS not-accessible
    STATUS     current
    DESCRIPTION
    "Table Entry for TTX Desc 5 Magazine Number"
    INDEX { slotId }
::= { enc1P86ttxdesc5MagazineNumberTable 1 }

Enc1P86ttxdesc5MagazineNumberEntry ::= SEQUENCE {
    enc1P86ttxdesc5MagazineNumberValue    INTEGER
}

enc1P86ttxdesc5MagazineNumberValue OBJECT-TYPE
    SYNTAX     INTEGER
    MAX-ACCESS read-write
    STATUS     current
    DESCRIPTION
    "Specifies teletext magazine number."
::= { enc1P86ttxdesc5MagazineNumberEntry 1 }

enc1P87ttxdesc5PageNumberTable OBJECT-TYPE
    SYNTAX SEQUENCE OF Enc1P87ttxdesc5PageNumberEntry
    MAX-ACCESS not-accessible
    STATUS     current
    DESCRIPTION
    "
    Name      : TTX Desc 5 Page Number
    Menu Path : /TS Mux/SI Parameters
    Units     : 
    Precision : 0
    Low Range : 0
    High Range: 255
    Details   : Specifies teletext page number.

     NOTE: Precision/Units/Ranges represent the state of the
           parameter during the MIB generation, and does not
           neccessary reflect the current state of the parameter
    "
::= { enc1Params 87 }

enc1P87ttxdesc5PageNumberEntry OBJECT-TYPE
    SYNTAX Enc1P87ttxdesc5PageNumberEntry
    MAX-ACCESS not-accessible
    STATUS     current
    DESCRIPTION
    "Table Entry for TTX Desc 5 Page Number"
    INDEX { slotId }
::= { enc1P87ttxdesc5PageNumberTable 1 }

Enc1P87ttxdesc5PageNumberEntry ::= SEQUENCE {
    enc1P87ttxdesc5PageNumberValue    INTEGER
}

enc1P87ttxdesc5PageNumberValue OBJECT-TYPE
    SYNTAX     INTEGER
    MAX-ACCESS read-write
    STATUS     current
    DESCRIPTION
    "Specifies teletext page number."
::= { enc1P87ttxdesc5PageNumberEntry 1 }

enc1P88ttxdesc6LanguageTable OBJECT-TYPE
    SYNTAX SEQUENCE OF Enc1P88ttxdesc6LanguageEntry
    MAX-ACCESS not-accessible
    STATUS     current
    DESCRIPTION
    "
    Name      : TTX Desc 6 Language
    Menu Path : /TS Mux/SI Parameters
    Details   : Specifies teletext descriptor language code.
    "
::= { enc1Params 88 }

enc1P88ttxdesc6LanguageEntry OBJECT-TYPE
    SYNTAX Enc1P88ttxdesc6LanguageEntry
    MAX-ACCESS not-accessible
    STATUS     current
    DESCRIPTION
    "Table Entry for TTX Desc 6 Language"
    INDEX { slotId }
::= { enc1P88ttxdesc6LanguageTable 1 }

Enc1P88ttxdesc6LanguageEntry ::= SEQUENCE {
    enc1P88ttxdesc6LanguageValue    DisplayString
}

enc1P88ttxdesc6LanguageValue OBJECT-TYPE
    SYNTAX     DisplayString
    MAX-ACCESS read-write
    STATUS     current
    DESCRIPTION
    "Specifies teletext descriptor language code."
::= { enc1P88ttxdesc6LanguageEntry 1 }

enc1P89ttxdesc6TypeTable OBJECT-TYPE
    SYNTAX SEQUENCE OF Enc1P89ttxdesc6TypeEntry
    MAX-ACCESS not-accessible
    STATUS     current
    DESCRIPTION
    "
    Name      : TTX Desc 6 Type
    Menu Path : /TS Mux/SI Parameters
    Units     : 
    Precision : 0
    Low Range : 0
    High Range: 31
    Details   : Specifies teletext descriptor type.

     NOTE: Precision/Units/Ranges represent the state of the
           parameter during the MIB generation, and does not
           neccessary reflect the current state of the parameter
    "
::= { enc1Params 89 }

enc1P89ttxdesc6TypeEntry OBJECT-TYPE
    SYNTAX Enc1P89ttxdesc6TypeEntry
    MAX-ACCESS not-accessible
    STATUS     current
    DESCRIPTION
    "Table Entry for TTX Desc 6 Type"
    INDEX { slotId }
::= { enc1P89ttxdesc6TypeTable 1 }

Enc1P89ttxdesc6TypeEntry ::= SEQUENCE {
    enc1P89ttxdesc6TypeValue    INTEGER
}

enc1P89ttxdesc6TypeValue OBJECT-TYPE
    SYNTAX     INTEGER
    MAX-ACCESS read-write
    STATUS     current
    DESCRIPTION
    "Specifies teletext descriptor type."
::= { enc1P89ttxdesc6TypeEntry 1 }

enc1P90ttxdesc6MagazineNumberTable OBJECT-TYPE
    SYNTAX SEQUENCE OF Enc1P90ttxdesc6MagazineNumberEntry
    MAX-ACCESS not-accessible
    STATUS     current
    DESCRIPTION
    "
    Name      : TTX Desc 6 Magazine Number
    Menu Path : /TS Mux/SI Parameters
    Units     : 
    Precision : 0
    Low Range : 1
    High Range: 8
    Details   : Specifies teletext magazine number.

     NOTE: Precision/Units/Ranges represent the state of the
           parameter during the MIB generation, and does not
           neccessary reflect the current state of the parameter
    "
::= { enc1Params 90 }

enc1P90ttxdesc6MagazineNumberEntry OBJECT-TYPE
    SYNTAX Enc1P90ttxdesc6MagazineNumberEntry
    MAX-ACCESS not-accessible
    STATUS     current
    DESCRIPTION
    "Table Entry for TTX Desc 6 Magazine Number"
    INDEX { slotId }
::= { enc1P90ttxdesc6MagazineNumberTable 1 }

Enc1P90ttxdesc6MagazineNumberEntry ::= SEQUENCE {
    enc1P90ttxdesc6MagazineNumberValue    INTEGER
}

enc1P90ttxdesc6MagazineNumberValue OBJECT-TYPE
    SYNTAX     INTEGER
    MAX-ACCESS read-write
    STATUS     current
    DESCRIPTION
    "Specifies teletext magazine number."
::= { enc1P90ttxdesc6MagazineNumberEntry 1 }

enc1P91ttxdesc6PageNumberTable OBJECT-TYPE
    SYNTAX SEQUENCE OF Enc1P91ttxdesc6PageNumberEntry
    MAX-ACCESS not-accessible
    STATUS     current
    DESCRIPTION
    "
    Name      : TTX Desc 6 Page Number
    Menu Path : /TS Mux/SI Parameters
    Units     : 
    Precision : 0
    Low Range : 0
    High Range: 255
    Details   : Specifies teletext page number.

     NOTE: Precision/Units/Ranges represent the state of the
           parameter during the MIB generation, and does not
           neccessary reflect the current state of the parameter
    "
::= { enc1Params 91 }

enc1P91ttxdesc6PageNumberEntry OBJECT-TYPE
    SYNTAX Enc1P91ttxdesc6PageNumberEntry
    MAX-ACCESS not-accessible
    STATUS     current
    DESCRIPTION
    "Table Entry for TTX Desc 6 Page Number"
    INDEX { slotId }
::= { enc1P91ttxdesc6PageNumberTable 1 }

Enc1P91ttxdesc6PageNumberEntry ::= SEQUENCE {
    enc1P91ttxdesc6PageNumberValue    INTEGER
}

enc1P91ttxdesc6PageNumberValue OBJECT-TYPE
    SYNTAX     INTEGER
    MAX-ACCESS read-write
    STATUS     current
    DESCRIPTION
    "Specifies teletext page number."
::= { enc1P91ttxdesc6PageNumberEntry 1 }

enc1P92ttxdesc7LanguageTable OBJECT-TYPE
    SYNTAX SEQUENCE OF Enc1P92ttxdesc7LanguageEntry
    MAX-ACCESS not-accessible
    STATUS     current
    DESCRIPTION
    "
    Name      : TTX Desc 7 Language
    Menu Path : /TS Mux/SI Parameters
    Details   : Specifies teletext descriptor language code.
    "
::= { enc1Params 92 }

enc1P92ttxdesc7LanguageEntry OBJECT-TYPE
    SYNTAX Enc1P92ttxdesc7LanguageEntry
    MAX-ACCESS not-accessible
    STATUS     current
    DESCRIPTION
    "Table Entry for TTX Desc 7 Language"
    INDEX { slotId }
::= { enc1P92ttxdesc7LanguageTable 1 }

Enc1P92ttxdesc7LanguageEntry ::= SEQUENCE {
    enc1P92ttxdesc7LanguageValue    DisplayString
}

enc1P92ttxdesc7LanguageValue OBJECT-TYPE
    SYNTAX     DisplayString
    MAX-ACCESS read-write
    STATUS     current
    DESCRIPTION
    "Specifies teletext descriptor language code."
::= { enc1P92ttxdesc7LanguageEntry 1 }

enc1P93ttxdesc7TypeTable OBJECT-TYPE
    SYNTAX SEQUENCE OF Enc1P93ttxdesc7TypeEntry
    MAX-ACCESS not-accessible
    STATUS     current
    DESCRIPTION
    "
    Name      : TTX Desc 7 Type
    Menu Path : /TS Mux/SI Parameters
    Units     : 
    Precision : 0
    Low Range : 0
    High Range: 31
    Details   : Specifies teletext descriptor type.

     NOTE: Precision/Units/Ranges represent the state of the
           parameter during the MIB generation, and does not
           neccessary reflect the current state of the parameter
    "
::= { enc1Params 93 }

enc1P93ttxdesc7TypeEntry OBJECT-TYPE
    SYNTAX Enc1P93ttxdesc7TypeEntry
    MAX-ACCESS not-accessible
    STATUS     current
    DESCRIPTION
    "Table Entry for TTX Desc 7 Type"
    INDEX { slotId }
::= { enc1P93ttxdesc7TypeTable 1 }

Enc1P93ttxdesc7TypeEntry ::= SEQUENCE {
    enc1P93ttxdesc7TypeValue    INTEGER
}

enc1P93ttxdesc7TypeValue OBJECT-TYPE
    SYNTAX     INTEGER
    MAX-ACCESS read-write
    STATUS     current
    DESCRIPTION
    "Specifies teletext descriptor type."
::= { enc1P93ttxdesc7TypeEntry 1 }

enc1P94ttxdesc7MagazineNumberTable OBJECT-TYPE
    SYNTAX SEQUENCE OF Enc1P94ttxdesc7MagazineNumberEntry
    MAX-ACCESS not-accessible
    STATUS     current
    DESCRIPTION
    "
    Name      : TTX Desc 7 Magazine Number
    Menu Path : /TS Mux/SI Parameters
    Units     : 
    Precision : 0
    Low Range : 1
    High Range: 8
    Details   : Specifies teletext magazine number.

     NOTE: Precision/Units/Ranges represent the state of the
           parameter during the MIB generation, and does not
           neccessary reflect the current state of the parameter
    "
::= { enc1Params 94 }

enc1P94ttxdesc7MagazineNumberEntry OBJECT-TYPE
    SYNTAX Enc1P94ttxdesc7MagazineNumberEntry
    MAX-ACCESS not-accessible
    STATUS     current
    DESCRIPTION
    "Table Entry for TTX Desc 7 Magazine Number"
    INDEX { slotId }
::= { enc1P94ttxdesc7MagazineNumberTable 1 }

Enc1P94ttxdesc7MagazineNumberEntry ::= SEQUENCE {
    enc1P94ttxdesc7MagazineNumberValue    INTEGER
}

enc1P94ttxdesc7MagazineNumberValue OBJECT-TYPE
    SYNTAX     INTEGER
    MAX-ACCESS read-write
    STATUS     current
    DESCRIPTION
    "Specifies teletext magazine number."
::= { enc1P94ttxdesc7MagazineNumberEntry 1 }

enc1P95ttxdesc7PageNumberTable OBJECT-TYPE
    SYNTAX SEQUENCE OF Enc1P95ttxdesc7PageNumberEntry
    MAX-ACCESS not-accessible
    STATUS     current
    DESCRIPTION
    "
    Name      : TTX Desc 7 Page Number
    Menu Path : /TS Mux/SI Parameters
    Units     : 
    Precision : 0
    Low Range : 0
    High Range: 255
    Details   : Specifies teletext page number.

     NOTE: Precision/Units/Ranges represent the state of the
           parameter during the MIB generation, and does not
           neccessary reflect the current state of the parameter
    "
::= { enc1Params 95 }

enc1P95ttxdesc7PageNumberEntry OBJECT-TYPE
    SYNTAX Enc1P95ttxdesc7PageNumberEntry
    MAX-ACCESS not-accessible
    STATUS     current
    DESCRIPTION
    "Table Entry for TTX Desc 7 Page Number"
    INDEX { slotId }
::= { enc1P95ttxdesc7PageNumberTable 1 }

Enc1P95ttxdesc7PageNumberEntry ::= SEQUENCE {
    enc1P95ttxdesc7PageNumberValue    INTEGER
}

enc1P95ttxdesc7PageNumberValue OBJECT-TYPE
    SYNTAX     INTEGER
    MAX-ACCESS read-write
    STATUS     current
    DESCRIPTION
    "Specifies teletext page number."
::= { enc1P95ttxdesc7PageNumberEntry 1 }

enc1P96ttxdesc8LanguageTable OBJECT-TYPE
    SYNTAX SEQUENCE OF Enc1P96ttxdesc8LanguageEntry
    MAX-ACCESS not-accessible
    STATUS     current
    DESCRIPTION
    "
    Name      : TTX Desc 8 Language
    Menu Path : /TS Mux/SI Parameters
    Details   : Specifies teletext descriptor language code.
    "
::= { enc1Params 96 }

enc1P96ttxdesc8LanguageEntry OBJECT-TYPE
    SYNTAX Enc1P96ttxdesc8LanguageEntry
    MAX-ACCESS not-accessible
    STATUS     current
    DESCRIPTION
    "Table Entry for TTX Desc 8 Language"
    INDEX { slotId }
::= { enc1P96ttxdesc8LanguageTable 1 }

Enc1P96ttxdesc8LanguageEntry ::= SEQUENCE {
    enc1P96ttxdesc8LanguageValue    DisplayString
}

enc1P96ttxdesc8LanguageValue OBJECT-TYPE
    SYNTAX     DisplayString
    MAX-ACCESS read-write
    STATUS     current
    DESCRIPTION
    "Specifies teletext descriptor language code."
::= { enc1P96ttxdesc8LanguageEntry 1 }

enc1P97ttxdesc8TypeTable OBJECT-TYPE
    SYNTAX SEQUENCE OF Enc1P97ttxdesc8TypeEntry
    MAX-ACCESS not-accessible
    STATUS     current
    DESCRIPTION
    "
    Name      : TTX Desc 8 Type
    Menu Path : /TS Mux/SI Parameters
    Units     : 
    Precision : 0
    Low Range : 0
    High Range: 31
    Details   : Specifies teletext descriptor type.

     NOTE: Precision/Units/Ranges represent the state of the
           parameter during the MIB generation, and does not
           neccessary reflect the current state of the parameter
    "
::= { enc1Params 97 }

enc1P97ttxdesc8TypeEntry OBJECT-TYPE
    SYNTAX Enc1P97ttxdesc8TypeEntry
    MAX-ACCESS not-accessible
    STATUS     current
    DESCRIPTION
    "Table Entry for TTX Desc 8 Type"
    INDEX { slotId }
::= { enc1P97ttxdesc8TypeTable 1 }

Enc1P97ttxdesc8TypeEntry ::= SEQUENCE {
    enc1P97ttxdesc8TypeValue    INTEGER
}

enc1P97ttxdesc8TypeValue OBJECT-TYPE
    SYNTAX     INTEGER
    MAX-ACCESS read-write
    STATUS     current
    DESCRIPTION
    "Specifies teletext descriptor type."
::= { enc1P97ttxdesc8TypeEntry 1 }

enc1P98ttxdesc8MagazineNumberTable OBJECT-TYPE
    SYNTAX SEQUENCE OF Enc1P98ttxdesc8MagazineNumberEntry
    MAX-ACCESS not-accessible
    STATUS     current
    DESCRIPTION
    "
    Name      : TTX Desc 8 Magazine Number
    Menu Path : /TS Mux/SI Parameters
    Units     : 
    Precision : 0
    Low Range : 1
    High Range: 8
    Details   : Specifies teletext magazine number.

     NOTE: Precision/Units/Ranges represent the state of the
           parameter during the MIB generation, and does not
           neccessary reflect the current state of the parameter
    "
::= { enc1Params 98 }

enc1P98ttxdesc8MagazineNumberEntry OBJECT-TYPE
    SYNTAX Enc1P98ttxdesc8MagazineNumberEntry
    MAX-ACCESS not-accessible
    STATUS     current
    DESCRIPTION
    "Table Entry for TTX Desc 8 Magazine Number"
    INDEX { slotId }
::= { enc1P98ttxdesc8MagazineNumberTable 1 }

Enc1P98ttxdesc8MagazineNumberEntry ::= SEQUENCE {
    enc1P98ttxdesc8MagazineNumberValue    INTEGER
}

enc1P98ttxdesc8MagazineNumberValue OBJECT-TYPE
    SYNTAX     INTEGER
    MAX-ACCESS read-write
    STATUS     current
    DESCRIPTION
    "Specifies teletext magazine number."
::= { enc1P98ttxdesc8MagazineNumberEntry 1 }

enc1P99ttxdesc8PageNumberTable OBJECT-TYPE
    SYNTAX SEQUENCE OF Enc1P99ttxdesc8PageNumberEntry
    MAX-ACCESS not-accessible
    STATUS     current
    DESCRIPTION
    "
    Name      : TTX Desc 8 Page Number
    Menu Path : /TS Mux/SI Parameters
    Units     : 
    Precision : 0
    Low Range : 0
    High Range: 255
    Details   : Specifies teletext page number.

     NOTE: Precision/Units/Ranges represent the state of the
           parameter during the MIB generation, and does not
           neccessary reflect the current state of the parameter
    "
::= { enc1Params 99 }

enc1P99ttxdesc8PageNumberEntry OBJECT-TYPE
    SYNTAX Enc1P99ttxdesc8PageNumberEntry
    MAX-ACCESS not-accessible
    STATUS     current
    DESCRIPTION
    "Table Entry for TTX Desc 8 Page Number"
    INDEX { slotId }
::= { enc1P99ttxdesc8PageNumberTable 1 }

Enc1P99ttxdesc8PageNumberEntry ::= SEQUENCE {
    enc1P99ttxdesc8PageNumberValue    INTEGER
}

enc1P99ttxdesc8PageNumberValue OBJECT-TYPE
    SYNTAX     INTEGER
    MAX-ACCESS read-write
    STATUS     current
    DESCRIPTION
    "Specifies teletext page number."
::= { enc1P99ttxdesc8PageNumberEntry 1 }

enc1P100ttxdesc9LanguageTable OBJECT-TYPE
    SYNTAX SEQUENCE OF Enc1P100ttxdesc9LanguageEntry
    MAX-ACCESS not-accessible
    STATUS     current
    DESCRIPTION
    "
    Name      : TTX Desc 9 Language
    Menu Path : /TS Mux/SI Parameters
    Details   : Specifies teletext descriptor language code.
    "
::= { enc1Params 100 }

enc1P100ttxdesc9LanguageEntry OBJECT-TYPE
    SYNTAX Enc1P100ttxdesc9LanguageEntry
    MAX-ACCESS not-accessible
    STATUS     current
    DESCRIPTION
    "Table Entry for TTX Desc 9 Language"
    INDEX { slotId }
::= { enc1P100ttxdesc9LanguageTable 1 }

Enc1P100ttxdesc9LanguageEntry ::= SEQUENCE {
    enc1P100ttxdesc9LanguageValue    DisplayString
}

enc1P100ttxdesc9LanguageValue OBJECT-TYPE
    SYNTAX     DisplayString
    MAX-ACCESS read-write
    STATUS     current
    DESCRIPTION
    "Specifies teletext descriptor language code."
::= { enc1P100ttxdesc9LanguageEntry 1 }

enc1P101ttxdesc9TypeTable OBJECT-TYPE
    SYNTAX SEQUENCE OF Enc1P101ttxdesc9TypeEntry
    MAX-ACCESS not-accessible
    STATUS     current
    DESCRIPTION
    "
    Name      : TTX Desc 9 Type
    Menu Path : /TS Mux/SI Parameters
    Units     : 
    Precision : 0
    Low Range : 0
    High Range: 31
    Details   : Specifies teletext descriptor type.

     NOTE: Precision/Units/Ranges represent the state of the
           parameter during the MIB generation, and does not
           neccessary reflect the current state of the parameter
    "
::= { enc1Params 101 }

enc1P101ttxdesc9TypeEntry OBJECT-TYPE
    SYNTAX Enc1P101ttxdesc9TypeEntry
    MAX-ACCESS not-accessible
    STATUS     current
    DESCRIPTION
    "Table Entry for TTX Desc 9 Type"
    INDEX { slotId }
::= { enc1P101ttxdesc9TypeTable 1 }

Enc1P101ttxdesc9TypeEntry ::= SEQUENCE {
    enc1P101ttxdesc9TypeValue    INTEGER
}

enc1P101ttxdesc9TypeValue OBJECT-TYPE
    SYNTAX     INTEGER
    MAX-ACCESS read-write
    STATUS     current
    DESCRIPTION
    "Specifies teletext descriptor type."
::= { enc1P101ttxdesc9TypeEntry 1 }

enc1P102ttxdesc9MagazineNumberTable OBJECT-TYPE
    SYNTAX SEQUENCE OF Enc1P102ttxdesc9MagazineNumberEntry
    MAX-ACCESS not-accessible
    STATUS     current
    DESCRIPTION
    "
    Name      : TTX Desc 9 Magazine Number
    Menu Path : /TS Mux/SI Parameters
    Units     : 
    Precision : 0
    Low Range : 1
    High Range: 8
    Details   : Specifies teletext magazine number.

     NOTE: Precision/Units/Ranges represent the state of the
           parameter during the MIB generation, and does not
           neccessary reflect the current state of the parameter
    "
::= { enc1Params 102 }

enc1P102ttxdesc9MagazineNumberEntry OBJECT-TYPE
    SYNTAX Enc1P102ttxdesc9MagazineNumberEntry
    MAX-ACCESS not-accessible
    STATUS     current
    DESCRIPTION
    "Table Entry for TTX Desc 9 Magazine Number"
    INDEX { slotId }
::= { enc1P102ttxdesc9MagazineNumberTable 1 }

Enc1P102ttxdesc9MagazineNumberEntry ::= SEQUENCE {
    enc1P102ttxdesc9MagazineNumberValue    INTEGER
}

enc1P102ttxdesc9MagazineNumberValue OBJECT-TYPE
    SYNTAX     INTEGER
    MAX-ACCESS read-write
    STATUS     current
    DESCRIPTION
    "Specifies teletext magazine number."
::= { enc1P102ttxdesc9MagazineNumberEntry 1 }

enc1P103ttxdesc9PageNumberTable OBJECT-TYPE
    SYNTAX SEQUENCE OF Enc1P103ttxdesc9PageNumberEntry
    MAX-ACCESS not-accessible
    STATUS     current
    DESCRIPTION
    "
    Name      : TTX Desc 9 Page Number
    Menu Path : /TS Mux/SI Parameters
    Units     : 
    Precision : 0
    Low Range : 0
    High Range: 255
    Details   : Specifies teletext page number.

     NOTE: Precision/Units/Ranges represent the state of the
           parameter during the MIB generation, and does not
           neccessary reflect the current state of the parameter
    "
::= { enc1Params 103 }

enc1P103ttxdesc9PageNumberEntry OBJECT-TYPE
    SYNTAX Enc1P103ttxdesc9PageNumberEntry
    MAX-ACCESS not-accessible
    STATUS     current
    DESCRIPTION
    "Table Entry for TTX Desc 9 Page Number"
    INDEX { slotId }
::= { enc1P103ttxdesc9PageNumberTable 1 }

Enc1P103ttxdesc9PageNumberEntry ::= SEQUENCE {
    enc1P103ttxdesc9PageNumberValue    INTEGER
}

enc1P103ttxdesc9PageNumberValue OBJECT-TYPE
    SYNTAX     INTEGER
    MAX-ACCESS read-write
    STATUS     current
    DESCRIPTION
    "Specifies teletext page number."
::= { enc1P103ttxdesc9PageNumberEntry 1 }

enc1P104ttxdesc10LanguageTable OBJECT-TYPE
    SYNTAX SEQUENCE OF Enc1P104ttxdesc10LanguageEntry
    MAX-ACCESS not-accessible
    STATUS     current
    DESCRIPTION
    "
    Name      : TTX Desc 10 Language
    Menu Path : /TS Mux/SI Parameters
    Details   : Specifies teletext descriptor language code.
    "
::= { enc1Params 104 }

enc1P104ttxdesc10LanguageEntry OBJECT-TYPE
    SYNTAX Enc1P104ttxdesc10LanguageEntry
    MAX-ACCESS not-accessible
    STATUS     current
    DESCRIPTION
    "Table Entry for TTX Desc 10 Language"
    INDEX { slotId }
::= { enc1P104ttxdesc10LanguageTable 1 }

Enc1P104ttxdesc10LanguageEntry ::= SEQUENCE {
    enc1P104ttxdesc10LanguageValue    DisplayString
}

enc1P104ttxdesc10LanguageValue OBJECT-TYPE
    SYNTAX     DisplayString
    MAX-ACCESS read-write
    STATUS     current
    DESCRIPTION
    "Specifies teletext descriptor language code."
::= { enc1P104ttxdesc10LanguageEntry 1 }

enc1P105ttxdesc10TypeTable OBJECT-TYPE
    SYNTAX SEQUENCE OF Enc1P105ttxdesc10TypeEntry
    MAX-ACCESS not-accessible
    STATUS     current
    DESCRIPTION
    "
    Name      : TTX Desc 10 Type
    Menu Path : /TS Mux/SI Parameters
    Units     : 
    Precision : 0
    Low Range : 0
    High Range: 31
    Details   : Specifies teletext descriptor type.

     NOTE: Precision/Units/Ranges represent the state of the
           parameter during the MIB generation, and does not
           neccessary reflect the current state of the parameter
    "
::= { enc1Params 105 }

enc1P105ttxdesc10TypeEntry OBJECT-TYPE
    SYNTAX Enc1P105ttxdesc10TypeEntry
    MAX-ACCESS not-accessible
    STATUS     current
    DESCRIPTION
    "Table Entry for TTX Desc 10 Type"
    INDEX { slotId }
::= { enc1P105ttxdesc10TypeTable 1 }

Enc1P105ttxdesc10TypeEntry ::= SEQUENCE {
    enc1P105ttxdesc10TypeValue    INTEGER
}

enc1P105ttxdesc10TypeValue OBJECT-TYPE
    SYNTAX     INTEGER
    MAX-ACCESS read-write
    STATUS     current
    DESCRIPTION
    "Specifies teletext descriptor type."
::= { enc1P105ttxdesc10TypeEntry 1 }

enc1P106ttxdesc10MagazineNumberTable OBJECT-TYPE
    SYNTAX SEQUENCE OF Enc1P106ttxdesc10MagazineNumberEntry
    MAX-ACCESS not-accessible
    STATUS     current
    DESCRIPTION
    "
    Name      : TTX Desc 10 Magazine Number
    Menu Path : /TS Mux/SI Parameters
    Units     : 
    Precision : 0
    Low Range : 1
    High Range: 8
    Details   : Specifies teletext magazine number.

     NOTE: Precision/Units/Ranges represent the state of the
           parameter during the MIB generation, and does not
           neccessary reflect the current state of the parameter
    "
::= { enc1Params 106 }

enc1P106ttxdesc10MagazineNumberEntry OBJECT-TYPE
    SYNTAX Enc1P106ttxdesc10MagazineNumberEntry
    MAX-ACCESS not-accessible
    STATUS     current
    DESCRIPTION
    "Table Entry for TTX Desc 10 Magazine Number"
    INDEX { slotId }
::= { enc1P106ttxdesc10MagazineNumberTable 1 }

Enc1P106ttxdesc10MagazineNumberEntry ::= SEQUENCE {
    enc1P106ttxdesc10MagazineNumberValue    INTEGER
}

enc1P106ttxdesc10MagazineNumberValue OBJECT-TYPE
    SYNTAX     INTEGER
    MAX-ACCESS read-write
    STATUS     current
    DESCRIPTION
    "Specifies teletext magazine number."
::= { enc1P106ttxdesc10MagazineNumberEntry 1 }

enc1P107ttxdesc10PageNumberTable OBJECT-TYPE
    SYNTAX SEQUENCE OF Enc1P107ttxdesc10PageNumberEntry
    MAX-ACCESS not-accessible
    STATUS     current
    DESCRIPTION
    "
    Name      : TTX Desc 10 Page Number
    Menu Path : /TS Mux/SI Parameters
    Units     : 
    Precision : 0
    Low Range : 0
    High Range: 255
    Details   : Specifies teletext page number.

     NOTE: Precision/Units/Ranges represent the state of the
           parameter during the MIB generation, and does not
           neccessary reflect the current state of the parameter
    "
::= { enc1Params 107 }

enc1P107ttxdesc10PageNumberEntry OBJECT-TYPE
    SYNTAX Enc1P107ttxdesc10PageNumberEntry
    MAX-ACCESS not-accessible
    STATUS     current
    DESCRIPTION
    "Table Entry for TTX Desc 10 Page Number"
    INDEX { slotId }
::= { enc1P107ttxdesc10PageNumberTable 1 }

Enc1P107ttxdesc10PageNumberEntry ::= SEQUENCE {
    enc1P107ttxdesc10PageNumberValue    INTEGER
}

enc1P107ttxdesc10PageNumberValue OBJECT-TYPE
    SYNTAX     INTEGER
    MAX-ACCESS read-write
    STATUS     current
    DESCRIPTION
    "Specifies teletext page number."
::= { enc1P107ttxdesc10PageNumberEntry 1 }

enc1P108ttxdesc11LanguageTable OBJECT-TYPE
    SYNTAX SEQUENCE OF Enc1P108ttxdesc11LanguageEntry
    MAX-ACCESS not-accessible
    STATUS     current
    DESCRIPTION
    "
    Name      : TTX Desc 11 Language
    Menu Path : /TS Mux/SI Parameters
    Details   : Specifies teletext descriptor language code.
    "
::= { enc1Params 108 }

enc1P108ttxdesc11LanguageEntry OBJECT-TYPE
    SYNTAX Enc1P108ttxdesc11LanguageEntry
    MAX-ACCESS not-accessible
    STATUS     current
    DESCRIPTION
    "Table Entry for TTX Desc 11 Language"
    INDEX { slotId }
::= { enc1P108ttxdesc11LanguageTable 1 }

Enc1P108ttxdesc11LanguageEntry ::= SEQUENCE {
    enc1P108ttxdesc11LanguageValue    DisplayString
}

enc1P108ttxdesc11LanguageValue OBJECT-TYPE
    SYNTAX     DisplayString
    MAX-ACCESS read-write
    STATUS     current
    DESCRIPTION
    "Specifies teletext descriptor language code."
::= { enc1P108ttxdesc11LanguageEntry 1 }

enc1P109ttxdesc11TypeTable OBJECT-TYPE
    SYNTAX SEQUENCE OF Enc1P109ttxdesc11TypeEntry
    MAX-ACCESS not-accessible
    STATUS     current
    DESCRIPTION
    "
    Name      : TTX Desc 11 Type
    Menu Path : /TS Mux/SI Parameters
    Units     : 
    Precision : 0
    Low Range : 0
    High Range: 31
    Details   : Specifies teletext descriptor type.

     NOTE: Precision/Units/Ranges represent the state of the
           parameter during the MIB generation, and does not
           neccessary reflect the current state of the parameter
    "
::= { enc1Params 109 }

enc1P109ttxdesc11TypeEntry OBJECT-TYPE
    SYNTAX Enc1P109ttxdesc11TypeEntry
    MAX-ACCESS not-accessible
    STATUS     current
    DESCRIPTION
    "Table Entry for TTX Desc 11 Type"
    INDEX { slotId }
::= { enc1P109ttxdesc11TypeTable 1 }

Enc1P109ttxdesc11TypeEntry ::= SEQUENCE {
    enc1P109ttxdesc11TypeValue    INTEGER
}

enc1P109ttxdesc11TypeValue OBJECT-TYPE
    SYNTAX     INTEGER
    MAX-ACCESS read-write
    STATUS     current
    DESCRIPTION
    "Specifies teletext descriptor type."
::= { enc1P109ttxdesc11TypeEntry 1 }

enc1P110ttxdesc11MagazineNumberTable OBJECT-TYPE
    SYNTAX SEQUENCE OF Enc1P110ttxdesc11MagazineNumberEntry
    MAX-ACCESS not-accessible
    STATUS     current
    DESCRIPTION
    "
    Name      : TTX Desc 11 Magazine Number
    Menu Path : /TS Mux/SI Parameters
    Units     : 
    Precision : 0
    Low Range : 1
    High Range: 8
    Details   : Specifies teletext magazine number.

     NOTE: Precision/Units/Ranges represent the state of the
           parameter during the MIB generation, and does not
           neccessary reflect the current state of the parameter
    "
::= { enc1Params 110 }

enc1P110ttxdesc11MagazineNumberEntry OBJECT-TYPE
    SYNTAX Enc1P110ttxdesc11MagazineNumberEntry
    MAX-ACCESS not-accessible
    STATUS     current
    DESCRIPTION
    "Table Entry for TTX Desc 11 Magazine Number"
    INDEX { slotId }
::= { enc1P110ttxdesc11MagazineNumberTable 1 }

Enc1P110ttxdesc11MagazineNumberEntry ::= SEQUENCE {
    enc1P110ttxdesc11MagazineNumberValue    INTEGER
}

enc1P110ttxdesc11MagazineNumberValue OBJECT-TYPE
    SYNTAX     INTEGER
    MAX-ACCESS read-write
    STATUS     current
    DESCRIPTION
    "Specifies teletext magazine number."
::= { enc1P110ttxdesc11MagazineNumberEntry 1 }

enc1P111ttxdesc11PageNumberTable OBJECT-TYPE
    SYNTAX SEQUENCE OF Enc1P111ttxdesc11PageNumberEntry
    MAX-ACCESS not-accessible
    STATUS     current
    DESCRIPTION
    "
    Name      : TTX Desc 11 Page Number
    Menu Path : /TS Mux/SI Parameters
    Units     : 
    Precision : 0
    Low Range : 0
    High Range: 255
    Details   : Specifies teletext page number.

     NOTE: Precision/Units/Ranges represent the state of the
           parameter during the MIB generation, and does not
           neccessary reflect the current state of the parameter
    "
::= { enc1Params 111 }

enc1P111ttxdesc11PageNumberEntry OBJECT-TYPE
    SYNTAX Enc1P111ttxdesc11PageNumberEntry
    MAX-ACCESS not-accessible
    STATUS     current
    DESCRIPTION
    "Table Entry for TTX Desc 11 Page Number"
    INDEX { slotId }
::= { enc1P111ttxdesc11PageNumberTable 1 }

Enc1P111ttxdesc11PageNumberEntry ::= SEQUENCE {
    enc1P111ttxdesc11PageNumberValue    INTEGER
}

enc1P111ttxdesc11PageNumberValue OBJECT-TYPE
    SYNTAX     INTEGER
    MAX-ACCESS read-write
    STATUS     current
    DESCRIPTION
    "Specifies teletext page number."
::= { enc1P111ttxdesc11PageNumberEntry 1 }

enc1P112ttxdesc12LanguageTable OBJECT-TYPE
    SYNTAX SEQUENCE OF Enc1P112ttxdesc12LanguageEntry
    MAX-ACCESS not-accessible
    STATUS     current
    DESCRIPTION
    "
    Name      : TTX Desc 12 Language
    Menu Path : /TS Mux/SI Parameters
    Details   : Specifies teletext descriptor language code.
    "
::= { enc1Params 112 }

enc1P112ttxdesc12LanguageEntry OBJECT-TYPE
    SYNTAX Enc1P112ttxdesc12LanguageEntry
    MAX-ACCESS not-accessible
    STATUS     current
    DESCRIPTION
    "Table Entry for TTX Desc 12 Language"
    INDEX { slotId }
::= { enc1P112ttxdesc12LanguageTable 1 }

Enc1P112ttxdesc12LanguageEntry ::= SEQUENCE {
    enc1P112ttxdesc12LanguageValue    DisplayString
}

enc1P112ttxdesc12LanguageValue OBJECT-TYPE
    SYNTAX     DisplayString
    MAX-ACCESS read-write
    STATUS     current
    DESCRIPTION
    "Specifies teletext descriptor language code."
::= { enc1P112ttxdesc12LanguageEntry 1 }

enc1P113ttxdesc12TypeTable OBJECT-TYPE
    SYNTAX SEQUENCE OF Enc1P113ttxdesc12TypeEntry
    MAX-ACCESS not-accessible
    STATUS     current
    DESCRIPTION
    "
    Name      : TTX Desc 12 Type
    Menu Path : /TS Mux/SI Parameters
    Units     : 
    Precision : 0
    Low Range : 0
    High Range: 31
    Details   : Specifies teletext descriptor type.

     NOTE: Precision/Units/Ranges represent the state of the
           parameter during the MIB generation, and does not
           neccessary reflect the current state of the parameter
    "
::= { enc1Params 113 }

enc1P113ttxdesc12TypeEntry OBJECT-TYPE
    SYNTAX Enc1P113ttxdesc12TypeEntry
    MAX-ACCESS not-accessible
    STATUS     current
    DESCRIPTION
    "Table Entry for TTX Desc 12 Type"
    INDEX { slotId }
::= { enc1P113ttxdesc12TypeTable 1 }

Enc1P113ttxdesc12TypeEntry ::= SEQUENCE {
    enc1P113ttxdesc12TypeValue    INTEGER
}

enc1P113ttxdesc12TypeValue OBJECT-TYPE
    SYNTAX     INTEGER
    MAX-ACCESS read-write
    STATUS     current
    DESCRIPTION
    "Specifies teletext descriptor type."
::= { enc1P113ttxdesc12TypeEntry 1 }

enc1P114ttxdesc12MagazineNumberTable OBJECT-TYPE
    SYNTAX SEQUENCE OF Enc1P114ttxdesc12MagazineNumberEntry
    MAX-ACCESS not-accessible
    STATUS     current
    DESCRIPTION
    "
    Name      : TTX Desc 12 Magazine Number
    Menu Path : /TS Mux/SI Parameters
    Units     : 
    Precision : 0
    Low Range : 1
    High Range: 8
    Details   : Specifies teletext magazine number.

     NOTE: Precision/Units/Ranges represent the state of the
           parameter during the MIB generation, and does not
           neccessary reflect the current state of the parameter
    "
::= { enc1Params 114 }

enc1P114ttxdesc12MagazineNumberEntry OBJECT-TYPE
    SYNTAX Enc1P114ttxdesc12MagazineNumberEntry
    MAX-ACCESS not-accessible
    STATUS     current
    DESCRIPTION
    "Table Entry for TTX Desc 12 Magazine Number"
    INDEX { slotId }
::= { enc1P114ttxdesc12MagazineNumberTable 1 }

Enc1P114ttxdesc12MagazineNumberEntry ::= SEQUENCE {
    enc1P114ttxdesc12MagazineNumberValue    INTEGER
}

enc1P114ttxdesc12MagazineNumberValue OBJECT-TYPE
    SYNTAX     INTEGER
    MAX-ACCESS read-write
    STATUS     current
    DESCRIPTION
    "Specifies teletext magazine number."
::= { enc1P114ttxdesc12MagazineNumberEntry 1 }

enc1P115ttxdesc12PageNumberTable OBJECT-TYPE
    SYNTAX SEQUENCE OF Enc1P115ttxdesc12PageNumberEntry
    MAX-ACCESS not-accessible
    STATUS     current
    DESCRIPTION
    "
    Name      : TTX Desc 12 Page Number
    Menu Path : /TS Mux/SI Parameters
    Units     : 
    Precision : 0
    Low Range : 0
    High Range: 255
    Details   : Specifies teletext page number.

     NOTE: Precision/Units/Ranges represent the state of the
           parameter during the MIB generation, and does not
           neccessary reflect the current state of the parameter
    "
::= { enc1Params 115 }

enc1P115ttxdesc12PageNumberEntry OBJECT-TYPE
    SYNTAX Enc1P115ttxdesc12PageNumberEntry
    MAX-ACCESS not-accessible
    STATUS     current
    DESCRIPTION
    "Table Entry for TTX Desc 12 Page Number"
    INDEX { slotId }
::= { enc1P115ttxdesc12PageNumberTable 1 }

Enc1P115ttxdesc12PageNumberEntry ::= SEQUENCE {
    enc1P115ttxdesc12PageNumberValue    INTEGER
}

enc1P115ttxdesc12PageNumberValue OBJECT-TYPE
    SYNTAX     INTEGER
    MAX-ACCESS read-write
    STATUS     current
    DESCRIPTION
    "Specifies teletext page number."
::= { enc1P115ttxdesc12PageNumberEntry 1 }

enc1P116ttxdesc13LanguageTable OBJECT-TYPE
    SYNTAX SEQUENCE OF Enc1P116ttxdesc13LanguageEntry
    MAX-ACCESS not-accessible
    STATUS     current
    DESCRIPTION
    "
    Name      : TTX Desc 13 Language
    Menu Path : /TS Mux/SI Parameters
    Details   : Specifies teletext descriptor language code.
    "
::= { enc1Params 116 }

enc1P116ttxdesc13LanguageEntry OBJECT-TYPE
    SYNTAX Enc1P116ttxdesc13LanguageEntry
    MAX-ACCESS not-accessible
    STATUS     current
    DESCRIPTION
    "Table Entry for TTX Desc 13 Language"
    INDEX { slotId }
::= { enc1P116ttxdesc13LanguageTable 1 }

Enc1P116ttxdesc13LanguageEntry ::= SEQUENCE {
    enc1P116ttxdesc13LanguageValue    DisplayString
}

enc1P116ttxdesc13LanguageValue OBJECT-TYPE
    SYNTAX     DisplayString
    MAX-ACCESS read-write
    STATUS     current
    DESCRIPTION
    "Specifies teletext descriptor language code."
::= { enc1P116ttxdesc13LanguageEntry 1 }

enc1P117ttxdesc13TypeTable OBJECT-TYPE
    SYNTAX SEQUENCE OF Enc1P117ttxdesc13TypeEntry
    MAX-ACCESS not-accessible
    STATUS     current
    DESCRIPTION
    "
    Name      : TTX Desc 13 Type
    Menu Path : /TS Mux/SI Parameters
    Units     : 
    Precision : 0
    Low Range : 0
    High Range: 31
    Details   : Specifies teletext descriptor type.

     NOTE: Precision/Units/Ranges represent the state of the
           parameter during the MIB generation, and does not
           neccessary reflect the current state of the parameter
    "
::= { enc1Params 117 }

enc1P117ttxdesc13TypeEntry OBJECT-TYPE
    SYNTAX Enc1P117ttxdesc13TypeEntry
    MAX-ACCESS not-accessible
    STATUS     current
    DESCRIPTION
    "Table Entry for TTX Desc 13 Type"
    INDEX { slotId }
::= { enc1P117ttxdesc13TypeTable 1 }

Enc1P117ttxdesc13TypeEntry ::= SEQUENCE {
    enc1P117ttxdesc13TypeValue    INTEGER
}

enc1P117ttxdesc13TypeValue OBJECT-TYPE
    SYNTAX     INTEGER
    MAX-ACCESS read-write
    STATUS     current
    DESCRIPTION
    "Specifies teletext descriptor type."
::= { enc1P117ttxdesc13TypeEntry 1 }

enc1P118ttxdesc13MagazineNumberTable OBJECT-TYPE
    SYNTAX SEQUENCE OF Enc1P118ttxdesc13MagazineNumberEntry
    MAX-ACCESS not-accessible
    STATUS     current
    DESCRIPTION
    "
    Name      : TTX Desc 13 Magazine Number
    Menu Path : /TS Mux/SI Parameters
    Units     : 
    Precision : 0
    Low Range : 1
    High Range: 8
    Details   : Specifies teletext magazine number.

     NOTE: Precision/Units/Ranges represent the state of the
           parameter during the MIB generation, and does not
           neccessary reflect the current state of the parameter
    "
::= { enc1Params 118 }

enc1P118ttxdesc13MagazineNumberEntry OBJECT-TYPE
    SYNTAX Enc1P118ttxdesc13MagazineNumberEntry
    MAX-ACCESS not-accessible
    STATUS     current
    DESCRIPTION
    "Table Entry for TTX Desc 13 Magazine Number"
    INDEX { slotId }
::= { enc1P118ttxdesc13MagazineNumberTable 1 }

Enc1P118ttxdesc13MagazineNumberEntry ::= SEQUENCE {
    enc1P118ttxdesc13MagazineNumberValue    INTEGER
}

enc1P118ttxdesc13MagazineNumberValue OBJECT-TYPE
    SYNTAX     INTEGER
    MAX-ACCESS read-write
    STATUS     current
    DESCRIPTION
    "Specifies teletext magazine number."
::= { enc1P118ttxdesc13MagazineNumberEntry 1 }

enc1P119ttxdesc13PageNumberTable OBJECT-TYPE
    SYNTAX SEQUENCE OF Enc1P119ttxdesc13PageNumberEntry
    MAX-ACCESS not-accessible
    STATUS     current
    DESCRIPTION
    "
    Name      : TTX Desc 13 Page Number
    Menu Path : /TS Mux/SI Parameters
    Units     : 
    Precision : 0
    Low Range : 0
    High Range: 255
    Details   : Specifies teletext page number.

     NOTE: Precision/Units/Ranges represent the state of the
           parameter during the MIB generation, and does not
           neccessary reflect the current state of the parameter
    "
::= { enc1Params 119 }

enc1P119ttxdesc13PageNumberEntry OBJECT-TYPE
    SYNTAX Enc1P119ttxdesc13PageNumberEntry
    MAX-ACCESS not-accessible
    STATUS     current
    DESCRIPTION
    "Table Entry for TTX Desc 13 Page Number"
    INDEX { slotId }
::= { enc1P119ttxdesc13PageNumberTable 1 }

Enc1P119ttxdesc13PageNumberEntry ::= SEQUENCE {
    enc1P119ttxdesc13PageNumberValue    INTEGER
}

enc1P119ttxdesc13PageNumberValue OBJECT-TYPE
    SYNTAX     INTEGER
    MAX-ACCESS read-write
    STATUS     current
    DESCRIPTION
    "Specifies teletext page number."
::= { enc1P119ttxdesc13PageNumberEntry 1 }

enc1P120ttxdesc14LanguageTable OBJECT-TYPE
    SYNTAX SEQUENCE OF Enc1P120ttxdesc14LanguageEntry
    MAX-ACCESS not-accessible
    STATUS     current
    DESCRIPTION
    "
    Name      : TTX Desc 14 Language
    Menu Path : /TS Mux/SI Parameters
    Details   : Specifies teletext descriptor language code.
    "
::= { enc1Params 120 }

enc1P120ttxdesc14LanguageEntry OBJECT-TYPE
    SYNTAX Enc1P120ttxdesc14LanguageEntry
    MAX-ACCESS not-accessible
    STATUS     current
    DESCRIPTION
    "Table Entry for TTX Desc 14 Language"
    INDEX { slotId }
::= { enc1P120ttxdesc14LanguageTable 1 }

Enc1P120ttxdesc14LanguageEntry ::= SEQUENCE {
    enc1P120ttxdesc14LanguageValue    DisplayString
}

enc1P120ttxdesc14LanguageValue OBJECT-TYPE
    SYNTAX     DisplayString
    MAX-ACCESS read-write
    STATUS     current
    DESCRIPTION
    "Specifies teletext descriptor language code."
::= { enc1P120ttxdesc14LanguageEntry 1 }

enc1P121ttxdesc14TypeTable OBJECT-TYPE
    SYNTAX SEQUENCE OF Enc1P121ttxdesc14TypeEntry
    MAX-ACCESS not-accessible
    STATUS     current
    DESCRIPTION
    "
    Name      : TTX Desc 14 Type
    Menu Path : /TS Mux/SI Parameters
    Units     : 
    Precision : 0
    Low Range : 0
    High Range: 31
    Details   : Specifies teletext descriptor type.

     NOTE: Precision/Units/Ranges represent the state of the
           parameter during the MIB generation, and does not
           neccessary reflect the current state of the parameter
    "
::= { enc1Params 121 }

enc1P121ttxdesc14TypeEntry OBJECT-TYPE
    SYNTAX Enc1P121ttxdesc14TypeEntry
    MAX-ACCESS not-accessible
    STATUS     current
    DESCRIPTION
    "Table Entry for TTX Desc 14 Type"
    INDEX { slotId }
::= { enc1P121ttxdesc14TypeTable 1 }

Enc1P121ttxdesc14TypeEntry ::= SEQUENCE {
    enc1P121ttxdesc14TypeValue    INTEGER
}

enc1P121ttxdesc14TypeValue OBJECT-TYPE
    SYNTAX     INTEGER
    MAX-ACCESS read-write
    STATUS     current
    DESCRIPTION
    "Specifies teletext descriptor type."
::= { enc1P121ttxdesc14TypeEntry 1 }

enc1P122ttxdesc14MagazineNumberTable OBJECT-TYPE
    SYNTAX SEQUENCE OF Enc1P122ttxdesc14MagazineNumberEntry
    MAX-ACCESS not-accessible
    STATUS     current
    DESCRIPTION
    "
    Name      : TTX Desc 14 Magazine Number
    Menu Path : /TS Mux/SI Parameters
    Units     : 
    Precision : 0
    Low Range : 1
    High Range: 8
    Details   : Specifies teletext magazine number.

     NOTE: Precision/Units/Ranges represent the state of the
           parameter during the MIB generation, and does not
           neccessary reflect the current state of the parameter
    "
::= { enc1Params 122 }

enc1P122ttxdesc14MagazineNumberEntry OBJECT-TYPE
    SYNTAX Enc1P122ttxdesc14MagazineNumberEntry
    MAX-ACCESS not-accessible
    STATUS     current
    DESCRIPTION
    "Table Entry for TTX Desc 14 Magazine Number"
    INDEX { slotId }
::= { enc1P122ttxdesc14MagazineNumberTable 1 }

Enc1P122ttxdesc14MagazineNumberEntry ::= SEQUENCE {
    enc1P122ttxdesc14MagazineNumberValue    INTEGER
}

enc1P122ttxdesc14MagazineNumberValue OBJECT-TYPE
    SYNTAX     INTEGER
    MAX-ACCESS read-write
    STATUS     current
    DESCRIPTION
    "Specifies teletext magazine number."
::= { enc1P122ttxdesc14MagazineNumberEntry 1 }

enc1P123ttxdesc14PageNumberTable OBJECT-TYPE
    SYNTAX SEQUENCE OF Enc1P123ttxdesc14PageNumberEntry
    MAX-ACCESS not-accessible
    STATUS     current
    DESCRIPTION
    "
    Name      : TTX Desc 14 Page Number
    Menu Path : /TS Mux/SI Parameters
    Units     : 
    Precision : 0
    Low Range : 0
    High Range: 255
    Details   : Specifies teletext page number.

     NOTE: Precision/Units/Ranges represent the state of the
           parameter during the MIB generation, and does not
           neccessary reflect the current state of the parameter
    "
::= { enc1Params 123 }

enc1P123ttxdesc14PageNumberEntry OBJECT-TYPE
    SYNTAX Enc1P123ttxdesc14PageNumberEntry
    MAX-ACCESS not-accessible
    STATUS     current
    DESCRIPTION
    "Table Entry for TTX Desc 14 Page Number"
    INDEX { slotId }
::= { enc1P123ttxdesc14PageNumberTable 1 }

Enc1P123ttxdesc14PageNumberEntry ::= SEQUENCE {
    enc1P123ttxdesc14PageNumberValue    INTEGER
}

enc1P123ttxdesc14PageNumberValue OBJECT-TYPE
    SYNTAX     INTEGER
    MAX-ACCESS read-write
    STATUS     current
    DESCRIPTION
    "Specifies teletext page number."
::= { enc1P123ttxdesc14PageNumberEntry 1 }

enc1P124ttxdesc15LanguageTable OBJECT-TYPE
    SYNTAX SEQUENCE OF Enc1P124ttxdesc15LanguageEntry
    MAX-ACCESS not-accessible
    STATUS     current
    DESCRIPTION
    "
    Name      : TTX Desc 15 Language
    Menu Path : /TS Mux/SI Parameters
    Details   : Specifies teletext descriptor language code.
    "
::= { enc1Params 124 }

enc1P124ttxdesc15LanguageEntry OBJECT-TYPE
    SYNTAX Enc1P124ttxdesc15LanguageEntry
    MAX-ACCESS not-accessible
    STATUS     current
    DESCRIPTION
    "Table Entry for TTX Desc 15 Language"
    INDEX { slotId }
::= { enc1P124ttxdesc15LanguageTable 1 }

Enc1P124ttxdesc15LanguageEntry ::= SEQUENCE {
    enc1P124ttxdesc15LanguageValue    DisplayString
}

enc1P124ttxdesc15LanguageValue OBJECT-TYPE
    SYNTAX     DisplayString
    MAX-ACCESS read-write
    STATUS     current
    DESCRIPTION
    "Specifies teletext descriptor language code."
::= { enc1P124ttxdesc15LanguageEntry 1 }

enc1P125ttxdesc15TypeTable OBJECT-TYPE
    SYNTAX SEQUENCE OF Enc1P125ttxdesc15TypeEntry
    MAX-ACCESS not-accessible
    STATUS     current
    DESCRIPTION
    "
    Name      : TTX Desc 15 Type
    Menu Path : /TS Mux/SI Parameters
    Units     : 
    Precision : 0
    Low Range : 0
    High Range: 31
    Details   : Specifies teletext descriptor type.

     NOTE: Precision/Units/Ranges represent the state of the
           parameter during the MIB generation, and does not
           neccessary reflect the current state of the parameter
    "
::= { enc1Params 125 }

enc1P125ttxdesc15TypeEntry OBJECT-TYPE
    SYNTAX Enc1P125ttxdesc15TypeEntry
    MAX-ACCESS not-accessible
    STATUS     current
    DESCRIPTION
    "Table Entry for TTX Desc 15 Type"
    INDEX { slotId }
::= { enc1P125ttxdesc15TypeTable 1 }

Enc1P125ttxdesc15TypeEntry ::= SEQUENCE {
    enc1P125ttxdesc15TypeValue    INTEGER
}

enc1P125ttxdesc15TypeValue OBJECT-TYPE
    SYNTAX     INTEGER
    MAX-ACCESS read-write
    STATUS     current
    DESCRIPTION
    "Specifies teletext descriptor type."
::= { enc1P125ttxdesc15TypeEntry 1 }

enc1P126ttxdesc15MagazineNumberTable OBJECT-TYPE
    SYNTAX SEQUENCE OF Enc1P126ttxdesc15MagazineNumberEntry
    MAX-ACCESS not-accessible
    STATUS     current
    DESCRIPTION
    "
    Name      : TTX Desc 15 Magazine Number
    Menu Path : /TS Mux/SI Parameters
    Units     : 
    Precision : 0
    Low Range : 1
    High Range: 8
    Details   : Specifies teletext magazine number.

     NOTE: Precision/Units/Ranges represent the state of the
           parameter during the MIB generation, and does not
           neccessary reflect the current state of the parameter
    "
::= { enc1Params 126 }

enc1P126ttxdesc15MagazineNumberEntry OBJECT-TYPE
    SYNTAX Enc1P126ttxdesc15MagazineNumberEntry
    MAX-ACCESS not-accessible
    STATUS     current
    DESCRIPTION
    "Table Entry for TTX Desc 15 Magazine Number"
    INDEX { slotId }
::= { enc1P126ttxdesc15MagazineNumberTable 1 }

Enc1P126ttxdesc15MagazineNumberEntry ::= SEQUENCE {
    enc1P126ttxdesc15MagazineNumberValue    INTEGER
}

enc1P126ttxdesc15MagazineNumberValue OBJECT-TYPE
    SYNTAX     INTEGER
    MAX-ACCESS read-write
    STATUS     current
    DESCRIPTION
    "Specifies teletext magazine number."
::= { enc1P126ttxdesc15MagazineNumberEntry 1 }

enc1P127ttxdesc15PageNumberTable OBJECT-TYPE
    SYNTAX SEQUENCE OF Enc1P127ttxdesc15PageNumberEntry
    MAX-ACCESS not-accessible
    STATUS     current
    DESCRIPTION
    "
    Name      : TTX Desc 15 Page Number
    Menu Path : /TS Mux/SI Parameters
    Units     : 
    Precision : 0
    Low Range : 0
    High Range: 255
    Details   : Specifies teletext page number.

     NOTE: Precision/Units/Ranges represent the state of the
           parameter during the MIB generation, and does not
           neccessary reflect the current state of the parameter
    "
::= { enc1Params 127 }

enc1P127ttxdesc15PageNumberEntry OBJECT-TYPE
    SYNTAX Enc1P127ttxdesc15PageNumberEntry
    MAX-ACCESS not-accessible
    STATUS     current
    DESCRIPTION
    "Table Entry for TTX Desc 15 Page Number"
    INDEX { slotId }
::= { enc1P127ttxdesc15PageNumberTable 1 }

Enc1P127ttxdesc15PageNumberEntry ::= SEQUENCE {
    enc1P127ttxdesc15PageNumberValue    INTEGER
}

enc1P127ttxdesc15PageNumberValue OBJECT-TYPE
    SYNTAX     INTEGER
    MAX-ACCESS read-write
    STATUS     current
    DESCRIPTION
    "Specifies teletext page number."
::= { enc1P127ttxdesc15PageNumberEntry 1 }

enc1P128ttxdesc16LanguageTable OBJECT-TYPE
    SYNTAX SEQUENCE OF Enc1P128ttxdesc16LanguageEntry
    MAX-ACCESS not-accessible
    STATUS     current
    DESCRIPTION
    "
    Name      : TTX Desc 16 Language
    Menu Path : /TS Mux/SI Parameters
    Details   : Specifies teletext descriptor language code.
    "
::= { enc1Params 128 }

enc1P128ttxdesc16LanguageEntry OBJECT-TYPE
    SYNTAX Enc1P128ttxdesc16LanguageEntry
    MAX-ACCESS not-accessible
    STATUS     current
    DESCRIPTION
    "Table Entry for TTX Desc 16 Language"
    INDEX { slotId }
::= { enc1P128ttxdesc16LanguageTable 1 }

Enc1P128ttxdesc16LanguageEntry ::= SEQUENCE {
    enc1P128ttxdesc16LanguageValue    DisplayString
}

enc1P128ttxdesc16LanguageValue OBJECT-TYPE
    SYNTAX     DisplayString
    MAX-ACCESS read-write
    STATUS     current
    DESCRIPTION
    "Specifies teletext descriptor language code."
::= { enc1P128ttxdesc16LanguageEntry 1 }

enc1P129ttxdesc16TypeTable OBJECT-TYPE
    SYNTAX SEQUENCE OF Enc1P129ttxdesc16TypeEntry
    MAX-ACCESS not-accessible
    STATUS     current
    DESCRIPTION
    "
    Name      : TTX Desc 16 Type
    Menu Path : /TS Mux/SI Parameters
    Units     : 
    Precision : 0
    Low Range : 0
    High Range: 31
    Details   : Specifies teletext descriptor type.

     NOTE: Precision/Units/Ranges represent the state of the
           parameter during the MIB generation, and does not
           neccessary reflect the current state of the parameter
    "
::= { enc1Params 129 }

enc1P129ttxdesc16TypeEntry OBJECT-TYPE
    SYNTAX Enc1P129ttxdesc16TypeEntry
    MAX-ACCESS not-accessible
    STATUS     current
    DESCRIPTION
    "Table Entry for TTX Desc 16 Type"
    INDEX { slotId }
::= { enc1P129ttxdesc16TypeTable 1 }

Enc1P129ttxdesc16TypeEntry ::= SEQUENCE {
    enc1P129ttxdesc16TypeValue    INTEGER
}

enc1P129ttxdesc16TypeValue OBJECT-TYPE
    SYNTAX     INTEGER
    MAX-ACCESS read-write
    STATUS     current
    DESCRIPTION
    "Specifies teletext descriptor type."
::= { enc1P129ttxdesc16TypeEntry 1 }

enc1P130ttxdesc16MagazineNumberTable OBJECT-TYPE
    SYNTAX SEQUENCE OF Enc1P130ttxdesc16MagazineNumberEntry
    MAX-ACCESS not-accessible
    STATUS     current
    DESCRIPTION
    "
    Name      : TTX Desc 16 Magazine Number
    Menu Path : /TS Mux/SI Parameters
    Units     : 
    Precision : 0
    Low Range : 1
    High Range: 8
    Details   : Specifies teletext magazine number.

     NOTE: Precision/Units/Ranges represent the state of the
           parameter during the MIB generation, and does not
           neccessary reflect the current state of the parameter
    "
::= { enc1Params 130 }

enc1P130ttxdesc16MagazineNumberEntry OBJECT-TYPE
    SYNTAX Enc1P130ttxdesc16MagazineNumberEntry
    MAX-ACCESS not-accessible
    STATUS     current
    DESCRIPTION
    "Table Entry for TTX Desc 16 Magazine Number"
    INDEX { slotId }
::= { enc1P130ttxdesc16MagazineNumberTable 1 }

Enc1P130ttxdesc16MagazineNumberEntry ::= SEQUENCE {
    enc1P130ttxdesc16MagazineNumberValue    INTEGER
}

enc1P130ttxdesc16MagazineNumberValue OBJECT-TYPE
    SYNTAX     INTEGER
    MAX-ACCESS read-write
    STATUS     current
    DESCRIPTION
    "Specifies teletext magazine number."
::= { enc1P130ttxdesc16MagazineNumberEntry 1 }

enc1P131ttxdesc16PageNumberTable OBJECT-TYPE
    SYNTAX SEQUENCE OF Enc1P131ttxdesc16PageNumberEntry
    MAX-ACCESS not-accessible
    STATUS     current
    DESCRIPTION
    "
    Name      : TTX Desc 16 Page Number
    Menu Path : /TS Mux/SI Parameters
    Units     : 
    Precision : 0
    Low Range : 0
    High Range: 255
    Details   : Specifies teletext page number.

     NOTE: Precision/Units/Ranges represent the state of the
           parameter during the MIB generation, and does not
           neccessary reflect the current state of the parameter
    "
::= { enc1Params 131 }

enc1P131ttxdesc16PageNumberEntry OBJECT-TYPE
    SYNTAX Enc1P131ttxdesc16PageNumberEntry
    MAX-ACCESS not-accessible
    STATUS     current
    DESCRIPTION
    "Table Entry for TTX Desc 16 Page Number"
    INDEX { slotId }
::= { enc1P131ttxdesc16PageNumberTable 1 }

Enc1P131ttxdesc16PageNumberEntry ::= SEQUENCE {
    enc1P131ttxdesc16PageNumberValue    INTEGER
}

enc1P131ttxdesc16PageNumberValue OBJECT-TYPE
    SYNTAX     INTEGER
    MAX-ACCESS read-write
    STATUS     current
    DESCRIPTION
    "Specifies teletext page number."
::= { enc1P131ttxdesc16PageNumberEntry 1 }

enc1P132lossofInputTable OBJECT-TYPE
    SYNTAX SEQUENCE OF Enc1P132lossofInputEntry
    MAX-ACCESS not-accessible
    STATUS     current
    DESCRIPTION
    "
    Name      : Loss of Input
    Menu Path : /Video/Input
    Details   : Selects program behavior for loss of video input.
    "
::= { enc1Params 132 }

enc1P132lossofInputEntry OBJECT-TYPE
    SYNTAX Enc1P132lossofInputEntry
    MAX-ACCESS not-accessible
    STATUS     current
    DESCRIPTION
    "Table Entry for Loss of Input"
    INDEX { slotId }
::= { enc1P132lossofInputTable 1 }

Enc1P132lossofInputEntry ::= SEQUENCE {
    enc1P132lossofInputValue    Enc1E33enumObj
}

enc1P132lossofInputValue OBJECT-TYPE
    SYNTAX     Enc1E33enumObj
    MAX-ACCESS read-write
    STATUS     current
    DESCRIPTION
    "Selects program behavior for loss of video input."
::= { enc1P132lossofInputEntry 1 }

enc1P133primarySourceTable OBJECT-TYPE
    SYNTAX SEQUENCE OF Enc1P133primarySourceEntry
    MAX-ACCESS not-accessible
    STATUS     current
    DESCRIPTION
    "
    Name      : Primary Source
    Menu Path : /Video/Input
    Details   : Selects primary video input source for encoding.
    "
::= { enc1Params 133 }

enc1P133primarySourceEntry OBJECT-TYPE
    SYNTAX Enc1P133primarySourceEntry
    MAX-ACCESS not-accessible
    STATUS     current
    DESCRIPTION
    "Table Entry for Primary Source"
    INDEX { slotId }
::= { enc1P133primarySourceTable 1 }

Enc1P133primarySourceEntry ::= SEQUENCE {
    enc1P133primarySourceValue    Enc1E35enumObj
}

enc1P133primarySourceValue OBJECT-TYPE
    SYNTAX     Enc1E35enumObj
    MAX-ACCESS read-write
    STATUS     current
    DESCRIPTION
    "Selects primary video input source for encoding."
::= { enc1P133primarySourceEntry 1 }

enc1P134sourceFormatTable OBJECT-TYPE
    SYNTAX SEQUENCE OF Enc1P134sourceFormatEntry
    MAX-ACCESS not-accessible
    STATUS     current
    DESCRIPTION
    "
    Name      : Source Format
    Menu Path : /Video/Input
    Details   : Specifies input video standard for encoding.
    "
::= { enc1Params 134 }

enc1P134sourceFormatEntry OBJECT-TYPE
    SYNTAX Enc1P134sourceFormatEntry
    MAX-ACCESS not-accessible
    STATUS     current
    DESCRIPTION
    "Table Entry for Source Format"
    INDEX { slotId }
::= { enc1P134sourceFormatTable 1 }

Enc1P134sourceFormatEntry ::= SEQUENCE {
    enc1P134sourceFormatValue    Enc1E40enumObj
}

enc1P134sourceFormatValue OBJECT-TYPE
    SYNTAX     Enc1E40enumObj
    MAX-ACCESS read-write
    STATUS     current
    DESCRIPTION
    "Specifies input video standard for encoding."
::= { enc1P134sourceFormatEntry 1 }

enc1P135oldResolutionTable OBJECT-TYPE
    SYNTAX SEQUENCE OF Enc1P135oldResolutionEntry
    MAX-ACCESS not-accessible
    STATUS     current
    DESCRIPTION
    "
    Name      : Old Resolution
    Menu Path : Not Applicable
    Details   : Backward compatible version of video encoding resolution.
    "
::= { enc1Params 135 }

enc1P135oldResolutionEntry OBJECT-TYPE
    SYNTAX Enc1P135oldResolutionEntry
    MAX-ACCESS not-accessible
    STATUS     current
    DESCRIPTION
    "Table Entry for Old Resolution"
    INDEX { slotId }
::= { enc1P135oldResolutionTable 1 }

Enc1P135oldResolutionEntry ::= SEQUENCE {
    enc1P135oldResolutionValue    Enc1E42enumObj
}

enc1P135oldResolutionValue OBJECT-TYPE
    SYNTAX     Enc1E42enumObj
    MAX-ACCESS read-write
    STATUS     current
    DESCRIPTION
    "Backward compatible version of video encoding resolution."
::= { enc1P135oldResolutionEntry 1 }

enc1P136arccontrolTable OBJECT-TYPE
    SYNTAX SEQUENCE OF Enc1P136arccontrolEntry
    MAX-ACCESS not-accessible
    STATUS     current
    DESCRIPTION
    "
    Name      : ARC Control
    Menu Path : /Video/Input
    Details   : Specifies input video aspect ratio.
    "
::= { enc1Params 136 }

enc1P136arccontrolEntry OBJECT-TYPE
    SYNTAX Enc1P136arccontrolEntry
    MAX-ACCESS not-accessible
    STATUS     current
    DESCRIPTION
    "Table Entry for ARC Control"
    INDEX { slotId }
::= { enc1P136arccontrolTable 1 }

Enc1P136arccontrolEntry ::= SEQUENCE {
    enc1P136arccontrolValue    Enc1E52enumObj
}

enc1P136arccontrolValue OBJECT-TYPE
    SYNTAX     Enc1E52enumObj
    MAX-ACCESS read-write
    STATUS     current
    DESCRIPTION
    "Specifies input video aspect ratio."
::= { enc1P136arccontrolEntry 1 }

enc1P137chromaSamplingTable OBJECT-TYPE
    SYNTAX SEQUENCE OF Enc1P137chromaSamplingEntry
    MAX-ACCESS not-accessible
    STATUS     current
    DESCRIPTION
    "
    Name      : Chroma Sampling
    Menu Path : /Video/Compression
    Details   : Specifies the chroma sampling format used for encoding.
    "
::= { enc1Params 137 }

enc1P137chromaSamplingEntry OBJECT-TYPE
    SYNTAX Enc1P137chromaSamplingEntry
    MAX-ACCESS not-accessible
    STATUS     current
    DESCRIPTION
    "Table Entry for Chroma Sampling"
    INDEX { slotId }
::= { enc1P137chromaSamplingTable 1 }

Enc1P137chromaSamplingEntry ::= SEQUENCE {
    enc1P137chromaSamplingValue    Enc1E48enumObj
}

enc1P137chromaSamplingValue OBJECT-TYPE
    SYNTAX     Enc1E48enumObj
    MAX-ACCESS read-write
    STATUS     current
    DESCRIPTION
    "Specifies the chroma sampling format used for encoding."
::= { enc1P137chromaSamplingEntry 1 }

enc1P138codingProfileTable OBJECT-TYPE
    SYNTAX SEQUENCE OF Enc1P138codingProfileEntry
    MAX-ACCESS not-accessible
    STATUS     current
    DESCRIPTION
    "
    Name      : Coding Profile
    Menu Path : /Video/Compression
    Details   : Specifies the video coding standard and profile.
    "
::= { enc1Params 138 }

enc1P138codingProfileEntry OBJECT-TYPE
    SYNTAX Enc1P138codingProfileEntry
    MAX-ACCESS not-accessible
    STATUS     current
    DESCRIPTION
    "Table Entry for Coding Profile"
    INDEX { slotId }
::= { enc1P138codingProfileTable 1 }

Enc1P138codingProfileEntry ::= SEQUENCE {
    enc1P138codingProfileValue    Enc1E44enumObj
}

enc1P138codingProfileValue OBJECT-TYPE
    SYNTAX     Enc1E44enumObj
    MAX-ACCESS read-write
    STATUS     current
    DESCRIPTION
    "Specifies the video coding standard and profile."
::= { enc1P138codingProfileEntry 1 }

enc1P139cbrTable OBJECT-TYPE
    SYNTAX SEQUENCE OF Enc1P139cbrEntry
    MAX-ACCESS not-accessible
    STATUS     current
    DESCRIPTION
    "
    Name      : CBR
    Menu Path : /Video/Compression
    Details   : Specifies whether encoder is in CBR mode, Capped VBR mode or StatMux Ready mode
    "
::= { enc1Params 139 }

enc1P139cbrEntry OBJECT-TYPE
    SYNTAX Enc1P139cbrEntry
    MAX-ACCESS not-accessible
    STATUS     current
    DESCRIPTION
    "Table Entry for CBR"
    INDEX { slotId }
::= { enc1P139cbrTable 1 }

Enc1P139cbrEntry ::= SEQUENCE {
    enc1P139cbrValue    Enc1E29enumObj
}

enc1P139cbrValue OBJECT-TYPE
    SYNTAX     Enc1E29enumObj
    MAX-ACCESS read-write
    STATUS     current
    DESCRIPTION
    "Specifies whether encoder is in CBR mode, Capped VBR mode or StatMux Ready mode"
::= { enc1P139cbrEntry 1 }

enc1P140gopStructureTable OBJECT-TYPE
    SYNTAX SEQUENCE OF Enc1P140gopStructureEntry
    MAX-ACCESS not-accessible
    STATUS     current
    DESCRIPTION
    "
    Name      : Gop Structure
    Menu Path : /Video/Compression
    Details   : Specifies GOP structure to be used for encoding.
    "
::= { enc1Params 140 }

enc1P140gopStructureEntry OBJECT-TYPE
    SYNTAX Enc1P140gopStructureEntry
    MAX-ACCESS not-accessible
    STATUS     current
    DESCRIPTION
    "Table Entry for Gop Structure"
    INDEX { slotId }
::= { enc1P140gopStructureTable 1 }

Enc1P140gopStructureEntry ::= SEQUENCE {
    enc1P140gopStructureValue    Enc1E56enumObj
}

enc1P140gopStructureValue OBJECT-TYPE
    SYNTAX     Enc1E56enumObj
    MAX-ACCESS read-write
    STATUS     current
    DESCRIPTION
    "Specifies GOP structure to be used for encoding."
::= { enc1P140gopStructureEntry 1 }

enc1P141gopSizeTable OBJECT-TYPE
    SYNTAX SEQUENCE OF Enc1P141gopSizeEntry
    MAX-ACCESS not-accessible
    STATUS     current
    DESCRIPTION
    "
    Name      : Gop Size
    Menu Path : /Video/Compression
    Details   : Specifies GOP size to be used while encoding.
    "
::= { enc1Params 141 }

enc1P141gopSizeEntry OBJECT-TYPE
    SYNTAX Enc1P141gopSizeEntry
    MAX-ACCESS not-accessible
    STATUS     current
    DESCRIPTION
    "Table Entry for Gop Size"
    INDEX { slotId }
::= { enc1P141gopSizeTable 1 }

Enc1P141gopSizeEntry ::= SEQUENCE {
    enc1P141gopSizeValue    Enc1E57enumObj
}

enc1P141gopSizeValue OBJECT-TYPE
    SYNTAX     Enc1E57enumObj
    MAX-ACCESS read-write
    STATUS     current
    DESCRIPTION
    "Specifies GOP size to be used while encoding."
::= { enc1P141gopSizeEntry 1 }

enc1P142closedGopTable OBJECT-TYPE
    SYNTAX SEQUENCE OF Enc1P142closedGopEntry
    MAX-ACCESS not-accessible
    STATUS     current
    DESCRIPTION
    "
    Name      : Closed Gop
    Menu Path : /Video/Compression
    Details   : Specifies if every GOP is closed.
    "
::= { enc1Params 142 }

enc1P142closedGopEntry OBJECT-TYPE
    SYNTAX Enc1P142closedGopEntry
    MAX-ACCESS not-accessible
    STATUS     current
    DESCRIPTION
    "Table Entry for Closed Gop"
    INDEX { slotId }
::= { enc1P142closedGopTable 1 }

Enc1P142closedGopEntry ::= SEQUENCE {
    enc1P142closedGopValue    Enc1E1enumObj
}

enc1P142closedGopValue OBJECT-TYPE
    SYNTAX     Enc1E1enumObj
    MAX-ACCESS read-write
    STATUS     current
    DESCRIPTION
    "Specifies if every GOP is closed."
::= { enc1P142closedGopEntry 1 }

enc1P143tgtQpTable OBJECT-TYPE
    SYNTAX SEQUENCE OF Enc1P143tgtQpEntry
    MAX-ACCESS not-accessible
    STATUS     current
    DESCRIPTION
    "
    Name      : Tgt Qp
    Menu Path : /Video/Compression
    Units     : 
    Precision : 0
    Low Range : 2
    High Range: 51
    Details   : Specifies the target quantizer level used when in VBR mode.

     NOTE: Precision/Units/Ranges represent the state of the
           parameter during the MIB generation, and does not
           neccessary reflect the current state of the parameter
    "
::= { enc1Params 143 }

enc1P143tgtQpEntry OBJECT-TYPE
    SYNTAX Enc1P143tgtQpEntry
    MAX-ACCESS not-accessible
    STATUS     current
    DESCRIPTION
    "Table Entry for Tgt Qp"
    INDEX { slotId }
::= { enc1P143tgtQpTable 1 }

Enc1P143tgtQpEntry ::= SEQUENCE {
    enc1P143tgtQpValue    INTEGER
}

enc1P143tgtQpValue OBJECT-TYPE
    SYNTAX     INTEGER
    MAX-ACCESS read-write
    STATUS     current
    DESCRIPTION
    "Specifies the target quantizer level used when in VBR mode."
::= { enc1P143tgtQpEntry 1 }

enc1P144filmDetectTable OBJECT-TYPE
    SYNTAX SEQUENCE OF Enc1P144filmDetectEntry
    MAX-ACCESS not-accessible
    STATUS     current
    DESCRIPTION
    "
    Name      : Film Detect
    Menu Path : /Video/Compression
    Details   : Enables/disables film mode detection.
    "
::= { enc1Params 144 }

enc1P144filmDetectEntry OBJECT-TYPE
    SYNTAX Enc1P144filmDetectEntry
    MAX-ACCESS not-accessible
    STATUS     current
    DESCRIPTION
    "Table Entry for Film Detect"
    INDEX { slotId }
::= { enc1P144filmDetectTable 1 }

Enc1P144filmDetectEntry ::= SEQUENCE {
    enc1P144filmDetectValue    Enc1E60enumObj
}

enc1P144filmDetectValue OBJECT-TYPE
    SYNTAX     Enc1E60enumObj
    MAX-ACCESS read-write
    STATUS     current
    DESCRIPTION
    "Enables/disables film mode detection."
::= { enc1P144filmDetectEntry 1 }

enc1P145preprocTable OBJECT-TYPE
    SYNTAX SEQUENCE OF Enc1P145preprocEntry
    MAX-ACCESS not-accessible
    STATUS     current
    DESCRIPTION
    "
    Name      : Preproc
    Menu Path : /Video/Compression
    Details   : Specifies the level of preprocessing applied to the input video.
    "
::= { enc1Params 145 }

enc1P145preprocEntry OBJECT-TYPE
    SYNTAX Enc1P145preprocEntry
    MAX-ACCESS not-accessible
    STATUS     current
    DESCRIPTION
    "Table Entry for Preproc"
    INDEX { slotId }
::= { enc1P145preprocTable 1 }

Enc1P145preprocEntry ::= SEQUENCE {
    enc1P145preprocValue    Enc1E59enumObj
}

enc1P145preprocValue OBJECT-TYPE
    SYNTAX     Enc1E59enumObj
    MAX-ACCESS read-write
    STATUS     current
    DESCRIPTION
    "Specifies the level of preprocessing applied to the input video."
::= { enc1P145preprocEntry 1 }

enc1P147lossofSignalTable OBJECT-TYPE
    SYNTAX SEQUENCE OF Enc1P147lossofSignalEntry
    MAX-ACCESS not-accessible
    STATUS     current
    DESCRIPTION
    "
    Name      : Loss of Signal
    Menu Path : /Video/Input/Status
    Details   : Indicates loss of signal fault.
    "
::= { enc1Params 147 }

enc1P147lossofSignalEntry OBJECT-TYPE
    SYNTAX Enc1P147lossofSignalEntry
    MAX-ACCESS not-accessible
    STATUS     current
    DESCRIPTION
    "Table Entry for Loss of Signal"
    INDEX { slotId }
::= { enc1P147lossofSignalTable 1 }

Enc1P147lossofSignalEntry ::= SEQUENCE {
    enc1P147lossofSignalValue    Enc1E5enumObj
}

enc1P147lossofSignalValue OBJECT-TYPE
    SYNTAX     Enc1E5enumObj
    MAX-ACCESS read-only
    STATUS     current
    DESCRIPTION
    "Indicates loss of signal fault."
::= { enc1P147lossofSignalEntry 1 }

enc1P148inputStandardTable OBJECT-TYPE
    SYNTAX SEQUENCE OF Enc1P148inputStandardEntry
    MAX-ACCESS not-accessible
    STATUS     current
    DESCRIPTION
    "
    Name      : Input Standard
    Menu Path : /Video/Input/Status
    Details   : Shows the current input video standard.
    "
::= { enc1Params 148 }

enc1P148inputStandardEntry OBJECT-TYPE
    SYNTAX Enc1P148inputStandardEntry
    MAX-ACCESS not-accessible
    STATUS     current
    DESCRIPTION
    "Table Entry for Input Standard"
    INDEX { slotId }
::= { enc1P148inputStandardTable 1 }

Enc1P148inputStandardEntry ::= SEQUENCE {
    enc1P148inputStandardValue    Enc1E61enumObj
}

enc1P148inputStandardValue OBJECT-TYPE
    SYNTAX     Enc1E61enumObj
    MAX-ACCESS read-only
    STATUS     current
    DESCRIPTION
    "Shows the current input video standard."
::= { enc1P148inputStandardEntry 1 }

enc1P149videoElementaryStreamRateTable OBJECT-TYPE
    SYNTAX SEQUENCE OF Enc1P149videoElementaryStreamRateEntry
    MAX-ACCESS not-accessible
    STATUS     current
    DESCRIPTION
    "
    Name      : Video Elementary Stream Rate
    Menu Path : /Video/Compression/Status
    Units     : Mbits/sec
    Precision : 6
    Low Range : 0
    High Range: 62500000
    Details   : Shows the average elementary stream bitrate. (Units: Mbits/sec)

     NOTE: Precision/Units/Ranges represent the state of the
           parameter during the MIB generation, and does not
           neccessary reflect the current state of the parameter
    "
::= { enc1Params 149 }

enc1P149videoElementaryStreamRateEntry OBJECT-TYPE
    SYNTAX Enc1P149videoElementaryStreamRateEntry
    MAX-ACCESS not-accessible
    STATUS     current
    DESCRIPTION
    "Table Entry for Video Elementary Stream Rate"
    INDEX { slotId }
::= { enc1P149videoElementaryStreamRateTable 1 }

Enc1P149videoElementaryStreamRateEntry ::= SEQUENCE {
    enc1P149videoElementaryStreamRateValue    INTEGER
}

enc1P149videoElementaryStreamRateValue OBJECT-TYPE
    SYNTAX     INTEGER
    MAX-ACCESS read-only
    STATUS     current
    DESCRIPTION
    "Shows the average elementary stream bitrate. (Units: Mbits/sec)"
::= { enc1P149videoElementaryStreamRateEntry 1 }

enc1P150ccservicesTable OBJECT-TYPE
    SYNTAX SEQUENCE OF Enc1P150ccservicesEntry
    MAX-ACCESS not-accessible
    STATUS     current
    DESCRIPTION
    "
    Table     : CC Services
    Menu Path : /Data/Closed Caption
    Details   : 
    "
::= { enc1Params 150 }

enc1P150ccservicesEntry OBJECT-TYPE
    SYNTAX Enc1P150ccservicesEntry
    MAX-ACCESS not-accessible
    STATUS     current
    DESCRIPTION
    "Table Entry for CC Services"
    INDEX { slotId, tableIdx, enc1P150ccservicesServiceInfo }
::= { enc1P150ccservicesTable 1 }

Enc1P150ccservicesEntry ::= SEQUENCE {
    enc1T150C1captionServiceEnableValue    Enc1E0enumObj,
    enc1T150C2captionServiceTypeValue    Enc1E120enumObj,
    enc1T150C3captionServiceNumberValue    INTEGER,
    enc1T150C4captionServiceLanguageValue    DisplayString,
    enc1T150C5captionServiceEasyReaderValue    Enc1E121enumObj,
    enc1T150C6captionServiceWideAspectRatioValue    Enc1E122enumObj,
    enc1P150ccservicesServiceInfo    INTEGER
}

enc1T150C1captionServiceEnableValue OBJECT-TYPE
    SYNTAX     Enc1E0enumObj
    MAX-ACCESS read-write
    STATUS     current
    DESCRIPTION
    "
    Column    : Caption Service Enable
    Details   : Specifies whether service is enabled or disabled.
    "
::= { enc1P150ccservicesEntry 1 }

enc1T150C2captionServiceTypeValue OBJECT-TYPE
    SYNTAX     Enc1E120enumObj
    MAX-ACCESS read-write
    STATUS     current
    DESCRIPTION
    "
    Column    : Caption Service Type
    Details   : Specifies whether caption service has 608 or 708 captions.
    "
::= { enc1P150ccservicesEntry 2 }

enc1T150C3captionServiceNumberValue OBJECT-TYPE
    SYNTAX     INTEGER
    MAX-ACCESS read-write
    STATUS     current
    DESCRIPTION
    "
    Column    : Caption Service Number
    Units     : 
    Precision : 0
    LowRange  : 0
    High Range: 63
    Details   : Specifies number for caption service.

     NOTE: Precision/Units/Ranges represent the state of the
           first row of the table during the MIB generation,
           and does not neccessary reflect current value of
           the table or row that is being modified
    "
::= { enc1P150ccservicesEntry 3 }

enc1T150C4captionServiceLanguageValue OBJECT-TYPE
    SYNTAX     DisplayString
    MAX-ACCESS read-write
    STATUS     current
    DESCRIPTION
    "
    Column    : Caption Service Language
    Details   : Specifies language of caption service.
    "
::= { enc1P150ccservicesEntry 4 }

enc1T150C5captionServiceEasyReaderValue OBJECT-TYPE
    SYNTAX     Enc1E121enumObj
    MAX-ACCESS read-write
    STATUS     current
    DESCRIPTION
    "
    Column    : Caption Service Easy Reader
    Details   : Specifies whether captions service is in easy reader format.
    "
::= { enc1P150ccservicesEntry 5 }

enc1T150C6captionServiceWideAspectRatioValue OBJECT-TYPE
    SYNTAX     Enc1E122enumObj
    MAX-ACCESS read-write
    STATUS     current
    DESCRIPTION
    "
    Column    : Caption Service Wide Aspect Ratio
    Details   : Specifies whether caption service is wide aspect ratio (16x9) or not.
    "
::= { enc1P150ccservicesEntry 6 }

enc1P150ccservicesServiceInfo OBJECT-TYPE
    SYNTAX     INTEGER
    MAX-ACCESS not-accessible
    STATUS     current
    DESCRIPTION
    "Index representing array dimension ServiceInfo"
::= { enc1P150ccservicesEntry 10001 }

enc1P151syncErrorTable OBJECT-TYPE
    SYNTAX SEQUENCE OF Enc1P151syncErrorEntry
    MAX-ACCESS not-accessible
    STATUS     current
    DESCRIPTION
    "
    Name      : Sync Error
    Menu Path : /Video/Input/Status
    Units     : 
    Precision : 0
    Low Range : 0
    High Range: -1
    Details   : Indicates the sync error count.

     NOTE: Precision/Units/Ranges represent the state of the
           parameter during the MIB generation, and does not
           neccessary reflect the current state of the parameter
    "
::= { enc1Params 151 }

enc1P151syncErrorEntry OBJECT-TYPE
    SYNTAX Enc1P151syncErrorEntry
    MAX-ACCESS not-accessible
    STATUS     current
    DESCRIPTION
    "Table Entry for Sync Error"
    INDEX { slotId }
::= { enc1P151syncErrorTable 1 }

Enc1P151syncErrorEntry ::= SEQUENCE {
    enc1P151syncErrorValue    INTEGER
}

enc1P151syncErrorValue OBJECT-TYPE
    SYNTAX     INTEGER
    MAX-ACCESS read-only
    STATUS     current
    DESCRIPTION
    "Indicates the sync error count."
::= { enc1P151syncErrorEntry 1 }

enc1P154edhpresentTable OBJECT-TYPE
    SYNTAX SEQUENCE OF Enc1P154edhpresentEntry
    MAX-ACCESS not-accessible
    STATUS     current
    DESCRIPTION
    "
    Name      : EDH Present
    Menu Path : /Video/Input/Status
    Details   : Indicates whether EDH check bytes are present.
    "
::= { enc1Params 154 }

enc1P154edhpresentEntry OBJECT-TYPE
    SYNTAX Enc1P154edhpresentEntry
    MAX-ACCESS not-accessible
    STATUS     current
    DESCRIPTION
    "Table Entry for EDH Present"
    INDEX { slotId }
::= { enc1P154edhpresentTable 1 }

Enc1P154edhpresentEntry ::= SEQUENCE {
    enc1P154edhpresentValue    Enc1E9enumObj
}

enc1P154edhpresentValue OBJECT-TYPE
    SYNTAX     Enc1E9enumObj
    MAX-ACCESS read-only
    STATUS     current
    DESCRIPTION
    "Indicates whether EDH check bytes are present."
::= { enc1P154edhpresentEntry 1 }

enc1P155nameTable OBJECT-TYPE
    SYNTAX SEQUENCE OF Enc1P155nameEntry
    MAX-ACCESS not-accessible
    STATUS     current
    DESCRIPTION
    "
    Name      : Name
    Menu Path : /Video/Pip
    Details   : Specifies program name for PIP program.
    "
::= { enc1Params 155 }

enc1P155nameEntry OBJECT-TYPE
    SYNTAX Enc1P155nameEntry
    MAX-ACCESS not-accessible
    STATUS     current
    DESCRIPTION
    "Table Entry for Name"
    INDEX { slotId }
::= { enc1P155nameTable 1 }

Enc1P155nameEntry ::= SEQUENCE {
    enc1P155nameValue    DisplayString
}

enc1P155nameValue OBJECT-TYPE
    SYNTAX     DisplayString
    MAX-ACCESS read-write
    STATUS     current
    DESCRIPTION
    "Specifies program name for PIP program."
::= { enc1P155nameEntry 1 }

enc1P156tagTable OBJECT-TYPE
    SYNTAX SEQUENCE OF Enc1P156tagEntry
    MAX-ACCESS not-accessible
    STATUS     current
    DESCRIPTION
    "
    Name      : Tag
    Menu Path : /Video/Pip
    Details   : Specifies program tag for PIP program.
    "
::= { enc1Params 156 }

enc1P156tagEntry OBJECT-TYPE
    SYNTAX Enc1P156tagEntry
    MAX-ACCESS not-accessible
    STATUS     current
    DESCRIPTION
    "Table Entry for Tag"
    INDEX { slotId }
::= { enc1P156tagTable 1 }

Enc1P156tagEntry ::= SEQUENCE {
    enc1P156tagValue    DisplayString
}

enc1P156tagValue OBJECT-TYPE
    SYNTAX     DisplayString
    MAX-ACCESS read-write
    STATUS     current
    DESCRIPTION
    "Specifies program tag for PIP program."
::= { enc1P156tagEntry 1 }

enc1P157totalTSRateTable OBJECT-TYPE
    SYNTAX SEQUENCE OF Enc1P157totalTSRateEntry
    MAX-ACCESS not-accessible
    STATUS     current
    DESCRIPTION
    "
    Name      : Total TS Rate
    Menu Path : /Video/Pip
    Units     : Mbits/sec
    Precision : 6
    Low Range : 100000
    High Range: 1000000
    Details   : Total transport stream rate for the PIP program (Units: Mbits/sec)

     NOTE: Precision/Units/Ranges represent the state of the
           parameter during the MIB generation, and does not
           neccessary reflect the current state of the parameter
    "
::= { enc1Params 157 }

enc1P157totalTSRateEntry OBJECT-TYPE
    SYNTAX Enc1P157totalTSRateEntry
    MAX-ACCESS not-accessible
    STATUS     current
    DESCRIPTION
    "Table Entry for Total TS Rate"
    INDEX { slotId }
::= { enc1P157totalTSRateTable 1 }

Enc1P157totalTSRateEntry ::= SEQUENCE {
    enc1P157totalTSRateValue    INTEGER
}

enc1P157totalTSRateValue OBJECT-TYPE
    SYNTAX     INTEGER
    MAX-ACCESS read-write
    STATUS     current
    DESCRIPTION
    "Total transport stream rate for the PIP program (Units: Mbits/sec)"
::= { enc1P157totalTSRateEntry 1 }

enc1P158pipresolutionTable OBJECT-TYPE
    SYNTAX SEQUENCE OF Enc1P158pipresolutionEntry
    MAX-ACCESS not-accessible
    STATUS     current
    DESCRIPTION
    "
    Name      : PIP Resolution
    Menu Path : /Video/Pip
    Details   : Specifies encoding resolution for the PIP program.
    "
::= { enc1Params 158 }

enc1P158pipresolutionEntry OBJECT-TYPE
    SYNTAX Enc1P158pipresolutionEntry
    MAX-ACCESS not-accessible
    STATUS     current
    DESCRIPTION
    "Table Entry for PIP Resolution"
    INDEX { slotId }
::= { enc1P158pipresolutionTable 1 }

Enc1P158pipresolutionEntry ::= SEQUENCE {
    enc1P158pipresolutionValue    Enc1E43enumObj
}

enc1P158pipresolutionValue OBJECT-TYPE
    SYNTAX     Enc1E43enumObj
    MAX-ACCESS read-write
    STATUS     current
    DESCRIPTION
    "Specifies encoding resolution for the PIP program."
::= { enc1P158pipresolutionEntry 1 }

enc1P159source1Table OBJECT-TYPE
    SYNTAX SEQUENCE OF Enc1P159source1Entry
    MAX-ACCESS not-accessible
    STATUS     current
    DESCRIPTION
    "
    Name      : Source 1
    Menu Path : /Audio/Audio 1
    Details   : Specifies audio source (pair) for this codec.
    "
::= { enc1Params 159 }

enc1P159source1Entry OBJECT-TYPE
    SYNTAX Enc1P159source1Entry
    MAX-ACCESS not-accessible
    STATUS     current
    DESCRIPTION
    "Table Entry for Source 1"
    INDEX { slotId }
::= { enc1P159source1Table 1 }

Enc1P159source1Entry ::= SEQUENCE {
    enc1P159source1Value    Enc1E70enumObj
}

enc1P159source1Value OBJECT-TYPE
    SYNTAX     Enc1E70enumObj
    MAX-ACCESS read-write
    STATUS     current
    DESCRIPTION
    "Specifies audio source (pair) for this codec."
::= { enc1P159source1Entry 1 }

enc1P160source2Table OBJECT-TYPE
    SYNTAX SEQUENCE OF Enc1P160source2Entry
    MAX-ACCESS not-accessible
    STATUS     current
    DESCRIPTION
    "
    Name      : Source 2
    Menu Path : /Audio/Audio 1
    Details   : Specifies second audio source (pair) for this multichannel codec.
    "
::= { enc1Params 160 }

enc1P160source2Entry OBJECT-TYPE
    SYNTAX Enc1P160source2Entry
    MAX-ACCESS not-accessible
    STATUS     current
    DESCRIPTION
    "Table Entry for Source 2"
    INDEX { slotId }
::= { enc1P160source2Table 1 }

Enc1P160source2Entry ::= SEQUENCE {
    enc1P160source2Value    Enc1E70enumObj
}

enc1P160source2Value OBJECT-TYPE
    SYNTAX     Enc1E70enumObj
    MAX-ACCESS read-write
    STATUS     current
    DESCRIPTION
    "Specifies second audio source (pair) for this multichannel codec."
::= { enc1P160source2Entry 1 }

enc1P161source3Table OBJECT-TYPE
    SYNTAX SEQUENCE OF Enc1P161source3Entry
    MAX-ACCESS not-accessible
    STATUS     current
    DESCRIPTION
    "
    Name      : Source 3
    Menu Path : /Audio/Audio 1
    Details   : Specifies third audio source (pair) for this multichannel codec.
    "
::= { enc1Params 161 }

enc1P161source3Entry OBJECT-TYPE
    SYNTAX Enc1P161source3Entry
    MAX-ACCESS not-accessible
    STATUS     current
    DESCRIPTION
    "Table Entry for Source 3"
    INDEX { slotId }
::= { enc1P161source3Table 1 }

Enc1P161source3Entry ::= SEQUENCE {
    enc1P161source3Value    Enc1E70enumObj
}

enc1P161source3Value OBJECT-TYPE
    SYNTAX     Enc1E70enumObj
    MAX-ACCESS read-write
    STATUS     current
    DESCRIPTION
    "Specifies third audio source (pair) for this multichannel codec."
::= { enc1P161source3Entry 1 }

enc1P162source4Table OBJECT-TYPE
    SYNTAX SEQUENCE OF Enc1P162source4Entry
    MAX-ACCESS not-accessible
    STATUS     current
    DESCRIPTION
    "
    Name      : Source 4
    Menu Path : /Audio/Audio 1
    Details   : Specifies fourth audio source (pair) for this multichannel codec.
    "
::= { enc1Params 162 }

enc1P162source4Entry OBJECT-TYPE
    SYNTAX Enc1P162source4Entry
    MAX-ACCESS not-accessible
    STATUS     current
    DESCRIPTION
    "Table Entry for Source 4"
    INDEX { slotId }
::= { enc1P162source4Table 1 }

Enc1P162source4Entry ::= SEQUENCE {
    enc1P162source4Value    Enc1E70enumObj
}

enc1P162source4Value OBJECT-TYPE
    SYNTAX     Enc1E70enumObj
    MAX-ACCESS read-write
    STATUS     current
    DESCRIPTION
    "Specifies fourth audio source (pair) for this multichannel codec."
::= { enc1P162source4Entry 1 }

enc1P163preProcessingTable OBJECT-TYPE
    SYNTAX SEQUENCE OF Enc1P163preProcessingEntry
    MAX-ACCESS not-accessible
    STATUS     current
    DESCRIPTION
    "
    Name      : Pre Processing
    Menu Path : Not Applicable
    Details   : Specifies special processing for audio channel
    "
::= { enc1Params 163 }

enc1P163preProcessingEntry OBJECT-TYPE
    SYNTAX Enc1P163preProcessingEntry
    MAX-ACCESS not-accessible
    STATUS     current
    DESCRIPTION
    "Table Entry for Pre Processing"
    INDEX { slotId }
::= { enc1P163preProcessingTable 1 }

Enc1P163preProcessingEntry ::= SEQUENCE {
    enc1P163preProcessingValue    Enc1E72enumObj
}

enc1P163preProcessingValue OBJECT-TYPE
    SYNTAX     Enc1E72enumObj
    MAX-ACCESS read-write
    STATUS     current
    DESCRIPTION
    "Specifies special processing for audio channel"
::= { enc1P163preProcessingEntry 1 }

enc1P164delayTable OBJECT-TYPE
    SYNTAX SEQUENCE OF Enc1P164delayEntry
    MAX-ACCESS not-accessible
    STATUS     current
    DESCRIPTION
    "
    Name      : Delay
    Menu Path : /Audio/Audio 1
    Units     : msec
    Precision : 0
    Low Range : -500
    High Range: 500
    Details   : Specify an additional audio delay, relative to video delay.

     NOTE: Precision/Units/Ranges represent the state of the
           parameter during the MIB generation, and does not
           neccessary reflect the current state of the parameter
    "
::= { enc1Params 164 }

enc1P164delayEntry OBJECT-TYPE
    SYNTAX Enc1P164delayEntry
    MAX-ACCESS not-accessible
    STATUS     current
    DESCRIPTION
    "Table Entry for Delay"
    INDEX { slotId }
::= { enc1P164delayTable 1 }

Enc1P164delayEntry ::= SEQUENCE {
    enc1P164delayValue    INTEGER
}

enc1P164delayValue OBJECT-TYPE
    SYNTAX     INTEGER
    MAX-ACCESS read-write
    STATUS     current
    DESCRIPTION
    "Specify an additional audio delay, relative to video delay."
::= { enc1P164delayEntry 1 }

enc1P165gainTable OBJECT-TYPE
    SYNTAX SEQUENCE OF Enc1P165gainEntry
    MAX-ACCESS not-accessible
    STATUS     current
    DESCRIPTION
    "
    Name      : Gain
    Menu Path : /Audio/Audio 1
    Units     : dB
    Precision : 1
    Low Range : -800
    High Range: 400
    Details   : Apply a gain (or attenuation) to all source channels.

     NOTE: Precision/Units/Ranges represent the state of the
           parameter during the MIB generation, and does not
           neccessary reflect the current state of the parameter
    "
::= { enc1Params 165 }

enc1P165gainEntry OBJECT-TYPE
    SYNTAX Enc1P165gainEntry
    MAX-ACCESS not-accessible
    STATUS     current
    DESCRIPTION
    "Table Entry for Gain"
    INDEX { slotId }
::= { enc1P165gainTable 1 }

Enc1P165gainEntry ::= SEQUENCE {
    enc1P165gainValue    INTEGER
}

enc1P165gainValue OBJECT-TYPE
    SYNTAX     INTEGER
    MAX-ACCESS read-write
    STATUS     current
    DESCRIPTION
    "Apply a gain (or attenuation) to all source channels."
::= { enc1P165gainEntry 1 }

enc1P167deemphasisTable OBJECT-TYPE
    SYNTAX SEQUENCE OF Enc1P167deemphasisEntry
    MAX-ACCESS not-accessible
    STATUS     current
    DESCRIPTION
    "
    Name      : Deemphasis
    Menu Path : /Audio/Audio 1
    Details   : Dolby Digital: applies deemphasis, Mpeg: indicates presence of preemphasis. Auto uses AES channel block indication.
    "
::= { enc1Params 167 }

enc1P167deemphasisEntry OBJECT-TYPE
    SYNTAX Enc1P167deemphasisEntry
    MAX-ACCESS not-accessible
    STATUS     current
    DESCRIPTION
    "Table Entry for Deemphasis"
    INDEX { slotId }
::= { enc1P167deemphasisTable 1 }

Enc1P167deemphasisEntry ::= SEQUENCE {
    enc1P167deemphasisValue    Enc1E2enumObj
}

enc1P167deemphasisValue OBJECT-TYPE
    SYNTAX     Enc1E2enumObj
    MAX-ACCESS read-write
    STATUS     current
    DESCRIPTION
    "Dolby Digital: applies deemphasis, Mpeg: indicates presence of preemphasis. Auto uses AES channel block indication."
::= { enc1P167deemphasisEntry 1 }

enc1P168modeTable OBJECT-TYPE
    SYNTAX SEQUENCE OF Enc1P168modeEntry
    MAX-ACCESS not-accessible
    STATUS     current
    DESCRIPTION
    "
    Name      : Mode
    Menu Path : /Audio/Audio 1
    Details   : Specifies the audio coding mode (maximum channel usage)
    "
::= { enc1Params 168 }

enc1P168modeEntry OBJECT-TYPE
    SYNTAX Enc1P168modeEntry
    MAX-ACCESS not-accessible
    STATUS     current
    DESCRIPTION
    "Table Entry for Mode"
    INDEX { slotId }
::= { enc1P168modeTable 1 }

Enc1P168modeEntry ::= SEQUENCE {
    enc1P168modeValue    Enc1E179enumObj
}

enc1P168modeValue OBJECT-TYPE
    SYNTAX     Enc1E179enumObj
    MAX-ACCESS read-write
    STATUS     current
    DESCRIPTION
    "Specifies the audio coding mode (maximum channel usage)"
::= { enc1P168modeEntry 1 }

enc1P169audioFormatTable OBJECT-TYPE
    SYNTAX SEQUENCE OF Enc1P169audioFormatEntry
    MAX-ACCESS not-accessible
    STATUS     current
    DESCRIPTION
    "
    Name      : Audio Format
    Menu Path : /Audio/Audio 1
    Details   : Specifies the audio encoding standard and bitrate.
    "
::= { enc1Params 169 }

enc1P169audioFormatEntry OBJECT-TYPE
    SYNTAX Enc1P169audioFormatEntry
    MAX-ACCESS not-accessible
    STATUS     current
    DESCRIPTION
    "Table Entry for Audio Format"
    INDEX { slotId }
::= { enc1P169audioFormatTable 1 }

Enc1P169audioFormatEntry ::= SEQUENCE {
    enc1P169audioFormatValue    Enc1E73enumObj
}

enc1P169audioFormatValue OBJECT-TYPE
    SYNTAX     Enc1E73enumObj
    MAX-ACCESS read-write
    STATUS     current
    DESCRIPTION
    "Specifies the audio encoding standard and bitrate."
::= { enc1P169audioFormatEntry 1 }

enc1P170languageCodeTable OBJECT-TYPE
    SYNTAX SEQUENCE OF Enc1P170languageCodeEntry
    MAX-ACCESS not-accessible
    STATUS     current
    DESCRIPTION
    "
    Name      : Language Code
    Menu Path : /Audio/Audio 1
    Details   : Specifies the ISO 639-2 (three letter) language code.
    "
::= { enc1Params 170 }

enc1P170languageCodeEntry OBJECT-TYPE
    SYNTAX Enc1P170languageCodeEntry
    MAX-ACCESS not-accessible
    STATUS     current
    DESCRIPTION
    "Table Entry for Language Code"
    INDEX { slotId }
::= { enc1P170languageCodeTable 1 }

Enc1P170languageCodeEntry ::= SEQUENCE {
    enc1P170languageCodeValue    DisplayString
}

enc1P170languageCodeValue OBJECT-TYPE
    SYNTAX     DisplayString
    MAX-ACCESS read-write
    STATUS     current
    DESCRIPTION
    "Specifies the ISO 639-2 (three letter) language code."
::= { enc1P170languageCodeEntry 1 }

enc1P171enableOutputTable OBJECT-TYPE
    SYNTAX SEQUENCE OF Enc1P171enableOutputEntry
    MAX-ACCESS not-accessible
    STATUS     current
    DESCRIPTION
    "
    Name      : Enable Output
    Menu Path : /Audio/Audio 1
    Details   : Specifies which encoded program carries this audio.
    "
::= { enc1Params 171 }

enc1P171enableOutputEntry OBJECT-TYPE
    SYNTAX Enc1P171enableOutputEntry
    MAX-ACCESS not-accessible
    STATUS     current
    DESCRIPTION
    "Table Entry for Enable Output"
    INDEX { slotId }
::= { enc1P171enableOutputTable 1 }

Enc1P171enableOutputEntry ::= SEQUENCE {
    enc1P171enableOutputValue    Enc1E81enumObj
}

enc1P171enableOutputValue OBJECT-TYPE
    SYNTAX     Enc1E81enumObj
    MAX-ACCESS read-write
    STATUS     current
    DESCRIPTION
    "Specifies which encoded program carries this audio."
::= { enc1P171enableOutputEntry 1 }

enc1P172metadataSourceTable OBJECT-TYPE
    SYNTAX SEQUENCE OF Enc1P172metadataSourceEntry
    MAX-ACCESS not-accessible
    STATUS     current
    DESCRIPTION
    "
    Name      : Metadata Source
    Menu Path : /Audio/Audio 1/Metadata
    Details   : Specifies source for Dolby audio metadata
    "
::= { enc1Params 172 }

enc1P172metadataSourceEntry OBJECT-TYPE
    SYNTAX Enc1P172metadataSourceEntry
    MAX-ACCESS not-accessible
    STATUS     current
    DESCRIPTION
    "Table Entry for Metadata Source"
    INDEX { slotId }
::= { enc1P172metadataSourceTable 1 }

Enc1P172metadataSourceEntry ::= SEQUENCE {
    enc1P172metadataSourceValue    Enc1E83enumObj
}

enc1P172metadataSourceValue OBJECT-TYPE
    SYNTAX     Enc1E83enumObj
    MAX-ACCESS read-write
    STATUS     current
    DESCRIPTION
    "Specifies source for Dolby audio metadata"
::= { enc1P172metadataSourceEntry 1 }

enc1P173metadataReversionModeTable OBJECT-TYPE
    SYNTAX SEQUENCE OF Enc1P173metadataReversionModeEntry
    MAX-ACCESS not-accessible
    STATUS     current
    DESCRIPTION
    "
    Name      : Metadata Reversion Mode
    Menu Path : /Audio/Audio 1/Metadata
    Details   : Specifies response to interruption in metadata source
    "
::= { enc1Params 173 }

enc1P173metadataReversionModeEntry OBJECT-TYPE
    SYNTAX Enc1P173metadataReversionModeEntry
    MAX-ACCESS not-accessible
    STATUS     current
    DESCRIPTION
    "Table Entry for Metadata Reversion Mode"
    INDEX { slotId }
::= { enc1P173metadataReversionModeTable 1 }

Enc1P173metadataReversionModeEntry ::= SEQUENCE {
    enc1P173metadataReversionModeValue    Enc1E84enumObj
}

enc1P173metadataReversionModeValue OBJECT-TYPE
    SYNTAX     Enc1E84enumObj
    MAX-ACCESS read-write
    STATUS     current
    DESCRIPTION
    "Specifies response to interruption in metadata source"
::= { enc1P173metadataReversionModeEntry 1 }

enc1P174pssignalingTable OBJECT-TYPE
    SYNTAX SEQUENCE OF Enc1P174pssignalingEntry
    MAX-ACCESS not-accessible
    STATUS     current
    DESCRIPTION
    "
    Name      : PS Signaling
    Menu Path : /Audio/Audio 1/AAC
    Details   : Specifies the parametric stereo signaling for AAC audio encoding.
    "
::= { enc1Params 174 }

enc1P174pssignalingEntry OBJECT-TYPE
    SYNTAX Enc1P174pssignalingEntry
    MAX-ACCESS not-accessible
    STATUS     current
    DESCRIPTION
    "Table Entry for PS Signaling"
    INDEX { slotId }
::= { enc1P174pssignalingTable 1 }

Enc1P174pssignalingEntry ::= SEQUENCE {
    enc1P174pssignalingValue    Enc1E76enumObj
}

enc1P174pssignalingValue OBJECT-TYPE
    SYNTAX     Enc1E76enumObj
    MAX-ACCESS read-write
    STATUS     current
    DESCRIPTION
    "Specifies the parametric stereo signaling for AAC audio encoding."
::= { enc1P174pssignalingEntry 1 }

enc1P175sbrsignalingTable OBJECT-TYPE
    SYNTAX SEQUENCE OF Enc1P175sbrsignalingEntry
    MAX-ACCESS not-accessible
    STATUS     current
    DESCRIPTION
    "
    Name      : SBR Signaling
    Menu Path : /Audio/Audio 1/AAC
    Details   : Specifies the SBR signaling for AAC audio encoding.
    "
::= { enc1Params 175 }

enc1P175sbrsignalingEntry OBJECT-TYPE
    SYNTAX Enc1P175sbrsignalingEntry
    MAX-ACCESS not-accessible
    STATUS     current
    DESCRIPTION
    "Table Entry for SBR Signaling"
    INDEX { slotId }
::= { enc1P175sbrsignalingTable 1 }

Enc1P175sbrsignalingEntry ::= SEQUENCE {
    enc1P175sbrsignalingValue    Enc1E77enumObj
}

enc1P175sbrsignalingValue OBJECT-TYPE
    SYNTAX     Enc1E77enumObj
    MAX-ACCESS read-write
    STATUS     current
    DESCRIPTION
    "Specifies the SBR signaling for AAC audio encoding."
::= { enc1P175sbrsignalingEntry 1 }

enc1P176transportTable OBJECT-TYPE
    SYNTAX SEQUENCE OF Enc1P176transportEntry
    MAX-ACCESS not-accessible
    STATUS     current
    DESCRIPTION
    "
    Name      : Transport
    Menu Path : /Audio/Audio 1/AAC
    Details   : Specifies the transport layer (framing) for AAC audio encoding.
    "
::= { enc1Params 176 }

enc1P176transportEntry OBJECT-TYPE
    SYNTAX Enc1P176transportEntry
    MAX-ACCESS not-accessible
    STATUS     current
    DESCRIPTION
    "Table Entry for Transport"
    INDEX { slotId }
::= { enc1P176transportTable 1 }

Enc1P176transportEntry ::= SEQUENCE {
    enc1P176transportValue    Enc1E78enumObj
}

enc1P176transportValue OBJECT-TYPE
    SYNTAX     Enc1E78enumObj
    MAX-ACCESS read-write
    STATUS     current
    DESCRIPTION
    "Specifies the transport layer (framing) for AAC audio encoding."
::= { enc1P176transportEntry 1 }

enc1P178programConfigurationTable OBJECT-TYPE
    SYNTAX SEQUENCE OF Enc1P178programConfigurationEntry
    MAX-ACCESS not-accessible
    STATUS     current
    DESCRIPTION
    "
    Name      : Program Configuration
    Menu Path : /Audio/Audio 1/Dolby E Encoder
    Details   : Determines how audio channels are grouped into programs within a Dolby E bitstream.
    "
::= { enc1Params 178 }

enc1P178programConfigurationEntry OBJECT-TYPE
    SYNTAX Enc1P178programConfigurationEntry
    MAX-ACCESS not-accessible
    STATUS     current
    DESCRIPTION
    "Table Entry for Program Configuration"
    INDEX { slotId }
::= { enc1P178programConfigurationTable 1 }

Enc1P178programConfigurationEntry ::= SEQUENCE {
    enc1P178programConfigurationValue    Enc1E180enumObj
}

enc1P178programConfigurationValue OBJECT-TYPE
    SYNTAX     Enc1E180enumObj
    MAX-ACCESS read-write
    STATUS     current
    DESCRIPTION
    "Determines how audio channels are grouped into programs within a Dolby E bitstream."
::= { enc1P178programConfigurationEntry 1 }

enc1P208avsyncAdjustCountTable OBJECT-TYPE
    SYNTAX SEQUENCE OF Enc1P208avsyncAdjustCountEntry
    MAX-ACCESS not-accessible
    STATUS     current
    DESCRIPTION
    "
    Name      : AV Sync Adjust Count
    Menu Path : /Audio/Audio 1/Status
    Units     : 
    Precision : 0
    Low Range : 0
    High Range: -1
    Details   : Displays the count of audio/video sync adjustments (lipsync discontinuities).

     NOTE: Precision/Units/Ranges represent the state of the
           parameter during the MIB generation, and does not
           neccessary reflect the current state of the parameter
    "
::= { enc1Params 208 }

enc1P208avsyncAdjustCountEntry OBJECT-TYPE
    SYNTAX Enc1P208avsyncAdjustCountEntry
    MAX-ACCESS not-accessible
    STATUS     current
    DESCRIPTION
    "Table Entry for AV Sync Adjust Count"
    INDEX { slotId }
::= { enc1P208avsyncAdjustCountTable 1 }

Enc1P208avsyncAdjustCountEntry ::= SEQUENCE {
    enc1P208avsyncAdjustCountValue    INTEGER
}

enc1P208avsyncAdjustCountValue OBJECT-TYPE
    SYNTAX     INTEGER
    MAX-ACCESS read-only
    STATUS     current
    DESCRIPTION
    "Displays the count of audio/video sync adjustments (lipsync discontinuities)."
::= { enc1P208avsyncAdjustCountEntry 1 }

enc1P209pmtpositionTable OBJECT-TYPE
    SYNTAX SEQUENCE OF Enc1P209pmtpositionEntry
    MAX-ACCESS not-accessible
    STATUS     current
    DESCRIPTION
    "
    Name      : PMT Position
    Menu Path : /Audio/Audio 1/Status
    Units     : 
    Precision : 0
    Low Range : 0
    High Range: 8
    Details   : Displays the relative position in the PMT of this audio stream

     NOTE: Precision/Units/Ranges represent the state of the
           parameter during the MIB generation, and does not
           neccessary reflect the current state of the parameter
    "
::= { enc1Params 209 }

enc1P209pmtpositionEntry OBJECT-TYPE
    SYNTAX Enc1P209pmtpositionEntry
    MAX-ACCESS not-accessible
    STATUS     current
    DESCRIPTION
    "Table Entry for PMT Position"
    INDEX { slotId }
::= { enc1P209pmtpositionTable 1 }

Enc1P209pmtpositionEntry ::= SEQUENCE {
    enc1P209pmtpositionValue    INTEGER
}

enc1P209pmtpositionValue OBJECT-TYPE
    SYNTAX     INTEGER
    MAX-ACCESS read-only
    STATUS     current
    DESCRIPTION
    "Displays the relative position in the PMT of this audio stream"
::= { enc1P209pmtpositionEntry 1 }

enc1P211lossofSignalTable OBJECT-TYPE
    SYNTAX SEQUENCE OF Enc1P211lossofSignalEntry
    MAX-ACCESS not-accessible
    STATUS     current
    DESCRIPTION
    "
    Name      : Loss of Signal
    Menu Path : /Audio/Audio 1/Status
    Details   : Indicates loss of a selected source signal.
    "
::= { enc1Params 211 }

enc1P211lossofSignalEntry OBJECT-TYPE
    SYNTAX Enc1P211lossofSignalEntry
    MAX-ACCESS not-accessible
    STATUS     current
    DESCRIPTION
    "Table Entry for Loss of Signal"
    INDEX { slotId }
::= { enc1P211lossofSignalTable 1 }

Enc1P211lossofSignalEntry ::= SEQUENCE {
    enc1P211lossofSignalValue    Enc1E5enumObj
}

enc1P211lossofSignalValue OBJECT-TYPE
    SYNTAX     Enc1E5enumObj
    MAX-ACCESS read-only
    STATUS     current
    DESCRIPTION
    "Indicates loss of a selected source signal."
::= { enc1P211lossofSignalEntry 1 }

enc1P212source1Table OBJECT-TYPE
    SYNTAX SEQUENCE OF Enc1P212source1Entry
    MAX-ACCESS not-accessible
    STATUS     current
    DESCRIPTION
    "
    Name      : Source 1
    Menu Path : /Audio/Audio 2
    Details   : Specifies audio source (pair) for this codec.
    "
::= { enc1Params 212 }

enc1P212source1Entry OBJECT-TYPE
    SYNTAX Enc1P212source1Entry
    MAX-ACCESS not-accessible
    STATUS     current
    DESCRIPTION
    "Table Entry for Source 1"
    INDEX { slotId }
::= { enc1P212source1Table 1 }

Enc1P212source1Entry ::= SEQUENCE {
    enc1P212source1Value    Enc1E70enumObj
}

enc1P212source1Value OBJECT-TYPE
    SYNTAX     Enc1E70enumObj
    MAX-ACCESS read-write
    STATUS     current
    DESCRIPTION
    "Specifies audio source (pair) for this codec."
::= { enc1P212source1Entry 1 }

enc1P213source2Table OBJECT-TYPE
    SYNTAX SEQUENCE OF Enc1P213source2Entry
    MAX-ACCESS not-accessible
    STATUS     current
    DESCRIPTION
    "
    Name      : Source 2
    Menu Path : /Audio/Audio 2
    Details   : Specifies second audio source (pair) for this multichannel codec.
    "
::= { enc1Params 213 }

enc1P213source2Entry OBJECT-TYPE
    SYNTAX Enc1P213source2Entry
    MAX-ACCESS not-accessible
    STATUS     current
    DESCRIPTION
    "Table Entry for Source 2"
    INDEX { slotId }
::= { enc1P213source2Table 1 }

Enc1P213source2Entry ::= SEQUENCE {
    enc1P213source2Value    Enc1E70enumObj
}

enc1P213source2Value OBJECT-TYPE
    SYNTAX     Enc1E70enumObj
    MAX-ACCESS read-write
    STATUS     current
    DESCRIPTION
    "Specifies second audio source (pair) for this multichannel codec."
::= { enc1P213source2Entry 1 }

enc1P214source3Table OBJECT-TYPE
    SYNTAX SEQUENCE OF Enc1P214source3Entry
    MAX-ACCESS not-accessible
    STATUS     current
    DESCRIPTION
    "
    Name      : Source 3
    Menu Path : /Audio/Audio 2
    Details   : Specifies third audio source (pair) for this multichannel codec.
    "
::= { enc1Params 214 }

enc1P214source3Entry OBJECT-TYPE
    SYNTAX Enc1P214source3Entry
    MAX-ACCESS not-accessible
    STATUS     current
    DESCRIPTION
    "Table Entry for Source 3"
    INDEX { slotId }
::= { enc1P214source3Table 1 }

Enc1P214source3Entry ::= SEQUENCE {
    enc1P214source3Value    Enc1E70enumObj
}

enc1P214source3Value OBJECT-TYPE
    SYNTAX     Enc1E70enumObj
    MAX-ACCESS read-write
    STATUS     current
    DESCRIPTION
    "Specifies third audio source (pair) for this multichannel codec."
::= { enc1P214source3Entry 1 }

enc1P215source4Table OBJECT-TYPE
    SYNTAX SEQUENCE OF Enc1P215source4Entry
    MAX-ACCESS not-accessible
    STATUS     current
    DESCRIPTION
    "
    Name      : Source 4
    Menu Path : /Audio/Audio 2
    Details   : Specifies fourth audio source (pair) for this multichannel codec.
    "
::= { enc1Params 215 }

enc1P215source4Entry OBJECT-TYPE
    SYNTAX Enc1P215source4Entry
    MAX-ACCESS not-accessible
    STATUS     current
    DESCRIPTION
    "Table Entry for Source 4"
    INDEX { slotId }
::= { enc1P215source4Table 1 }

Enc1P215source4Entry ::= SEQUENCE {
    enc1P215source4Value    Enc1E70enumObj
}

enc1P215source4Value OBJECT-TYPE
    SYNTAX     Enc1E70enumObj
    MAX-ACCESS read-write
    STATUS     current
    DESCRIPTION
    "Specifies fourth audio source (pair) for this multichannel codec."
::= { enc1P215source4Entry 1 }

enc1P216preProcessingTable OBJECT-TYPE
    SYNTAX SEQUENCE OF Enc1P216preProcessingEntry
    MAX-ACCESS not-accessible
    STATUS     current
    DESCRIPTION
    "
    Name      : Pre Processing
    Menu Path : Not Applicable
    Details   : Specifies special processing for audio channel
    "
::= { enc1Params 216 }

enc1P216preProcessingEntry OBJECT-TYPE
    SYNTAX Enc1P216preProcessingEntry
    MAX-ACCESS not-accessible
    STATUS     current
    DESCRIPTION
    "Table Entry for Pre Processing"
    INDEX { slotId }
::= { enc1P216preProcessingTable 1 }

Enc1P216preProcessingEntry ::= SEQUENCE {
    enc1P216preProcessingValue    Enc1E72enumObj
}

enc1P216preProcessingValue OBJECT-TYPE
    SYNTAX     Enc1E72enumObj
    MAX-ACCESS read-write
    STATUS     current
    DESCRIPTION
    "Specifies special processing for audio channel"
::= { enc1P216preProcessingEntry 1 }

enc1P217delayTable OBJECT-TYPE
    SYNTAX SEQUENCE OF Enc1P217delayEntry
    MAX-ACCESS not-accessible
    STATUS     current
    DESCRIPTION
    "
    Name      : Delay
    Menu Path : /Audio/Audio 2
    Units     : msec
    Precision : 0
    Low Range : -500
    High Range: 500
    Details   : Specify an additional audio delay, relative to video delay.

     NOTE: Precision/Units/Ranges represent the state of the
           parameter during the MIB generation, and does not
           neccessary reflect the current state of the parameter
    "
::= { enc1Params 217 }

enc1P217delayEntry OBJECT-TYPE
    SYNTAX Enc1P217delayEntry
    MAX-ACCESS not-accessible
    STATUS     current
    DESCRIPTION
    "Table Entry for Delay"
    INDEX { slotId }
::= { enc1P217delayTable 1 }

Enc1P217delayEntry ::= SEQUENCE {
    enc1P217delayValue    INTEGER
}

enc1P217delayValue OBJECT-TYPE
    SYNTAX     INTEGER
    MAX-ACCESS read-write
    STATUS     current
    DESCRIPTION
    "Specify an additional audio delay, relative to video delay."
::= { enc1P217delayEntry 1 }

enc1P218gainTable OBJECT-TYPE
    SYNTAX SEQUENCE OF Enc1P218gainEntry
    MAX-ACCESS not-accessible
    STATUS     current
    DESCRIPTION
    "
    Name      : Gain
    Menu Path : /Audio/Audio 2
    Units     : dB
    Precision : 1
    Low Range : -800
    High Range: 400
    Details   : Apply a gain (or attenuation) to all source channels.

     NOTE: Precision/Units/Ranges represent the state of the
           parameter during the MIB generation, and does not
           neccessary reflect the current state of the parameter
    "
::= { enc1Params 218 }

enc1P218gainEntry OBJECT-TYPE
    SYNTAX Enc1P218gainEntry
    MAX-ACCESS not-accessible
    STATUS     current
    DESCRIPTION
    "Table Entry for Gain"
    INDEX { slotId }
::= { enc1P218gainTable 1 }

Enc1P218gainEntry ::= SEQUENCE {
    enc1P218gainValue    INTEGER
}

enc1P218gainValue OBJECT-TYPE
    SYNTAX     INTEGER
    MAX-ACCESS read-write
    STATUS     current
    DESCRIPTION
    "Apply a gain (or attenuation) to all source channels."
::= { enc1P218gainEntry 1 }

enc1P220deemphasisTable OBJECT-TYPE
    SYNTAX SEQUENCE OF Enc1P220deemphasisEntry
    MAX-ACCESS not-accessible
    STATUS     current
    DESCRIPTION
    "
    Name      : Deemphasis
    Menu Path : /Audio/Audio 2
    Details   : Dolby Digital: applies deemphasis, Mpeg: indicates presence of preemphasis. Auto uses AES channel block indication.
    "
::= { enc1Params 220 }

enc1P220deemphasisEntry OBJECT-TYPE
    SYNTAX Enc1P220deemphasisEntry
    MAX-ACCESS not-accessible
    STATUS     current
    DESCRIPTION
    "Table Entry for Deemphasis"
    INDEX { slotId }
::= { enc1P220deemphasisTable 1 }

Enc1P220deemphasisEntry ::= SEQUENCE {
    enc1P220deemphasisValue    Enc1E2enumObj
}

enc1P220deemphasisValue OBJECT-TYPE
    SYNTAX     Enc1E2enumObj
    MAX-ACCESS read-write
    STATUS     current
    DESCRIPTION
    "Dolby Digital: applies deemphasis, Mpeg: indicates presence of preemphasis. Auto uses AES channel block indication."
::= { enc1P220deemphasisEntry 1 }

enc1P221modeTable OBJECT-TYPE
    SYNTAX SEQUENCE OF Enc1P221modeEntry
    MAX-ACCESS not-accessible
    STATUS     current
    DESCRIPTION
    "
    Name      : Mode
    Menu Path : /Audio/Audio 2
    Details   : Specifies the audio coding mode (maximum channel usage)
    "
::= { enc1Params 221 }

enc1P221modeEntry OBJECT-TYPE
    SYNTAX Enc1P221modeEntry
    MAX-ACCESS not-accessible
    STATUS     current
    DESCRIPTION
    "Table Entry for Mode"
    INDEX { slotId }
::= { enc1P221modeTable 1 }

Enc1P221modeEntry ::= SEQUENCE {
    enc1P221modeValue    Enc1E182enumObj
}

enc1P221modeValue OBJECT-TYPE
    SYNTAX     Enc1E182enumObj
    MAX-ACCESS read-write
    STATUS     current
    DESCRIPTION
    "Specifies the audio coding mode (maximum channel usage)"
::= { enc1P221modeEntry 1 }

enc1P222audioFormatTable OBJECT-TYPE
    SYNTAX SEQUENCE OF Enc1P222audioFormatEntry
    MAX-ACCESS not-accessible
    STATUS     current
    DESCRIPTION
    "
    Name      : Audio Format
    Menu Path : /Audio/Audio 2
    Details   : Specifies the audio encoding standard and bitrate.
    "
::= { enc1Params 222 }

enc1P222audioFormatEntry OBJECT-TYPE
    SYNTAX Enc1P222audioFormatEntry
    MAX-ACCESS not-accessible
    STATUS     current
    DESCRIPTION
    "Table Entry for Audio Format"
    INDEX { slotId }
::= { enc1P222audioFormatTable 1 }

Enc1P222audioFormatEntry ::= SEQUENCE {
    enc1P222audioFormatValue    Enc1E73enumObj
}

enc1P222audioFormatValue OBJECT-TYPE
    SYNTAX     Enc1E73enumObj
    MAX-ACCESS read-write
    STATUS     current
    DESCRIPTION
    "Specifies the audio encoding standard and bitrate."
::= { enc1P222audioFormatEntry 1 }

enc1P223languageCodeTable OBJECT-TYPE
    SYNTAX SEQUENCE OF Enc1P223languageCodeEntry
    MAX-ACCESS not-accessible
    STATUS     current
    DESCRIPTION
    "
    Name      : Language Code
    Menu Path : /Audio/Audio 2
    Details   : Specifies the ISO 639-2 (three letter) language code.
    "
::= { enc1Params 223 }

enc1P223languageCodeEntry OBJECT-TYPE
    SYNTAX Enc1P223languageCodeEntry
    MAX-ACCESS not-accessible
    STATUS     current
    DESCRIPTION
    "Table Entry for Language Code"
    INDEX { slotId }
::= { enc1P223languageCodeTable 1 }

Enc1P223languageCodeEntry ::= SEQUENCE {
    enc1P223languageCodeValue    DisplayString
}

enc1P223languageCodeValue OBJECT-TYPE
    SYNTAX     DisplayString
    MAX-ACCESS read-write
    STATUS     current
    DESCRIPTION
    "Specifies the ISO 639-2 (three letter) language code."
::= { enc1P223languageCodeEntry 1 }

enc1P224enableOutputTable OBJECT-TYPE
    SYNTAX SEQUENCE OF Enc1P224enableOutputEntry
    MAX-ACCESS not-accessible
    STATUS     current
    DESCRIPTION
    "
    Name      : Enable Output
    Menu Path : /Audio/Audio 2
    Details   : Specifies which encoded program carries this audio.
    "
::= { enc1Params 224 }

enc1P224enableOutputEntry OBJECT-TYPE
    SYNTAX Enc1P224enableOutputEntry
    MAX-ACCESS not-accessible
    STATUS     current
    DESCRIPTION
    "Table Entry for Enable Output"
    INDEX { slotId }
::= { enc1P224enableOutputTable 1 }

Enc1P224enableOutputEntry ::= SEQUENCE {
    enc1P224enableOutputValue    Enc1E81enumObj
}

enc1P224enableOutputValue OBJECT-TYPE
    SYNTAX     Enc1E81enumObj
    MAX-ACCESS read-write
    STATUS     current
    DESCRIPTION
    "Specifies which encoded program carries this audio."
::= { enc1P224enableOutputEntry 1 }

enc1P225metadataSourceTable OBJECT-TYPE
    SYNTAX SEQUENCE OF Enc1P225metadataSourceEntry
    MAX-ACCESS not-accessible
    STATUS     current
    DESCRIPTION
    "
    Name      : Metadata Source
    Menu Path : /Audio/Audio 2/Metadata
    Details   : Specifies source for Dolby audio metadata
    "
::= { enc1Params 225 }

enc1P225metadataSourceEntry OBJECT-TYPE
    SYNTAX Enc1P225metadataSourceEntry
    MAX-ACCESS not-accessible
    STATUS     current
    DESCRIPTION
    "Table Entry for Metadata Source"
    INDEX { slotId }
::= { enc1P225metadataSourceTable 1 }

Enc1P225metadataSourceEntry ::= SEQUENCE {
    enc1P225metadataSourceValue    Enc1E83enumObj
}

enc1P225metadataSourceValue OBJECT-TYPE
    SYNTAX     Enc1E83enumObj
    MAX-ACCESS read-write
    STATUS     current
    DESCRIPTION
    "Specifies source for Dolby audio metadata"
::= { enc1P225metadataSourceEntry 1 }

enc1P226metadataReversionModeTable OBJECT-TYPE
    SYNTAX SEQUENCE OF Enc1P226metadataReversionModeEntry
    MAX-ACCESS not-accessible
    STATUS     current
    DESCRIPTION
    "
    Name      : Metadata Reversion Mode
    Menu Path : /Audio/Audio 2/Metadata
    Details   : Specifies response to interruption in metadata source
    "
::= { enc1Params 226 }

enc1P226metadataReversionModeEntry OBJECT-TYPE
    SYNTAX Enc1P226metadataReversionModeEntry
    MAX-ACCESS not-accessible
    STATUS     current
    DESCRIPTION
    "Table Entry for Metadata Reversion Mode"
    INDEX { slotId }
::= { enc1P226metadataReversionModeTable 1 }

Enc1P226metadataReversionModeEntry ::= SEQUENCE {
    enc1P226metadataReversionModeValue    Enc1E84enumObj
}

enc1P226metadataReversionModeValue OBJECT-TYPE
    SYNTAX     Enc1E84enumObj
    MAX-ACCESS read-write
    STATUS     current
    DESCRIPTION
    "Specifies response to interruption in metadata source"
::= { enc1P226metadataReversionModeEntry 1 }

enc1P227pssignalingTable OBJECT-TYPE
    SYNTAX SEQUENCE OF Enc1P227pssignalingEntry
    MAX-ACCESS not-accessible
    STATUS     current
    DESCRIPTION
    "
    Name      : PS Signaling
    Menu Path : /Audio/Audio 2/AAC
    Details   : Specifies the parametric stereo signaling for AAC audio encoding.
    "
::= { enc1Params 227 }

enc1P227pssignalingEntry OBJECT-TYPE
    SYNTAX Enc1P227pssignalingEntry
    MAX-ACCESS not-accessible
    STATUS     current
    DESCRIPTION
    "Table Entry for PS Signaling"
    INDEX { slotId }
::= { enc1P227pssignalingTable 1 }

Enc1P227pssignalingEntry ::= SEQUENCE {
    enc1P227pssignalingValue    Enc1E76enumObj
}

enc1P227pssignalingValue OBJECT-TYPE
    SYNTAX     Enc1E76enumObj
    MAX-ACCESS read-write
    STATUS     current
    DESCRIPTION
    "Specifies the parametric stereo signaling for AAC audio encoding."
::= { enc1P227pssignalingEntry 1 }

enc1P228sbrsignalingTable OBJECT-TYPE
    SYNTAX SEQUENCE OF Enc1P228sbrsignalingEntry
    MAX-ACCESS not-accessible
    STATUS     current
    DESCRIPTION
    "
    Name      : SBR Signaling
    Menu Path : /Audio/Audio 2/AAC
    Details   : Specifies the SBR signaling for AAC audio encoding.
    "
::= { enc1Params 228 }

enc1P228sbrsignalingEntry OBJECT-TYPE
    SYNTAX Enc1P228sbrsignalingEntry
    MAX-ACCESS not-accessible
    STATUS     current
    DESCRIPTION
    "Table Entry for SBR Signaling"
    INDEX { slotId }
::= { enc1P228sbrsignalingTable 1 }

Enc1P228sbrsignalingEntry ::= SEQUENCE {
    enc1P228sbrsignalingValue    Enc1E77enumObj
}

enc1P228sbrsignalingValue OBJECT-TYPE
    SYNTAX     Enc1E77enumObj
    MAX-ACCESS read-write
    STATUS     current
    DESCRIPTION
    "Specifies the SBR signaling for AAC audio encoding."
::= { enc1P228sbrsignalingEntry 1 }

enc1P229transportTable OBJECT-TYPE
    SYNTAX SEQUENCE OF Enc1P229transportEntry
    MAX-ACCESS not-accessible
    STATUS     current
    DESCRIPTION
    "
    Name      : Transport
    Menu Path : /Audio/Audio 2/AAC
    Details   : Specifies the transport layer (framing) for AAC audio encoding.
    "
::= { enc1Params 229 }

enc1P229transportEntry OBJECT-TYPE
    SYNTAX Enc1P229transportEntry
    MAX-ACCESS not-accessible
    STATUS     current
    DESCRIPTION
    "Table Entry for Transport"
    INDEX { slotId }
::= { enc1P229transportTable 1 }

Enc1P229transportEntry ::= SEQUENCE {
    enc1P229transportValue    Enc1E78enumObj
}

enc1P229transportValue OBJECT-TYPE
    SYNTAX     Enc1E78enumObj
    MAX-ACCESS read-write
    STATUS     current
    DESCRIPTION
    "Specifies the transport layer (framing) for AAC audio encoding."
::= { enc1P229transportEntry 1 }

enc1P231programConfigurationTable OBJECT-TYPE
    SYNTAX SEQUENCE OF Enc1P231programConfigurationEntry
    MAX-ACCESS not-accessible
    STATUS     current
    DESCRIPTION
    "
    Name      : Program Configuration
    Menu Path : /Audio/Audio 2/Dolby E Encoder
    Details   : Determines how audio channels are grouped into programs within a Dolby E bitstream.
    "
::= { enc1Params 231 }

enc1P231programConfigurationEntry OBJECT-TYPE
    SYNTAX Enc1P231programConfigurationEntry
    MAX-ACCESS not-accessible
    STATUS     current
    DESCRIPTION
    "Table Entry for Program Configuration"
    INDEX { slotId }
::= { enc1P231programConfigurationTable 1 }

Enc1P231programConfigurationEntry ::= SEQUENCE {
    enc1P231programConfigurationValue    Enc1E183enumObj
}

enc1P231programConfigurationValue OBJECT-TYPE
    SYNTAX     Enc1E183enumObj
    MAX-ACCESS read-write
    STATUS     current
    DESCRIPTION
    "Determines how audio channels are grouped into programs within a Dolby E bitstream."
::= { enc1P231programConfigurationEntry 1 }

enc1P261avsyncAdjustCountTable OBJECT-TYPE
    SYNTAX SEQUENCE OF Enc1P261avsyncAdjustCountEntry
    MAX-ACCESS not-accessible
    STATUS     current
    DESCRIPTION
    "
    Name      : AV Sync Adjust Count
    Menu Path : /Audio/Audio 2/Status
    Units     : 
    Precision : 0
    Low Range : 0
    High Range: -1
    Details   : Displays the count of audio/video sync adjustments (lipsync discontinuities).

     NOTE: Precision/Units/Ranges represent the state of the
           parameter during the MIB generation, and does not
           neccessary reflect the current state of the parameter
    "
::= { enc1Params 261 }

enc1P261avsyncAdjustCountEntry OBJECT-TYPE
    SYNTAX Enc1P261avsyncAdjustCountEntry
    MAX-ACCESS not-accessible
    STATUS     current
    DESCRIPTION
    "Table Entry for AV Sync Adjust Count"
    INDEX { slotId }
::= { enc1P261avsyncAdjustCountTable 1 }

Enc1P261avsyncAdjustCountEntry ::= SEQUENCE {
    enc1P261avsyncAdjustCountValue    INTEGER
}

enc1P261avsyncAdjustCountValue OBJECT-TYPE
    SYNTAX     INTEGER
    MAX-ACCESS read-only
    STATUS     current
    DESCRIPTION
    "Displays the count of audio/video sync adjustments (lipsync discontinuities)."
::= { enc1P261avsyncAdjustCountEntry 1 }

enc1P262pmtpositionTable OBJECT-TYPE
    SYNTAX SEQUENCE OF Enc1P262pmtpositionEntry
    MAX-ACCESS not-accessible
    STATUS     current
    DESCRIPTION
    "
    Name      : PMT Position
    Menu Path : /Audio/Audio 2/Status
    Units     : 
    Precision : 0
    Low Range : 0
    High Range: 8
    Details   : Displays the relative position in the PMT of this audio stream

     NOTE: Precision/Units/Ranges represent the state of the
           parameter during the MIB generation, and does not
           neccessary reflect the current state of the parameter
    "
::= { enc1Params 262 }

enc1P262pmtpositionEntry OBJECT-TYPE
    SYNTAX Enc1P262pmtpositionEntry
    MAX-ACCESS not-accessible
    STATUS     current
    DESCRIPTION
    "Table Entry for PMT Position"
    INDEX { slotId }
::= { enc1P262pmtpositionTable 1 }

Enc1P262pmtpositionEntry ::= SEQUENCE {
    enc1P262pmtpositionValue    INTEGER
}

enc1P262pmtpositionValue OBJECT-TYPE
    SYNTAX     INTEGER
    MAX-ACCESS read-only
    STATUS     current
    DESCRIPTION
    "Displays the relative position in the PMT of this audio stream"
::= { enc1P262pmtpositionEntry 1 }

enc1P264lossofSignalTable OBJECT-TYPE
    SYNTAX SEQUENCE OF Enc1P264lossofSignalEntry
    MAX-ACCESS not-accessible
    STATUS     current
    DESCRIPTION
    "
    Name      : Loss of Signal
    Menu Path : /Audio/Audio 2/Status
    Details   : Indicates loss of a selected source signal.
    "
::= { enc1Params 264 }

enc1P264lossofSignalEntry OBJECT-TYPE
    SYNTAX Enc1P264lossofSignalEntry
    MAX-ACCESS not-accessible
    STATUS     current
    DESCRIPTION
    "Table Entry for Loss of Signal"
    INDEX { slotId }
::= { enc1P264lossofSignalTable 1 }

Enc1P264lossofSignalEntry ::= SEQUENCE {
    enc1P264lossofSignalValue    Enc1E5enumObj
}

enc1P264lossofSignalValue OBJECT-TYPE
    SYNTAX     Enc1E5enumObj
    MAX-ACCESS read-only
    STATUS     current
    DESCRIPTION
    "Indicates loss of a selected source signal."
::= { enc1P264lossofSignalEntry 1 }

enc1P265source1Table OBJECT-TYPE
    SYNTAX SEQUENCE OF Enc1P265source1Entry
    MAX-ACCESS not-accessible
    STATUS     current
    DESCRIPTION
    "
    Name      : Source 1
    Menu Path : /Audio/Audio 3
    Details   : Specifies audio source (pair) for this codec.
    "
::= { enc1Params 265 }

enc1P265source1Entry OBJECT-TYPE
    SYNTAX Enc1P265source1Entry
    MAX-ACCESS not-accessible
    STATUS     current
    DESCRIPTION
    "Table Entry for Source 1"
    INDEX { slotId }
::= { enc1P265source1Table 1 }

Enc1P265source1Entry ::= SEQUENCE {
    enc1P265source1Value    Enc1E70enumObj
}

enc1P265source1Value OBJECT-TYPE
    SYNTAX     Enc1E70enumObj
    MAX-ACCESS read-write
    STATUS     current
    DESCRIPTION
    "Specifies audio source (pair) for this codec."
::= { enc1P265source1Entry 1 }

enc1P266source2Table OBJECT-TYPE
    SYNTAX SEQUENCE OF Enc1P266source2Entry
    MAX-ACCESS not-accessible
    STATUS     current
    DESCRIPTION
    "
    Name      : Source 2
    Menu Path : /Audio/Audio 3
    Details   : Specifies second audio source (pair) for this multichannel codec.
    "
::= { enc1Params 266 }

enc1P266source2Entry OBJECT-TYPE
    SYNTAX Enc1P266source2Entry
    MAX-ACCESS not-accessible
    STATUS     current
    DESCRIPTION
    "Table Entry for Source 2"
    INDEX { slotId }
::= { enc1P266source2Table 1 }

Enc1P266source2Entry ::= SEQUENCE {
    enc1P266source2Value    Enc1E70enumObj
}

enc1P266source2Value OBJECT-TYPE
    SYNTAX     Enc1E70enumObj
    MAX-ACCESS read-write
    STATUS     current
    DESCRIPTION
    "Specifies second audio source (pair) for this multichannel codec."
::= { enc1P266source2Entry 1 }

enc1P267source3Table OBJECT-TYPE
    SYNTAX SEQUENCE OF Enc1P267source3Entry
    MAX-ACCESS not-accessible
    STATUS     current
    DESCRIPTION
    "
    Name      : Source 3
    Menu Path : /Audio/Audio 3
    Details   : Specifies third audio source (pair) for this multichannel codec.
    "
::= { enc1Params 267 }

enc1P267source3Entry OBJECT-TYPE
    SYNTAX Enc1P267source3Entry
    MAX-ACCESS not-accessible
    STATUS     current
    DESCRIPTION
    "Table Entry for Source 3"
    INDEX { slotId }
::= { enc1P267source3Table 1 }

Enc1P267source3Entry ::= SEQUENCE {
    enc1P267source3Value    Enc1E70enumObj
}

enc1P267source3Value OBJECT-TYPE
    SYNTAX     Enc1E70enumObj
    MAX-ACCESS read-write
    STATUS     current
    DESCRIPTION
    "Specifies third audio source (pair) for this multichannel codec."
::= { enc1P267source3Entry 1 }

enc1P268source4Table OBJECT-TYPE
    SYNTAX SEQUENCE OF Enc1P268source4Entry
    MAX-ACCESS not-accessible
    STATUS     current
    DESCRIPTION
    "
    Name      : Source 4
    Menu Path : /Audio/Audio 3
    Details   : Specifies fourth audio source (pair) for this multichannel codec.
    "
::= { enc1Params 268 }

enc1P268source4Entry OBJECT-TYPE
    SYNTAX Enc1P268source4Entry
    MAX-ACCESS not-accessible
    STATUS     current
    DESCRIPTION
    "Table Entry for Source 4"
    INDEX { slotId }
::= { enc1P268source4Table 1 }

Enc1P268source4Entry ::= SEQUENCE {
    enc1P268source4Value    Enc1E70enumObj
}

enc1P268source4Value OBJECT-TYPE
    SYNTAX     Enc1E70enumObj
    MAX-ACCESS read-write
    STATUS     current
    DESCRIPTION
    "Specifies fourth audio source (pair) for this multichannel codec."
::= { enc1P268source4Entry 1 }

enc1P269preProcessingTable OBJECT-TYPE
    SYNTAX SEQUENCE OF Enc1P269preProcessingEntry
    MAX-ACCESS not-accessible
    STATUS     current
    DESCRIPTION
    "
    Name      : Pre Processing
    Menu Path : Not Applicable
    Details   : Specifies special processing for audio channel
    "
::= { enc1Params 269 }

enc1P269preProcessingEntry OBJECT-TYPE
    SYNTAX Enc1P269preProcessingEntry
    MAX-ACCESS not-accessible
    STATUS     current
    DESCRIPTION
    "Table Entry for Pre Processing"
    INDEX { slotId }
::= { enc1P269preProcessingTable 1 }

Enc1P269preProcessingEntry ::= SEQUENCE {
    enc1P269preProcessingValue    Enc1E72enumObj
}

enc1P269preProcessingValue OBJECT-TYPE
    SYNTAX     Enc1E72enumObj
    MAX-ACCESS read-write
    STATUS     current
    DESCRIPTION
    "Specifies special processing for audio channel"
::= { enc1P269preProcessingEntry 1 }

enc1P270delayTable OBJECT-TYPE
    SYNTAX SEQUENCE OF Enc1P270delayEntry
    MAX-ACCESS not-accessible
    STATUS     current
    DESCRIPTION
    "
    Name      : Delay
    Menu Path : /Audio/Audio 3
    Units     : msec
    Precision : 0
    Low Range : -500
    High Range: 500
    Details   : Specify an additional audio delay, relative to video delay.

     NOTE: Precision/Units/Ranges represent the state of the
           parameter during the MIB generation, and does not
           neccessary reflect the current state of the parameter
    "
::= { enc1Params 270 }

enc1P270delayEntry OBJECT-TYPE
    SYNTAX Enc1P270delayEntry
    MAX-ACCESS not-accessible
    STATUS     current
    DESCRIPTION
    "Table Entry for Delay"
    INDEX { slotId }
::= { enc1P270delayTable 1 }

Enc1P270delayEntry ::= SEQUENCE {
    enc1P270delayValue    INTEGER
}

enc1P270delayValue OBJECT-TYPE
    SYNTAX     INTEGER
    MAX-ACCESS read-write
    STATUS     current
    DESCRIPTION
    "Specify an additional audio delay, relative to video delay."
::= { enc1P270delayEntry 1 }

enc1P271gainTable OBJECT-TYPE
    SYNTAX SEQUENCE OF Enc1P271gainEntry
    MAX-ACCESS not-accessible
    STATUS     current
    DESCRIPTION
    "
    Name      : Gain
    Menu Path : /Audio/Audio 3
    Units     : dB
    Precision : 1
    Low Range : -800
    High Range: 400
    Details   : Apply a gain (or attenuation) to all source channels.

     NOTE: Precision/Units/Ranges represent the state of the
           parameter during the MIB generation, and does not
           neccessary reflect the current state of the parameter
    "
::= { enc1Params 271 }

enc1P271gainEntry OBJECT-TYPE
    SYNTAX Enc1P271gainEntry
    MAX-ACCESS not-accessible
    STATUS     current
    DESCRIPTION
    "Table Entry for Gain"
    INDEX { slotId }
::= { enc1P271gainTable 1 }

Enc1P271gainEntry ::= SEQUENCE {
    enc1P271gainValue    INTEGER
}

enc1P271gainValue OBJECT-TYPE
    SYNTAX     INTEGER
    MAX-ACCESS read-write
    STATUS     current
    DESCRIPTION
    "Apply a gain (or attenuation) to all source channels."
::= { enc1P271gainEntry 1 }

enc1P273deemphasisTable OBJECT-TYPE
    SYNTAX SEQUENCE OF Enc1P273deemphasisEntry
    MAX-ACCESS not-accessible
    STATUS     current
    DESCRIPTION
    "
    Name      : Deemphasis
    Menu Path : /Audio/Audio 3
    Details   : Dolby Digital: applies deemphasis, Mpeg: indicates presence of preemphasis. Auto uses AES channel block indication.
    "
::= { enc1Params 273 }

enc1P273deemphasisEntry OBJECT-TYPE
    SYNTAX Enc1P273deemphasisEntry
    MAX-ACCESS not-accessible
    STATUS     current
    DESCRIPTION
    "Table Entry for Deemphasis"
    INDEX { slotId }
::= { enc1P273deemphasisTable 1 }

Enc1P273deemphasisEntry ::= SEQUENCE {
    enc1P273deemphasisValue    Enc1E2enumObj
}

enc1P273deemphasisValue OBJECT-TYPE
    SYNTAX     Enc1E2enumObj
    MAX-ACCESS read-write
    STATUS     current
    DESCRIPTION
    "Dolby Digital: applies deemphasis, Mpeg: indicates presence of preemphasis. Auto uses AES channel block indication."
::= { enc1P273deemphasisEntry 1 }

enc1P274modeTable OBJECT-TYPE
    SYNTAX SEQUENCE OF Enc1P274modeEntry
    MAX-ACCESS not-accessible
    STATUS     current
    DESCRIPTION
    "
    Name      : Mode
    Menu Path : /Audio/Audio 3
    Details   : Specifies the audio coding mode (maximum channel usage)
    "
::= { enc1Params 274 }

enc1P274modeEntry OBJECT-TYPE
    SYNTAX Enc1P274modeEntry
    MAX-ACCESS not-accessible
    STATUS     current
    DESCRIPTION
    "Table Entry for Mode"
    INDEX { slotId }
::= { enc1P274modeTable 1 }

Enc1P274modeEntry ::= SEQUENCE {
    enc1P274modeValue    Enc1E185enumObj
}

enc1P274modeValue OBJECT-TYPE
    SYNTAX     Enc1E185enumObj
    MAX-ACCESS read-write
    STATUS     current
    DESCRIPTION
    "Specifies the audio coding mode (maximum channel usage)"
::= { enc1P274modeEntry 1 }

enc1P275audioFormatTable OBJECT-TYPE
    SYNTAX SEQUENCE OF Enc1P275audioFormatEntry
    MAX-ACCESS not-accessible
    STATUS     current
    DESCRIPTION
    "
    Name      : Audio Format
    Menu Path : /Audio/Audio 3
    Details   : Specifies the audio encoding standard and bitrate.
    "
::= { enc1Params 275 }

enc1P275audioFormatEntry OBJECT-TYPE
    SYNTAX Enc1P275audioFormatEntry
    MAX-ACCESS not-accessible
    STATUS     current
    DESCRIPTION
    "Table Entry for Audio Format"
    INDEX { slotId }
::= { enc1P275audioFormatTable 1 }

Enc1P275audioFormatEntry ::= SEQUENCE {
    enc1P275audioFormatValue    Enc1E73enumObj
}

enc1P275audioFormatValue OBJECT-TYPE
    SYNTAX     Enc1E73enumObj
    MAX-ACCESS read-write
    STATUS     current
    DESCRIPTION
    "Specifies the audio encoding standard and bitrate."
::= { enc1P275audioFormatEntry 1 }

enc1P276languageCodeTable OBJECT-TYPE
    SYNTAX SEQUENCE OF Enc1P276languageCodeEntry
    MAX-ACCESS not-accessible
    STATUS     current
    DESCRIPTION
    "
    Name      : Language Code
    Menu Path : /Audio/Audio 3
    Details   : Specifies the ISO 639-2 (three letter) language code.
    "
::= { enc1Params 276 }

enc1P276languageCodeEntry OBJECT-TYPE
    SYNTAX Enc1P276languageCodeEntry
    MAX-ACCESS not-accessible
    STATUS     current
    DESCRIPTION
    "Table Entry for Language Code"
    INDEX { slotId }
::= { enc1P276languageCodeTable 1 }

Enc1P276languageCodeEntry ::= SEQUENCE {
    enc1P276languageCodeValue    DisplayString
}

enc1P276languageCodeValue OBJECT-TYPE
    SYNTAX     DisplayString
    MAX-ACCESS read-write
    STATUS     current
    DESCRIPTION
    "Specifies the ISO 639-2 (three letter) language code."
::= { enc1P276languageCodeEntry 1 }

enc1P277enableOutputTable OBJECT-TYPE
    SYNTAX SEQUENCE OF Enc1P277enableOutputEntry
    MAX-ACCESS not-accessible
    STATUS     current
    DESCRIPTION
    "
    Name      : Enable Output
    Menu Path : /Audio/Audio 3
    Details   : Specifies which encoded program carries this audio.
    "
::= { enc1Params 277 }

enc1P277enableOutputEntry OBJECT-TYPE
    SYNTAX Enc1P277enableOutputEntry
    MAX-ACCESS not-accessible
    STATUS     current
    DESCRIPTION
    "Table Entry for Enable Output"
    INDEX { slotId }
::= { enc1P277enableOutputTable 1 }

Enc1P277enableOutputEntry ::= SEQUENCE {
    enc1P277enableOutputValue    Enc1E81enumObj
}

enc1P277enableOutputValue OBJECT-TYPE
    SYNTAX     Enc1E81enumObj
    MAX-ACCESS read-write
    STATUS     current
    DESCRIPTION
    "Specifies which encoded program carries this audio."
::= { enc1P277enableOutputEntry 1 }

enc1P278metadataSourceTable OBJECT-TYPE
    SYNTAX SEQUENCE OF Enc1P278metadataSourceEntry
    MAX-ACCESS not-accessible
    STATUS     current
    DESCRIPTION
    "
    Name      : Metadata Source
    Menu Path : /Audio/Audio 3/Metadata
    Details   : Specifies source for Dolby audio metadata
    "
::= { enc1Params 278 }

enc1P278metadataSourceEntry OBJECT-TYPE
    SYNTAX Enc1P278metadataSourceEntry
    MAX-ACCESS not-accessible
    STATUS     current
    DESCRIPTION
    "Table Entry for Metadata Source"
    INDEX { slotId }
::= { enc1P278metadataSourceTable 1 }

Enc1P278metadataSourceEntry ::= SEQUENCE {
    enc1P278metadataSourceValue    Enc1E83enumObj
}

enc1P278metadataSourceValue OBJECT-TYPE
    SYNTAX     Enc1E83enumObj
    MAX-ACCESS read-write
    STATUS     current
    DESCRIPTION
    "Specifies source for Dolby audio metadata"
::= { enc1P278metadataSourceEntry 1 }

enc1P279metadataReversionModeTable OBJECT-TYPE
    SYNTAX SEQUENCE OF Enc1P279metadataReversionModeEntry
    MAX-ACCESS not-accessible
    STATUS     current
    DESCRIPTION
    "
    Name      : Metadata Reversion Mode
    Menu Path : /Audio/Audio 3/Metadata
    Details   : Specifies response to interruption in metadata source
    "
::= { enc1Params 279 }

enc1P279metadataReversionModeEntry OBJECT-TYPE
    SYNTAX Enc1P279metadataReversionModeEntry
    MAX-ACCESS not-accessible
    STATUS     current
    DESCRIPTION
    "Table Entry for Metadata Reversion Mode"
    INDEX { slotId }
::= { enc1P279metadataReversionModeTable 1 }

Enc1P279metadataReversionModeEntry ::= SEQUENCE {
    enc1P279metadataReversionModeValue    Enc1E84enumObj
}

enc1P279metadataReversionModeValue OBJECT-TYPE
    SYNTAX     Enc1E84enumObj
    MAX-ACCESS read-write
    STATUS     current
    DESCRIPTION
    "Specifies response to interruption in metadata source"
::= { enc1P279metadataReversionModeEntry 1 }

enc1P280pssignalingTable OBJECT-TYPE
    SYNTAX SEQUENCE OF Enc1P280pssignalingEntry
    MAX-ACCESS not-accessible
    STATUS     current
    DESCRIPTION
    "
    Name      : PS Signaling
    Menu Path : /Audio/Audio 3/AAC
    Details   : Specifies the parametric stereo signaling for AAC audio encoding.
    "
::= { enc1Params 280 }

enc1P280pssignalingEntry OBJECT-TYPE
    SYNTAX Enc1P280pssignalingEntry
    MAX-ACCESS not-accessible
    STATUS     current
    DESCRIPTION
    "Table Entry for PS Signaling"
    INDEX { slotId }
::= { enc1P280pssignalingTable 1 }

Enc1P280pssignalingEntry ::= SEQUENCE {
    enc1P280pssignalingValue    Enc1E76enumObj
}

enc1P280pssignalingValue OBJECT-TYPE
    SYNTAX     Enc1E76enumObj
    MAX-ACCESS read-write
    STATUS     current
    DESCRIPTION
    "Specifies the parametric stereo signaling for AAC audio encoding."
::= { enc1P280pssignalingEntry 1 }

enc1P281sbrsignalingTable OBJECT-TYPE
    SYNTAX SEQUENCE OF Enc1P281sbrsignalingEntry
    MAX-ACCESS not-accessible
    STATUS     current
    DESCRIPTION
    "
    Name      : SBR Signaling
    Menu Path : /Audio/Audio 3/AAC
    Details   : Specifies the SBR signaling for AAC audio encoding.
    "
::= { enc1Params 281 }

enc1P281sbrsignalingEntry OBJECT-TYPE
    SYNTAX Enc1P281sbrsignalingEntry
    MAX-ACCESS not-accessible
    STATUS     current
    DESCRIPTION
    "Table Entry for SBR Signaling"
    INDEX { slotId }
::= { enc1P281sbrsignalingTable 1 }

Enc1P281sbrsignalingEntry ::= SEQUENCE {
    enc1P281sbrsignalingValue    Enc1E77enumObj
}

enc1P281sbrsignalingValue OBJECT-TYPE
    SYNTAX     Enc1E77enumObj
    MAX-ACCESS read-write
    STATUS     current
    DESCRIPTION
    "Specifies the SBR signaling for AAC audio encoding."
::= { enc1P281sbrsignalingEntry 1 }

enc1P282transportTable OBJECT-TYPE
    SYNTAX SEQUENCE OF Enc1P282transportEntry
    MAX-ACCESS not-accessible
    STATUS     current
    DESCRIPTION
    "
    Name      : Transport
    Menu Path : /Audio/Audio 3/AAC
    Details   : Specifies the transport layer (framing) for AAC audio encoding.
    "
::= { enc1Params 282 }

enc1P282transportEntry OBJECT-TYPE
    SYNTAX Enc1P282transportEntry
    MAX-ACCESS not-accessible
    STATUS     current
    DESCRIPTION
    "Table Entry for Transport"
    INDEX { slotId }
::= { enc1P282transportTable 1 }

Enc1P282transportEntry ::= SEQUENCE {
    enc1P282transportValue    Enc1E78enumObj
}

enc1P282transportValue OBJECT-TYPE
    SYNTAX     Enc1E78enumObj
    MAX-ACCESS read-write
    STATUS     current
    DESCRIPTION
    "Specifies the transport layer (framing) for AAC audio encoding."
::= { enc1P282transportEntry 1 }

enc1P284programConfigurationTable OBJECT-TYPE
    SYNTAX SEQUENCE OF Enc1P284programConfigurationEntry
    MAX-ACCESS not-accessible
    STATUS     current
    DESCRIPTION
    "
    Name      : Program Configuration
    Menu Path : /Audio/Audio 3/Dolby E Encoder
    Details   : Determines how audio channels are grouped into programs within a Dolby E bitstream.
    "
::= { enc1Params 284 }

enc1P284programConfigurationEntry OBJECT-TYPE
    SYNTAX Enc1P284programConfigurationEntry
    MAX-ACCESS not-accessible
    STATUS     current
    DESCRIPTION
    "Table Entry for Program Configuration"
    INDEX { slotId }
::= { enc1P284programConfigurationTable 1 }

Enc1P284programConfigurationEntry ::= SEQUENCE {
    enc1P284programConfigurationValue    Enc1E186enumObj
}

enc1P284programConfigurationValue OBJECT-TYPE
    SYNTAX     Enc1E186enumObj
    MAX-ACCESS read-write
    STATUS     current
    DESCRIPTION
    "Determines how audio channels are grouped into programs within a Dolby E bitstream."
::= { enc1P284programConfigurationEntry 1 }

enc1P314avsyncAdjustCountTable OBJECT-TYPE
    SYNTAX SEQUENCE OF Enc1P314avsyncAdjustCountEntry
    MAX-ACCESS not-accessible
    STATUS     current
    DESCRIPTION
    "
    Name      : AV Sync Adjust Count
    Menu Path : /Audio/Audio 3/Status
    Units     : 
    Precision : 0
    Low Range : 0
    High Range: -1
    Details   : Displays the count of audio/video sync adjustments (lipsync discontinuities).

     NOTE: Precision/Units/Ranges represent the state of the
           parameter during the MIB generation, and does not
           neccessary reflect the current state of the parameter
    "
::= { enc1Params 314 }

enc1P314avsyncAdjustCountEntry OBJECT-TYPE
    SYNTAX Enc1P314avsyncAdjustCountEntry
    MAX-ACCESS not-accessible
    STATUS     current
    DESCRIPTION
    "Table Entry for AV Sync Adjust Count"
    INDEX { slotId }
::= { enc1P314avsyncAdjustCountTable 1 }

Enc1P314avsyncAdjustCountEntry ::= SEQUENCE {
    enc1P314avsyncAdjustCountValue    INTEGER
}

enc1P314avsyncAdjustCountValue OBJECT-TYPE
    SYNTAX     INTEGER
    MAX-ACCESS read-only
    STATUS     current
    DESCRIPTION
    "Displays the count of audio/video sync adjustments (lipsync discontinuities)."
::= { enc1P314avsyncAdjustCountEntry 1 }

enc1P315pmtpositionTable OBJECT-TYPE
    SYNTAX SEQUENCE OF Enc1P315pmtpositionEntry
    MAX-ACCESS not-accessible
    STATUS     current
    DESCRIPTION
    "
    Name      : PMT Position
    Menu Path : /Audio/Audio 3/Status
    Units     : 
    Precision : 0
    Low Range : 0
    High Range: 8
    Details   : Displays the relative position in the PMT of this audio stream

     NOTE: Precision/Units/Ranges represent the state of the
           parameter during the MIB generation, and does not
           neccessary reflect the current state of the parameter
    "
::= { enc1Params 315 }

enc1P315pmtpositionEntry OBJECT-TYPE
    SYNTAX Enc1P315pmtpositionEntry
    MAX-ACCESS not-accessible
    STATUS     current
    DESCRIPTION
    "Table Entry for PMT Position"
    INDEX { slotId }
::= { enc1P315pmtpositionTable 1 }

Enc1P315pmtpositionEntry ::= SEQUENCE {
    enc1P315pmtpositionValue    INTEGER
}

enc1P315pmtpositionValue OBJECT-TYPE
    SYNTAX     INTEGER
    MAX-ACCESS read-only
    STATUS     current
    DESCRIPTION
    "Displays the relative position in the PMT of this audio stream"
::= { enc1P315pmtpositionEntry 1 }

enc1P317lossofSignalTable OBJECT-TYPE
    SYNTAX SEQUENCE OF Enc1P317lossofSignalEntry
    MAX-ACCESS not-accessible
    STATUS     current
    DESCRIPTION
    "
    Name      : Loss of Signal
    Menu Path : /Audio/Audio 3/Status
    Details   : Indicates loss of a selected source signal.
    "
::= { enc1Params 317 }

enc1P317lossofSignalEntry OBJECT-TYPE
    SYNTAX Enc1P317lossofSignalEntry
    MAX-ACCESS not-accessible
    STATUS     current
    DESCRIPTION
    "Table Entry for Loss of Signal"
    INDEX { slotId }
::= { enc1P317lossofSignalTable 1 }

Enc1P317lossofSignalEntry ::= SEQUENCE {
    enc1P317lossofSignalValue    Enc1E5enumObj
}

enc1P317lossofSignalValue OBJECT-TYPE
    SYNTAX     Enc1E5enumObj
    MAX-ACCESS read-only
    STATUS     current
    DESCRIPTION
    "Indicates loss of a selected source signal."
::= { enc1P317lossofSignalEntry 1 }

enc1P318source1Table OBJECT-TYPE
    SYNTAX SEQUENCE OF Enc1P318source1Entry
    MAX-ACCESS not-accessible
    STATUS     current
    DESCRIPTION
    "
    Name      : Source 1
    Menu Path : /Audio/Audio 4
    Details   : Specifies audio source (pair) for this codec.
    "
::= { enc1Params 318 }

enc1P318source1Entry OBJECT-TYPE
    SYNTAX Enc1P318source1Entry
    MAX-ACCESS not-accessible
    STATUS     current
    DESCRIPTION
    "Table Entry for Source 1"
    INDEX { slotId }
::= { enc1P318source1Table 1 }

Enc1P318source1Entry ::= SEQUENCE {
    enc1P318source1Value    Enc1E70enumObj
}

enc1P318source1Value OBJECT-TYPE
    SYNTAX     Enc1E70enumObj
    MAX-ACCESS read-write
    STATUS     current
    DESCRIPTION
    "Specifies audio source (pair) for this codec."
::= { enc1P318source1Entry 1 }

enc1P319source2Table OBJECT-TYPE
    SYNTAX SEQUENCE OF Enc1P319source2Entry
    MAX-ACCESS not-accessible
    STATUS     current
    DESCRIPTION
    "
    Name      : Source 2
    Menu Path : /Audio/Audio 4
    Details   : Specifies second audio source (pair) for this multichannel codec.
    "
::= { enc1Params 319 }

enc1P319source2Entry OBJECT-TYPE
    SYNTAX Enc1P319source2Entry
    MAX-ACCESS not-accessible
    STATUS     current
    DESCRIPTION
    "Table Entry for Source 2"
    INDEX { slotId }
::= { enc1P319source2Table 1 }

Enc1P319source2Entry ::= SEQUENCE {
    enc1P319source2Value    Enc1E70enumObj
}

enc1P319source2Value OBJECT-TYPE
    SYNTAX     Enc1E70enumObj
    MAX-ACCESS read-write
    STATUS     current
    DESCRIPTION
    "Specifies second audio source (pair) for this multichannel codec."
::= { enc1P319source2Entry 1 }

enc1P320source3Table OBJECT-TYPE
    SYNTAX SEQUENCE OF Enc1P320source3Entry
    MAX-ACCESS not-accessible
    STATUS     current
    DESCRIPTION
    "
    Name      : Source 3
    Menu Path : /Audio/Audio 4
    Details   : Specifies third audio source (pair) for this multichannel codec.
    "
::= { enc1Params 320 }

enc1P320source3Entry OBJECT-TYPE
    SYNTAX Enc1P320source3Entry
    MAX-ACCESS not-accessible
    STATUS     current
    DESCRIPTION
    "Table Entry for Source 3"
    INDEX { slotId }
::= { enc1P320source3Table 1 }

Enc1P320source3Entry ::= SEQUENCE {
    enc1P320source3Value    Enc1E70enumObj
}

enc1P320source3Value OBJECT-TYPE
    SYNTAX     Enc1E70enumObj
    MAX-ACCESS read-write
    STATUS     current
    DESCRIPTION
    "Specifies third audio source (pair) for this multichannel codec."
::= { enc1P320source3Entry 1 }

enc1P321source4Table OBJECT-TYPE
    SYNTAX SEQUENCE OF Enc1P321source4Entry
    MAX-ACCESS not-accessible
    STATUS     current
    DESCRIPTION
    "
    Name      : Source 4
    Menu Path : /Audio/Audio 4
    Details   : Specifies fourth audio source (pair) for this multichannel codec.
    "
::= { enc1Params 321 }

enc1P321source4Entry OBJECT-TYPE
    SYNTAX Enc1P321source4Entry
    MAX-ACCESS not-accessible
    STATUS     current
    DESCRIPTION
    "Table Entry for Source 4"
    INDEX { slotId }
::= { enc1P321source4Table 1 }

Enc1P321source4Entry ::= SEQUENCE {
    enc1P321source4Value    Enc1E70enumObj
}

enc1P321source4Value OBJECT-TYPE
    SYNTAX     Enc1E70enumObj
    MAX-ACCESS read-write
    STATUS     current
    DESCRIPTION
    "Specifies fourth audio source (pair) for this multichannel codec."
::= { enc1P321source4Entry 1 }

enc1P322preProcessingTable OBJECT-TYPE
    SYNTAX SEQUENCE OF Enc1P322preProcessingEntry
    MAX-ACCESS not-accessible
    STATUS     current
    DESCRIPTION
    "
    Name      : Pre Processing
    Menu Path : Not Applicable
    Details   : Specifies special processing for audio channel
    "
::= { enc1Params 322 }

enc1P322preProcessingEntry OBJECT-TYPE
    SYNTAX Enc1P322preProcessingEntry
    MAX-ACCESS not-accessible
    STATUS     current
    DESCRIPTION
    "Table Entry for Pre Processing"
    INDEX { slotId }
::= { enc1P322preProcessingTable 1 }

Enc1P322preProcessingEntry ::= SEQUENCE {
    enc1P322preProcessingValue    Enc1E72enumObj
}

enc1P322preProcessingValue OBJECT-TYPE
    SYNTAX     Enc1E72enumObj
    MAX-ACCESS read-write
    STATUS     current
    DESCRIPTION
    "Specifies special processing for audio channel"
::= { enc1P322preProcessingEntry 1 }

enc1P323delayTable OBJECT-TYPE
    SYNTAX SEQUENCE OF Enc1P323delayEntry
    MAX-ACCESS not-accessible
    STATUS     current
    DESCRIPTION
    "
    Name      : Delay
    Menu Path : /Audio/Audio 4
    Units     : msec
    Precision : 0
    Low Range : -500
    High Range: 500
    Details   : Specify an additional audio delay, relative to video delay.

     NOTE: Precision/Units/Ranges represent the state of the
           parameter during the MIB generation, and does not
           neccessary reflect the current state of the parameter
    "
::= { enc1Params 323 }

enc1P323delayEntry OBJECT-TYPE
    SYNTAX Enc1P323delayEntry
    MAX-ACCESS not-accessible
    STATUS     current
    DESCRIPTION
    "Table Entry for Delay"
    INDEX { slotId }
::= { enc1P323delayTable 1 }

Enc1P323delayEntry ::= SEQUENCE {
    enc1P323delayValue    INTEGER
}

enc1P323delayValue OBJECT-TYPE
    SYNTAX     INTEGER
    MAX-ACCESS read-write
    STATUS     current
    DESCRIPTION
    "Specify an additional audio delay, relative to video delay."
::= { enc1P323delayEntry 1 }

enc1P324gainTable OBJECT-TYPE
    SYNTAX SEQUENCE OF Enc1P324gainEntry
    MAX-ACCESS not-accessible
    STATUS     current
    DESCRIPTION
    "
    Name      : Gain
    Menu Path : /Audio/Audio 4
    Units     : dB
    Precision : 1
    Low Range : -800
    High Range: 400
    Details   : Apply a gain (or attenuation) to all source channels.

     NOTE: Precision/Units/Ranges represent the state of the
           parameter during the MIB generation, and does not
           neccessary reflect the current state of the parameter
    "
::= { enc1Params 324 }

enc1P324gainEntry OBJECT-TYPE
    SYNTAX Enc1P324gainEntry
    MAX-ACCESS not-accessible
    STATUS     current
    DESCRIPTION
    "Table Entry for Gain"
    INDEX { slotId }
::= { enc1P324gainTable 1 }

Enc1P324gainEntry ::= SEQUENCE {
    enc1P324gainValue    INTEGER
}

enc1P324gainValue OBJECT-TYPE
    SYNTAX     INTEGER
    MAX-ACCESS read-write
    STATUS     current
    DESCRIPTION
    "Apply a gain (or attenuation) to all source channels."
::= { enc1P324gainEntry 1 }

enc1P326deemphasisTable OBJECT-TYPE
    SYNTAX SEQUENCE OF Enc1P326deemphasisEntry
    MAX-ACCESS not-accessible
    STATUS     current
    DESCRIPTION
    "
    Name      : Deemphasis
    Menu Path : /Audio/Audio 4
    Details   : Dolby Digital: applies deemphasis, Mpeg: indicates presence of preemphasis. Auto uses AES channel block indication.
    "
::= { enc1Params 326 }

enc1P326deemphasisEntry OBJECT-TYPE
    SYNTAX Enc1P326deemphasisEntry
    MAX-ACCESS not-accessible
    STATUS     current
    DESCRIPTION
    "Table Entry for Deemphasis"
    INDEX { slotId }
::= { enc1P326deemphasisTable 1 }

Enc1P326deemphasisEntry ::= SEQUENCE {
    enc1P326deemphasisValue    Enc1E2enumObj
}

enc1P326deemphasisValue OBJECT-TYPE
    SYNTAX     Enc1E2enumObj
    MAX-ACCESS read-write
    STATUS     current
    DESCRIPTION
    "Dolby Digital: applies deemphasis, Mpeg: indicates presence of preemphasis. Auto uses AES channel block indication."
::= { enc1P326deemphasisEntry 1 }

enc1P327modeTable OBJECT-TYPE
    SYNTAX SEQUENCE OF Enc1P327modeEntry
    MAX-ACCESS not-accessible
    STATUS     current
    DESCRIPTION
    "
    Name      : Mode
    Menu Path : /Audio/Audio 4
    Details   : Specifies the audio coding mode (maximum channel usage)
    "
::= { enc1Params 327 }

enc1P327modeEntry OBJECT-TYPE
    SYNTAX Enc1P327modeEntry
    MAX-ACCESS not-accessible
    STATUS     current
    DESCRIPTION
    "Table Entry for Mode"
    INDEX { slotId }
::= { enc1P327modeTable 1 }

Enc1P327modeEntry ::= SEQUENCE {
    enc1P327modeValue    Enc1E188enumObj
}

enc1P327modeValue OBJECT-TYPE
    SYNTAX     Enc1E188enumObj
    MAX-ACCESS read-write
    STATUS     current
    DESCRIPTION
    "Specifies the audio coding mode (maximum channel usage)"
::= { enc1P327modeEntry 1 }

enc1P328audioFormatTable OBJECT-TYPE
    SYNTAX SEQUENCE OF Enc1P328audioFormatEntry
    MAX-ACCESS not-accessible
    STATUS     current
    DESCRIPTION
    "
    Name      : Audio Format
    Menu Path : /Audio/Audio 4
    Details   : Specifies the audio encoding standard and bitrate.
    "
::= { enc1Params 328 }

enc1P328audioFormatEntry OBJECT-TYPE
    SYNTAX Enc1P328audioFormatEntry
    MAX-ACCESS not-accessible
    STATUS     current
    DESCRIPTION
    "Table Entry for Audio Format"
    INDEX { slotId }
::= { enc1P328audioFormatTable 1 }

Enc1P328audioFormatEntry ::= SEQUENCE {
    enc1P328audioFormatValue    Enc1E73enumObj
}

enc1P328audioFormatValue OBJECT-TYPE
    SYNTAX     Enc1E73enumObj
    MAX-ACCESS read-write
    STATUS     current
    DESCRIPTION
    "Specifies the audio encoding standard and bitrate."
::= { enc1P328audioFormatEntry 1 }

enc1P329languageCodeTable OBJECT-TYPE
    SYNTAX SEQUENCE OF Enc1P329languageCodeEntry
    MAX-ACCESS not-accessible
    STATUS     current
    DESCRIPTION
    "
    Name      : Language Code
    Menu Path : /Audio/Audio 4
    Details   : Specifies the ISO 639-2 (three letter) language code.
    "
::= { enc1Params 329 }

enc1P329languageCodeEntry OBJECT-TYPE
    SYNTAX Enc1P329languageCodeEntry
    MAX-ACCESS not-accessible
    STATUS     current
    DESCRIPTION
    "Table Entry for Language Code"
    INDEX { slotId }
::= { enc1P329languageCodeTable 1 }

Enc1P329languageCodeEntry ::= SEQUENCE {
    enc1P329languageCodeValue    DisplayString
}

enc1P329languageCodeValue OBJECT-TYPE
    SYNTAX     DisplayString
    MAX-ACCESS read-write
    STATUS     current
    DESCRIPTION
    "Specifies the ISO 639-2 (three letter) language code."
::= { enc1P329languageCodeEntry 1 }

enc1P330enableOutputTable OBJECT-TYPE
    SYNTAX SEQUENCE OF Enc1P330enableOutputEntry
    MAX-ACCESS not-accessible
    STATUS     current
    DESCRIPTION
    "
    Name      : Enable Output
    Menu Path : /Audio/Audio 4
    Details   : Specifies which encoded program carries this audio.
    "
::= { enc1Params 330 }

enc1P330enableOutputEntry OBJECT-TYPE
    SYNTAX Enc1P330enableOutputEntry
    MAX-ACCESS not-accessible
    STATUS     current
    DESCRIPTION
    "Table Entry for Enable Output"
    INDEX { slotId }
::= { enc1P330enableOutputTable 1 }

Enc1P330enableOutputEntry ::= SEQUENCE {
    enc1P330enableOutputValue    Enc1E81enumObj
}

enc1P330enableOutputValue OBJECT-TYPE
    SYNTAX     Enc1E81enumObj
    MAX-ACCESS read-write
    STATUS     current
    DESCRIPTION
    "Specifies which encoded program carries this audio."
::= { enc1P330enableOutputEntry 1 }

enc1P331metadataSourceTable OBJECT-TYPE
    SYNTAX SEQUENCE OF Enc1P331metadataSourceEntry
    MAX-ACCESS not-accessible
    STATUS     current
    DESCRIPTION
    "
    Name      : Metadata Source
    Menu Path : /Audio/Audio 4/Metadata
    Details   : Specifies source for Dolby audio metadata
    "
::= { enc1Params 331 }

enc1P331metadataSourceEntry OBJECT-TYPE
    SYNTAX Enc1P331metadataSourceEntry
    MAX-ACCESS not-accessible
    STATUS     current
    DESCRIPTION
    "Table Entry for Metadata Source"
    INDEX { slotId }
::= { enc1P331metadataSourceTable 1 }

Enc1P331metadataSourceEntry ::= SEQUENCE {
    enc1P331metadataSourceValue    Enc1E83enumObj
}

enc1P331metadataSourceValue OBJECT-TYPE
    SYNTAX     Enc1E83enumObj
    MAX-ACCESS read-write
    STATUS     current
    DESCRIPTION
    "Specifies source for Dolby audio metadata"
::= { enc1P331metadataSourceEntry 1 }

enc1P332metadataReversionModeTable OBJECT-TYPE
    SYNTAX SEQUENCE OF Enc1P332metadataReversionModeEntry
    MAX-ACCESS not-accessible
    STATUS     current
    DESCRIPTION
    "
    Name      : Metadata Reversion Mode
    Menu Path : /Audio/Audio 4/Metadata
    Details   : Specifies response to interruption in metadata source
    "
::= { enc1Params 332 }

enc1P332metadataReversionModeEntry OBJECT-TYPE
    SYNTAX Enc1P332metadataReversionModeEntry
    MAX-ACCESS not-accessible
    STATUS     current
    DESCRIPTION
    "Table Entry for Metadata Reversion Mode"
    INDEX { slotId }
::= { enc1P332metadataReversionModeTable 1 }

Enc1P332metadataReversionModeEntry ::= SEQUENCE {
    enc1P332metadataReversionModeValue    Enc1E84enumObj
}

enc1P332metadataReversionModeValue OBJECT-TYPE
    SYNTAX     Enc1E84enumObj
    MAX-ACCESS read-write
    STATUS     current
    DESCRIPTION
    "Specifies response to interruption in metadata source"
::= { enc1P332metadataReversionModeEntry 1 }

enc1P333pssignalingTable OBJECT-TYPE
    SYNTAX SEQUENCE OF Enc1P333pssignalingEntry
    MAX-ACCESS not-accessible
    STATUS     current
    DESCRIPTION
    "
    Name      : PS Signaling
    Menu Path : /Audio/Audio 4/AAC
    Details   : Specifies the parametric stereo signaling for AAC audio encoding.
    "
::= { enc1Params 333 }

enc1P333pssignalingEntry OBJECT-TYPE
    SYNTAX Enc1P333pssignalingEntry
    MAX-ACCESS not-accessible
    STATUS     current
    DESCRIPTION
    "Table Entry for PS Signaling"
    INDEX { slotId }
::= { enc1P333pssignalingTable 1 }

Enc1P333pssignalingEntry ::= SEQUENCE {
    enc1P333pssignalingValue    Enc1E76enumObj
}

enc1P333pssignalingValue OBJECT-TYPE
    SYNTAX     Enc1E76enumObj
    MAX-ACCESS read-write
    STATUS     current
    DESCRIPTION
    "Specifies the parametric stereo signaling for AAC audio encoding."
::= { enc1P333pssignalingEntry 1 }

enc1P334sbrsignalingTable OBJECT-TYPE
    SYNTAX SEQUENCE OF Enc1P334sbrsignalingEntry
    MAX-ACCESS not-accessible
    STATUS     current
    DESCRIPTION
    "
    Name      : SBR Signaling
    Menu Path : /Audio/Audio 4/AAC
    Details   : Specifies the SBR signaling for AAC audio encoding.
    "
::= { enc1Params 334 }

enc1P334sbrsignalingEntry OBJECT-TYPE
    SYNTAX Enc1P334sbrsignalingEntry
    MAX-ACCESS not-accessible
    STATUS     current
    DESCRIPTION
    "Table Entry for SBR Signaling"
    INDEX { slotId }
::= { enc1P334sbrsignalingTable 1 }

Enc1P334sbrsignalingEntry ::= SEQUENCE {
    enc1P334sbrsignalingValue    Enc1E77enumObj
}

enc1P334sbrsignalingValue OBJECT-TYPE
    SYNTAX     Enc1E77enumObj
    MAX-ACCESS read-write
    STATUS     current
    DESCRIPTION
    "Specifies the SBR signaling for AAC audio encoding."
::= { enc1P334sbrsignalingEntry 1 }

enc1P335transportTable OBJECT-TYPE
    SYNTAX SEQUENCE OF Enc1P335transportEntry
    MAX-ACCESS not-accessible
    STATUS     current
    DESCRIPTION
    "
    Name      : Transport
    Menu Path : /Audio/Audio 4/AAC
    Details   : Specifies the transport layer (framing) for AAC audio encoding.
    "
::= { enc1Params 335 }

enc1P335transportEntry OBJECT-TYPE
    SYNTAX Enc1P335transportEntry
    MAX-ACCESS not-accessible
    STATUS     current
    DESCRIPTION
    "Table Entry for Transport"
    INDEX { slotId }
::= { enc1P335transportTable 1 }

Enc1P335transportEntry ::= SEQUENCE {
    enc1P335transportValue    Enc1E78enumObj
}

enc1P335transportValue OBJECT-TYPE
    SYNTAX     Enc1E78enumObj
    MAX-ACCESS read-write
    STATUS     current
    DESCRIPTION
    "Specifies the transport layer (framing) for AAC audio encoding."
::= { enc1P335transportEntry 1 }

enc1P337programConfigurationTable OBJECT-TYPE
    SYNTAX SEQUENCE OF Enc1P337programConfigurationEntry
    MAX-ACCESS not-accessible
    STATUS     current
    DESCRIPTION
    "
    Name      : Program Configuration
    Menu Path : /Audio/Audio 4/Dolby E Encoder
    Details   : Determines how audio channels are grouped into programs within a Dolby E bitstream.
    "
::= { enc1Params 337 }

enc1P337programConfigurationEntry OBJECT-TYPE
    SYNTAX Enc1P337programConfigurationEntry
    MAX-ACCESS not-accessible
    STATUS     current
    DESCRIPTION
    "Table Entry for Program Configuration"
    INDEX { slotId }
::= { enc1P337programConfigurationTable 1 }

Enc1P337programConfigurationEntry ::= SEQUENCE {
    enc1P337programConfigurationValue    Enc1E189enumObj
}

enc1P337programConfigurationValue OBJECT-TYPE
    SYNTAX     Enc1E189enumObj
    MAX-ACCESS read-write
    STATUS     current
    DESCRIPTION
    "Determines how audio channels are grouped into programs within a Dolby E bitstream."
::= { enc1P337programConfigurationEntry 1 }

enc1P367avsyncAdjustCountTable OBJECT-TYPE
    SYNTAX SEQUENCE OF Enc1P367avsyncAdjustCountEntry
    MAX-ACCESS not-accessible
    STATUS     current
    DESCRIPTION
    "
    Name      : AV Sync Adjust Count
    Menu Path : /Audio/Audio 4/Status
    Units     : 
    Precision : 0
    Low Range : 0
    High Range: -1
    Details   : Displays the count of audio/video sync adjustments (lipsync discontinuities).

     NOTE: Precision/Units/Ranges represent the state of the
           parameter during the MIB generation, and does not
           neccessary reflect the current state of the parameter
    "
::= { enc1Params 367 }

enc1P367avsyncAdjustCountEntry OBJECT-TYPE
    SYNTAX Enc1P367avsyncAdjustCountEntry
    MAX-ACCESS not-accessible
    STATUS     current
    DESCRIPTION
    "Table Entry for AV Sync Adjust Count"
    INDEX { slotId }
::= { enc1P367avsyncAdjustCountTable 1 }

Enc1P367avsyncAdjustCountEntry ::= SEQUENCE {
    enc1P367avsyncAdjustCountValue    INTEGER
}

enc1P367avsyncAdjustCountValue OBJECT-TYPE
    SYNTAX     INTEGER
    MAX-ACCESS read-only
    STATUS     current
    DESCRIPTION
    "Displays the count of audio/video sync adjustments (lipsync discontinuities)."
::= { enc1P367avsyncAdjustCountEntry 1 }

enc1P368pmtpositionTable OBJECT-TYPE
    SYNTAX SEQUENCE OF Enc1P368pmtpositionEntry
    MAX-ACCESS not-accessible
    STATUS     current
    DESCRIPTION
    "
    Name      : PMT Position
    Menu Path : /Audio/Audio 4/Status
    Units     : 
    Precision : 0
    Low Range : 0
    High Range: 8
    Details   : Displays the relative position in the PMT of this audio stream

     NOTE: Precision/Units/Ranges represent the state of the
           parameter during the MIB generation, and does not
           neccessary reflect the current state of the parameter
    "
::= { enc1Params 368 }

enc1P368pmtpositionEntry OBJECT-TYPE
    SYNTAX Enc1P368pmtpositionEntry
    MAX-ACCESS not-accessible
    STATUS     current
    DESCRIPTION
    "Table Entry for PMT Position"
    INDEX { slotId }
::= { enc1P368pmtpositionTable 1 }

Enc1P368pmtpositionEntry ::= SEQUENCE {
    enc1P368pmtpositionValue    INTEGER
}

enc1P368pmtpositionValue OBJECT-TYPE
    SYNTAX     INTEGER
    MAX-ACCESS read-only
    STATUS     current
    DESCRIPTION
    "Displays the relative position in the PMT of this audio stream"
::= { enc1P368pmtpositionEntry 1 }

enc1P370lossofSignalTable OBJECT-TYPE
    SYNTAX SEQUENCE OF Enc1P370lossofSignalEntry
    MAX-ACCESS not-accessible
    STATUS     current
    DESCRIPTION
    "
    Name      : Loss of Signal
    Menu Path : /Audio/Audio 4/Status
    Details   : Indicates loss of a selected source signal.
    "
::= { enc1Params 370 }

enc1P370lossofSignalEntry OBJECT-TYPE
    SYNTAX Enc1P370lossofSignalEntry
    MAX-ACCESS not-accessible
    STATUS     current
    DESCRIPTION
    "Table Entry for Loss of Signal"
    INDEX { slotId }
::= { enc1P370lossofSignalTable 1 }

Enc1P370lossofSignalEntry ::= SEQUENCE {
    enc1P370lossofSignalValue    Enc1E5enumObj
}

enc1P370lossofSignalValue OBJECT-TYPE
    SYNTAX     Enc1E5enumObj
    MAX-ACCESS read-only
    STATUS     current
    DESCRIPTION
    "Indicates loss of a selected source signal."
::= { enc1P370lossofSignalEntry 1 }

enc1P371source1Table OBJECT-TYPE
    SYNTAX SEQUENCE OF Enc1P371source1Entry
    MAX-ACCESS not-accessible
    STATUS     current
    DESCRIPTION
    "
    Name      : Source 1
    Menu Path : /Audio/Audio 5
    Details   : Specifies audio source (pair) for this codec.
    "
::= { enc1Params 371 }

enc1P371source1Entry OBJECT-TYPE
    SYNTAX Enc1P371source1Entry
    MAX-ACCESS not-accessible
    STATUS     current
    DESCRIPTION
    "Table Entry for Source 1"
    INDEX { slotId }
::= { enc1P371source1Table 1 }

Enc1P371source1Entry ::= SEQUENCE {
    enc1P371source1Value    Enc1E70enumObj
}

enc1P371source1Value OBJECT-TYPE
    SYNTAX     Enc1E70enumObj
    MAX-ACCESS read-write
    STATUS     current
    DESCRIPTION
    "Specifies audio source (pair) for this codec."
::= { enc1P371source1Entry 1 }

enc1P372source2Table OBJECT-TYPE
    SYNTAX SEQUENCE OF Enc1P372source2Entry
    MAX-ACCESS not-accessible
    STATUS     current
    DESCRIPTION
    "
    Name      : Source 2
    Menu Path : /Audio/Audio 5
    Details   : Specifies second audio source (pair) for this multichannel codec.
    "
::= { enc1Params 372 }

enc1P372source2Entry OBJECT-TYPE
    SYNTAX Enc1P372source2Entry
    MAX-ACCESS not-accessible
    STATUS     current
    DESCRIPTION
    "Table Entry for Source 2"
    INDEX { slotId }
::= { enc1P372source2Table 1 }

Enc1P372source2Entry ::= SEQUENCE {
    enc1P372source2Value    Enc1E70enumObj
}

enc1P372source2Value OBJECT-TYPE
    SYNTAX     Enc1E70enumObj
    MAX-ACCESS read-write
    STATUS     current
    DESCRIPTION
    "Specifies second audio source (pair) for this multichannel codec."
::= { enc1P372source2Entry 1 }

enc1P373source3Table OBJECT-TYPE
    SYNTAX SEQUENCE OF Enc1P373source3Entry
    MAX-ACCESS not-accessible
    STATUS     current
    DESCRIPTION
    "
    Name      : Source 3
    Menu Path : /Audio/Audio 5
    Details   : Specifies third audio source (pair) for this multichannel codec.
    "
::= { enc1Params 373 }

enc1P373source3Entry OBJECT-TYPE
    SYNTAX Enc1P373source3Entry
    MAX-ACCESS not-accessible
    STATUS     current
    DESCRIPTION
    "Table Entry for Source 3"
    INDEX { slotId }
::= { enc1P373source3Table 1 }

Enc1P373source3Entry ::= SEQUENCE {
    enc1P373source3Value    Enc1E70enumObj
}

enc1P373source3Value OBJECT-TYPE
    SYNTAX     Enc1E70enumObj
    MAX-ACCESS read-write
    STATUS     current
    DESCRIPTION
    "Specifies third audio source (pair) for this multichannel codec."
::= { enc1P373source3Entry 1 }

enc1P374source4Table OBJECT-TYPE
    SYNTAX SEQUENCE OF Enc1P374source4Entry
    MAX-ACCESS not-accessible
    STATUS     current
    DESCRIPTION
    "
    Name      : Source 4
    Menu Path : /Audio/Audio 5
    Details   : Specifies fourth audio source (pair) for this multichannel codec.
    "
::= { enc1Params 374 }

enc1P374source4Entry OBJECT-TYPE
    SYNTAX Enc1P374source4Entry
    MAX-ACCESS not-accessible
    STATUS     current
    DESCRIPTION
    "Table Entry for Source 4"
    INDEX { slotId }
::= { enc1P374source4Table 1 }

Enc1P374source4Entry ::= SEQUENCE {
    enc1P374source4Value    Enc1E70enumObj
}

enc1P374source4Value OBJECT-TYPE
    SYNTAX     Enc1E70enumObj
    MAX-ACCESS read-write
    STATUS     current
    DESCRIPTION
    "Specifies fourth audio source (pair) for this multichannel codec."
::= { enc1P374source4Entry 1 }

enc1P375preProcessingTable OBJECT-TYPE
    SYNTAX SEQUENCE OF Enc1P375preProcessingEntry
    MAX-ACCESS not-accessible
    STATUS     current
    DESCRIPTION
    "
    Name      : Pre Processing
    Menu Path : Not Applicable
    Details   : Specifies special processing for audio channel
    "
::= { enc1Params 375 }

enc1P375preProcessingEntry OBJECT-TYPE
    SYNTAX Enc1P375preProcessingEntry
    MAX-ACCESS not-accessible
    STATUS     current
    DESCRIPTION
    "Table Entry for Pre Processing"
    INDEX { slotId }
::= { enc1P375preProcessingTable 1 }

Enc1P375preProcessingEntry ::= SEQUENCE {
    enc1P375preProcessingValue    Enc1E72enumObj
}

enc1P375preProcessingValue OBJECT-TYPE
    SYNTAX     Enc1E72enumObj
    MAX-ACCESS read-write
    STATUS     current
    DESCRIPTION
    "Specifies special processing for audio channel"
::= { enc1P375preProcessingEntry 1 }

enc1P376delayTable OBJECT-TYPE
    SYNTAX SEQUENCE OF Enc1P376delayEntry
    MAX-ACCESS not-accessible
    STATUS     current
    DESCRIPTION
    "
    Name      : Delay
    Menu Path : /Audio/Audio 5
    Units     : msec
    Precision : 0
    Low Range : -500
    High Range: 500
    Details   : Specify an additional audio delay, relative to video delay.

     NOTE: Precision/Units/Ranges represent the state of the
           parameter during the MIB generation, and does not
           neccessary reflect the current state of the parameter
    "
::= { enc1Params 376 }

enc1P376delayEntry OBJECT-TYPE
    SYNTAX Enc1P376delayEntry
    MAX-ACCESS not-accessible
    STATUS     current
    DESCRIPTION
    "Table Entry for Delay"
    INDEX { slotId }
::= { enc1P376delayTable 1 }

Enc1P376delayEntry ::= SEQUENCE {
    enc1P376delayValue    INTEGER
}

enc1P376delayValue OBJECT-TYPE
    SYNTAX     INTEGER
    MAX-ACCESS read-write
    STATUS     current
    DESCRIPTION
    "Specify an additional audio delay, relative to video delay."
::= { enc1P376delayEntry 1 }

enc1P377gainTable OBJECT-TYPE
    SYNTAX SEQUENCE OF Enc1P377gainEntry
    MAX-ACCESS not-accessible
    STATUS     current
    DESCRIPTION
    "
    Name      : Gain
    Menu Path : /Audio/Audio 5
    Units     : dB
    Precision : 1
    Low Range : -800
    High Range: 400
    Details   : Apply a gain (or attenuation) to all source channels.

     NOTE: Precision/Units/Ranges represent the state of the
           parameter during the MIB generation, and does not
           neccessary reflect the current state of the parameter
    "
::= { enc1Params 377 }

enc1P377gainEntry OBJECT-TYPE
    SYNTAX Enc1P377gainEntry
    MAX-ACCESS not-accessible
    STATUS     current
    DESCRIPTION
    "Table Entry for Gain"
    INDEX { slotId }
::= { enc1P377gainTable 1 }

Enc1P377gainEntry ::= SEQUENCE {
    enc1P377gainValue    INTEGER
}

enc1P377gainValue OBJECT-TYPE
    SYNTAX     INTEGER
    MAX-ACCESS read-write
    STATUS     current
    DESCRIPTION
    "Apply a gain (or attenuation) to all source channels."
::= { enc1P377gainEntry 1 }

enc1P379deemphasisTable OBJECT-TYPE
    SYNTAX SEQUENCE OF Enc1P379deemphasisEntry
    MAX-ACCESS not-accessible
    STATUS     current
    DESCRIPTION
    "
    Name      : Deemphasis
    Menu Path : /Audio/Audio 5
    Details   : Dolby Digital: applies deemphasis, Mpeg: indicates presence of preemphasis. Auto uses AES channel block indication.
    "
::= { enc1Params 379 }

enc1P379deemphasisEntry OBJECT-TYPE
    SYNTAX Enc1P379deemphasisEntry
    MAX-ACCESS not-accessible
    STATUS     current
    DESCRIPTION
    "Table Entry for Deemphasis"
    INDEX { slotId }
::= { enc1P379deemphasisTable 1 }

Enc1P379deemphasisEntry ::= SEQUENCE {
    enc1P379deemphasisValue    Enc1E2enumObj
}

enc1P379deemphasisValue OBJECT-TYPE
    SYNTAX     Enc1E2enumObj
    MAX-ACCESS read-write
    STATUS     current
    DESCRIPTION
    "Dolby Digital: applies deemphasis, Mpeg: indicates presence of preemphasis. Auto uses AES channel block indication."
::= { enc1P379deemphasisEntry 1 }

enc1P380modeTable OBJECT-TYPE
    SYNTAX SEQUENCE OF Enc1P380modeEntry
    MAX-ACCESS not-accessible
    STATUS     current
    DESCRIPTION
    "
    Name      : Mode
    Menu Path : /Audio/Audio 5
    Details   : Specifies the audio coding mode (maximum channel usage)
    "
::= { enc1Params 380 }

enc1P380modeEntry OBJECT-TYPE
    SYNTAX Enc1P380modeEntry
    MAX-ACCESS not-accessible
    STATUS     current
    DESCRIPTION
    "Table Entry for Mode"
    INDEX { slotId }
::= { enc1P380modeTable 1 }

Enc1P380modeEntry ::= SEQUENCE {
    enc1P380modeValue    Enc1E191enumObj
}

enc1P380modeValue OBJECT-TYPE
    SYNTAX     Enc1E191enumObj
    MAX-ACCESS read-write
    STATUS     current
    DESCRIPTION
    "Specifies the audio coding mode (maximum channel usage)"
::= { enc1P380modeEntry 1 }

enc1P381audioFormatTable OBJECT-TYPE
    SYNTAX SEQUENCE OF Enc1P381audioFormatEntry
    MAX-ACCESS not-accessible
    STATUS     current
    DESCRIPTION
    "
    Name      : Audio Format
    Menu Path : /Audio/Audio 5
    Details   : Specifies the audio encoding standard and bitrate.
    "
::= { enc1Params 381 }

enc1P381audioFormatEntry OBJECT-TYPE
    SYNTAX Enc1P381audioFormatEntry
    MAX-ACCESS not-accessible
    STATUS     current
    DESCRIPTION
    "Table Entry for Audio Format"
    INDEX { slotId }
::= { enc1P381audioFormatTable 1 }

Enc1P381audioFormatEntry ::= SEQUENCE {
    enc1P381audioFormatValue    Enc1E73enumObj
}

enc1P381audioFormatValue OBJECT-TYPE
    SYNTAX     Enc1E73enumObj
    MAX-ACCESS read-write
    STATUS     current
    DESCRIPTION
    "Specifies the audio encoding standard and bitrate."
::= { enc1P381audioFormatEntry 1 }

enc1P382languageCodeTable OBJECT-TYPE
    SYNTAX SEQUENCE OF Enc1P382languageCodeEntry
    MAX-ACCESS not-accessible
    STATUS     current
    DESCRIPTION
    "
    Name      : Language Code
    Menu Path : /Audio/Audio 5
    Details   : Specifies the ISO 639-2 (three letter) language code.
    "
::= { enc1Params 382 }

enc1P382languageCodeEntry OBJECT-TYPE
    SYNTAX Enc1P382languageCodeEntry
    MAX-ACCESS not-accessible
    STATUS     current
    DESCRIPTION
    "Table Entry for Language Code"
    INDEX { slotId }
::= { enc1P382languageCodeTable 1 }

Enc1P382languageCodeEntry ::= SEQUENCE {
    enc1P382languageCodeValue    DisplayString
}

enc1P382languageCodeValue OBJECT-TYPE
    SYNTAX     DisplayString
    MAX-ACCESS read-write
    STATUS     current
    DESCRIPTION
    "Specifies the ISO 639-2 (three letter) language code."
::= { enc1P382languageCodeEntry 1 }

enc1P383enableOutputTable OBJECT-TYPE
    SYNTAX SEQUENCE OF Enc1P383enableOutputEntry
    MAX-ACCESS not-accessible
    STATUS     current
    DESCRIPTION
    "
    Name      : Enable Output
    Menu Path : /Audio/Audio 5
    Details   : Specifies which encoded program carries this audio.
    "
::= { enc1Params 383 }

enc1P383enableOutputEntry OBJECT-TYPE
    SYNTAX Enc1P383enableOutputEntry
    MAX-ACCESS not-accessible
    STATUS     current
    DESCRIPTION
    "Table Entry for Enable Output"
    INDEX { slotId }
::= { enc1P383enableOutputTable 1 }

Enc1P383enableOutputEntry ::= SEQUENCE {
    enc1P383enableOutputValue    Enc1E82enumObj
}

enc1P383enableOutputValue OBJECT-TYPE
    SYNTAX     Enc1E82enumObj
    MAX-ACCESS read-write
    STATUS     current
    DESCRIPTION
    "Specifies which encoded program carries this audio."
::= { enc1P383enableOutputEntry 1 }

enc1P384metadataSourceTable OBJECT-TYPE
    SYNTAX SEQUENCE OF Enc1P384metadataSourceEntry
    MAX-ACCESS not-accessible
    STATUS     current
    DESCRIPTION
    "
    Name      : Metadata Source
    Menu Path : /Audio/Audio 5/Metadata
    Details   : Specifies source for Dolby audio metadata
    "
::= { enc1Params 384 }

enc1P384metadataSourceEntry OBJECT-TYPE
    SYNTAX Enc1P384metadataSourceEntry
    MAX-ACCESS not-accessible
    STATUS     current
    DESCRIPTION
    "Table Entry for Metadata Source"
    INDEX { slotId }
::= { enc1P384metadataSourceTable 1 }

Enc1P384metadataSourceEntry ::= SEQUENCE {
    enc1P384metadataSourceValue    Enc1E83enumObj
}

enc1P384metadataSourceValue OBJECT-TYPE
    SYNTAX     Enc1E83enumObj
    MAX-ACCESS read-write
    STATUS     current
    DESCRIPTION
    "Specifies source for Dolby audio metadata"
::= { enc1P384metadataSourceEntry 1 }

enc1P385metadataReversionModeTable OBJECT-TYPE
    SYNTAX SEQUENCE OF Enc1P385metadataReversionModeEntry
    MAX-ACCESS not-accessible
    STATUS     current
    DESCRIPTION
    "
    Name      : Metadata Reversion Mode
    Menu Path : /Audio/Audio 5/Metadata
    Details   : Specifies response to interruption in metadata source
    "
::= { enc1Params 385 }

enc1P385metadataReversionModeEntry OBJECT-TYPE
    SYNTAX Enc1P385metadataReversionModeEntry
    MAX-ACCESS not-accessible
    STATUS     current
    DESCRIPTION
    "Table Entry for Metadata Reversion Mode"
    INDEX { slotId }
::= { enc1P385metadataReversionModeTable 1 }

Enc1P385metadataReversionModeEntry ::= SEQUENCE {
    enc1P385metadataReversionModeValue    Enc1E84enumObj
}

enc1P385metadataReversionModeValue OBJECT-TYPE
    SYNTAX     Enc1E84enumObj
    MAX-ACCESS read-write
    STATUS     current
    DESCRIPTION
    "Specifies response to interruption in metadata source"
::= { enc1P385metadataReversionModeEntry 1 }

enc1P386pssignalingTable OBJECT-TYPE
    SYNTAX SEQUENCE OF Enc1P386pssignalingEntry
    MAX-ACCESS not-accessible
    STATUS     current
    DESCRIPTION
    "
    Name      : PS Signaling
    Menu Path : /Audio/Audio 5/AAC
    Details   : Specifies the parametric stereo signaling for AAC audio encoding.
    "
::= { enc1Params 386 }

enc1P386pssignalingEntry OBJECT-TYPE
    SYNTAX Enc1P386pssignalingEntry
    MAX-ACCESS not-accessible
    STATUS     current
    DESCRIPTION
    "Table Entry for PS Signaling"
    INDEX { slotId }
::= { enc1P386pssignalingTable 1 }

Enc1P386pssignalingEntry ::= SEQUENCE {
    enc1P386pssignalingValue    Enc1E76enumObj
}

enc1P386pssignalingValue OBJECT-TYPE
    SYNTAX     Enc1E76enumObj
    MAX-ACCESS read-write
    STATUS     current
    DESCRIPTION
    "Specifies the parametric stereo signaling for AAC audio encoding."
::= { enc1P386pssignalingEntry 1 }

enc1P387sbrsignalingTable OBJECT-TYPE
    SYNTAX SEQUENCE OF Enc1P387sbrsignalingEntry
    MAX-ACCESS not-accessible
    STATUS     current
    DESCRIPTION
    "
    Name      : SBR Signaling
    Menu Path : /Audio/Audio 5/AAC
    Details   : Specifies the SBR signaling for AAC audio encoding.
    "
::= { enc1Params 387 }

enc1P387sbrsignalingEntry OBJECT-TYPE
    SYNTAX Enc1P387sbrsignalingEntry
    MAX-ACCESS not-accessible
    STATUS     current
    DESCRIPTION
    "Table Entry for SBR Signaling"
    INDEX { slotId }
::= { enc1P387sbrsignalingTable 1 }

Enc1P387sbrsignalingEntry ::= SEQUENCE {
    enc1P387sbrsignalingValue    Enc1E77enumObj
}

enc1P387sbrsignalingValue OBJECT-TYPE
    SYNTAX     Enc1E77enumObj
    MAX-ACCESS read-write
    STATUS     current
    DESCRIPTION
    "Specifies the SBR signaling for AAC audio encoding."
::= { enc1P387sbrsignalingEntry 1 }

enc1P388transportTable OBJECT-TYPE
    SYNTAX SEQUENCE OF Enc1P388transportEntry
    MAX-ACCESS not-accessible
    STATUS     current
    DESCRIPTION
    "
    Name      : Transport
    Menu Path : /Audio/Audio 5/AAC
    Details   : Specifies the transport layer (framing) for AAC audio encoding.
    "
::= { enc1Params 388 }

enc1P388transportEntry OBJECT-TYPE
    SYNTAX Enc1P388transportEntry
    MAX-ACCESS not-accessible
    STATUS     current
    DESCRIPTION
    "Table Entry for Transport"
    INDEX { slotId }
::= { enc1P388transportTable 1 }

Enc1P388transportEntry ::= SEQUENCE {
    enc1P388transportValue    Enc1E78enumObj
}

enc1P388transportValue OBJECT-TYPE
    SYNTAX     Enc1E78enumObj
    MAX-ACCESS read-write
    STATUS     current
    DESCRIPTION
    "Specifies the transport layer (framing) for AAC audio encoding."
::= { enc1P388transportEntry 1 }

enc1P390programConfigurationTable OBJECT-TYPE
    SYNTAX SEQUENCE OF Enc1P390programConfigurationEntry
    MAX-ACCESS not-accessible
    STATUS     current
    DESCRIPTION
    "
    Name      : Program Configuration
    Menu Path : /Audio/Audio 5/Dolby E Encoder
    Details   : Determines how audio channels are grouped into programs within a Dolby E bitstream.
    "
::= { enc1Params 390 }

enc1P390programConfigurationEntry OBJECT-TYPE
    SYNTAX Enc1P390programConfigurationEntry
    MAX-ACCESS not-accessible
    STATUS     current
    DESCRIPTION
    "Table Entry for Program Configuration"
    INDEX { slotId }
::= { enc1P390programConfigurationTable 1 }

Enc1P390programConfigurationEntry ::= SEQUENCE {
    enc1P390programConfigurationValue    Enc1E192enumObj
}

enc1P390programConfigurationValue OBJECT-TYPE
    SYNTAX     Enc1E192enumObj
    MAX-ACCESS read-write
    STATUS     current
    DESCRIPTION
    "Determines how audio channels are grouped into programs within a Dolby E bitstream."
::= { enc1P390programConfigurationEntry 1 }

enc1P420avsyncAdjustCountTable OBJECT-TYPE
    SYNTAX SEQUENCE OF Enc1P420avsyncAdjustCountEntry
    MAX-ACCESS not-accessible
    STATUS     current
    DESCRIPTION
    "
    Name      : AV Sync Adjust Count
    Menu Path : /Audio/Audio 5/Status
    Units     : 
    Precision : 0
    Low Range : 0
    High Range: -1
    Details   : Displays the count of audio/video sync adjustments (lipsync discontinuities).

     NOTE: Precision/Units/Ranges represent the state of the
           parameter during the MIB generation, and does not
           neccessary reflect the current state of the parameter
    "
::= { enc1Params 420 }

enc1P420avsyncAdjustCountEntry OBJECT-TYPE
    SYNTAX Enc1P420avsyncAdjustCountEntry
    MAX-ACCESS not-accessible
    STATUS     current
    DESCRIPTION
    "Table Entry for AV Sync Adjust Count"
    INDEX { slotId }
::= { enc1P420avsyncAdjustCountTable 1 }

Enc1P420avsyncAdjustCountEntry ::= SEQUENCE {
    enc1P420avsyncAdjustCountValue    INTEGER
}

enc1P420avsyncAdjustCountValue OBJECT-TYPE
    SYNTAX     INTEGER
    MAX-ACCESS read-only
    STATUS     current
    DESCRIPTION
    "Displays the count of audio/video sync adjustments (lipsync discontinuities)."
::= { enc1P420avsyncAdjustCountEntry 1 }

enc1P421pmtpositionTable OBJECT-TYPE
    SYNTAX SEQUENCE OF Enc1P421pmtpositionEntry
    MAX-ACCESS not-accessible
    STATUS     current
    DESCRIPTION
    "
    Name      : PMT Position
    Menu Path : /Audio/Audio 5/Status
    Units     : 
    Precision : 0
    Low Range : 0
    High Range: 8
    Details   : Displays the relative position in the PMT of this audio stream

     NOTE: Precision/Units/Ranges represent the state of the
           parameter during the MIB generation, and does not
           neccessary reflect the current state of the parameter
    "
::= { enc1Params 421 }

enc1P421pmtpositionEntry OBJECT-TYPE
    SYNTAX Enc1P421pmtpositionEntry
    MAX-ACCESS not-accessible
    STATUS     current
    DESCRIPTION
    "Table Entry for PMT Position"
    INDEX { slotId }
::= { enc1P421pmtpositionTable 1 }

Enc1P421pmtpositionEntry ::= SEQUENCE {
    enc1P421pmtpositionValue    INTEGER
}

enc1P421pmtpositionValue OBJECT-TYPE
    SYNTAX     INTEGER
    MAX-ACCESS read-only
    STATUS     current
    DESCRIPTION
    "Displays the relative position in the PMT of this audio stream"
::= { enc1P421pmtpositionEntry 1 }

enc1P423lossofSignalTable OBJECT-TYPE
    SYNTAX SEQUENCE OF Enc1P423lossofSignalEntry
    MAX-ACCESS not-accessible
    STATUS     current
    DESCRIPTION
    "
    Name      : Loss of Signal
    Menu Path : /Audio/Audio 5/Status
    Details   : Indicates loss of a selected source signal.
    "
::= { enc1Params 423 }

enc1P423lossofSignalEntry OBJECT-TYPE
    SYNTAX Enc1P423lossofSignalEntry
    MAX-ACCESS not-accessible
    STATUS     current
    DESCRIPTION
    "Table Entry for Loss of Signal"
    INDEX { slotId }
::= { enc1P423lossofSignalTable 1 }

Enc1P423lossofSignalEntry ::= SEQUENCE {
    enc1P423lossofSignalValue    Enc1E5enumObj
}

enc1P423lossofSignalValue OBJECT-TYPE
    SYNTAX     Enc1E5enumObj
    MAX-ACCESS read-only
    STATUS     current
    DESCRIPTION
    "Indicates loss of a selected source signal."
::= { enc1P423lossofSignalEntry 1 }

enc1P424source1Table OBJECT-TYPE
    SYNTAX SEQUENCE OF Enc1P424source1Entry
    MAX-ACCESS not-accessible
    STATUS     current
    DESCRIPTION
    "
    Name      : Source 1
    Menu Path : /Audio/Audio 6
    Details   : Specifies audio source (pair) for this codec.
    "
::= { enc1Params 424 }

enc1P424source1Entry OBJECT-TYPE
    SYNTAX Enc1P424source1Entry
    MAX-ACCESS not-accessible
    STATUS     current
    DESCRIPTION
    "Table Entry for Source 1"
    INDEX { slotId }
::= { enc1P424source1Table 1 }

Enc1P424source1Entry ::= SEQUENCE {
    enc1P424source1Value    Enc1E70enumObj
}

enc1P424source1Value OBJECT-TYPE
    SYNTAX     Enc1E70enumObj
    MAX-ACCESS read-write
    STATUS     current
    DESCRIPTION
    "Specifies audio source (pair) for this codec."
::= { enc1P424source1Entry 1 }

enc1P425source2Table OBJECT-TYPE
    SYNTAX SEQUENCE OF Enc1P425source2Entry
    MAX-ACCESS not-accessible
    STATUS     current
    DESCRIPTION
    "
    Name      : Source 2
    Menu Path : /Audio/Audio 6
    Details   : Specifies second audio source (pair) for this multichannel codec.
    "
::= { enc1Params 425 }

enc1P425source2Entry OBJECT-TYPE
    SYNTAX Enc1P425source2Entry
    MAX-ACCESS not-accessible
    STATUS     current
    DESCRIPTION
    "Table Entry for Source 2"
    INDEX { slotId }
::= { enc1P425source2Table 1 }

Enc1P425source2Entry ::= SEQUENCE {
    enc1P425source2Value    Enc1E70enumObj
}

enc1P425source2Value OBJECT-TYPE
    SYNTAX     Enc1E70enumObj
    MAX-ACCESS read-write
    STATUS     current
    DESCRIPTION
    "Specifies second audio source (pair) for this multichannel codec."
::= { enc1P425source2Entry 1 }

enc1P426source3Table OBJECT-TYPE
    SYNTAX SEQUENCE OF Enc1P426source3Entry
    MAX-ACCESS not-accessible
    STATUS     current
    DESCRIPTION
    "
    Name      : Source 3
    Menu Path : /Audio/Audio 6
    Details   : Specifies third audio source (pair) for this multichannel codec.
    "
::= { enc1Params 426 }

enc1P426source3Entry OBJECT-TYPE
    SYNTAX Enc1P426source3Entry
    MAX-ACCESS not-accessible
    STATUS     current
    DESCRIPTION
    "Table Entry for Source 3"
    INDEX { slotId }
::= { enc1P426source3Table 1 }

Enc1P426source3Entry ::= SEQUENCE {
    enc1P426source3Value    Enc1E70enumObj
}

enc1P426source3Value OBJECT-TYPE
    SYNTAX     Enc1E70enumObj
    MAX-ACCESS read-write
    STATUS     current
    DESCRIPTION
    "Specifies third audio source (pair) for this multichannel codec."
::= { enc1P426source3Entry 1 }

enc1P427source4Table OBJECT-TYPE
    SYNTAX SEQUENCE OF Enc1P427source4Entry
    MAX-ACCESS not-accessible
    STATUS     current
    DESCRIPTION
    "
    Name      : Source 4
    Menu Path : /Audio/Audio 6
    Details   : Specifies fourth audio source (pair) for this multichannel codec.
    "
::= { enc1Params 427 }

enc1P427source4Entry OBJECT-TYPE
    SYNTAX Enc1P427source4Entry
    MAX-ACCESS not-accessible
    STATUS     current
    DESCRIPTION
    "Table Entry for Source 4"
    INDEX { slotId }
::= { enc1P427source4Table 1 }

Enc1P427source4Entry ::= SEQUENCE {
    enc1P427source4Value    Enc1E70enumObj
}

enc1P427source4Value OBJECT-TYPE
    SYNTAX     Enc1E70enumObj
    MAX-ACCESS read-write
    STATUS     current
    DESCRIPTION
    "Specifies fourth audio source (pair) for this multichannel codec."
::= { enc1P427source4Entry 1 }

enc1P428preProcessingTable OBJECT-TYPE
    SYNTAX SEQUENCE OF Enc1P428preProcessingEntry
    MAX-ACCESS not-accessible
    STATUS     current
    DESCRIPTION
    "
    Name      : Pre Processing
    Menu Path : Not Applicable
    Details   : Specifies special processing for audio channel
    "
::= { enc1Params 428 }

enc1P428preProcessingEntry OBJECT-TYPE
    SYNTAX Enc1P428preProcessingEntry
    MAX-ACCESS not-accessible
    STATUS     current
    DESCRIPTION
    "Table Entry for Pre Processing"
    INDEX { slotId }
::= { enc1P428preProcessingTable 1 }

Enc1P428preProcessingEntry ::= SEQUENCE {
    enc1P428preProcessingValue    Enc1E72enumObj
}

enc1P428preProcessingValue OBJECT-TYPE
    SYNTAX     Enc1E72enumObj
    MAX-ACCESS read-write
    STATUS     current
    DESCRIPTION
    "Specifies special processing for audio channel"
::= { enc1P428preProcessingEntry 1 }

enc1P429delayTable OBJECT-TYPE
    SYNTAX SEQUENCE OF Enc1P429delayEntry
    MAX-ACCESS not-accessible
    STATUS     current
    DESCRIPTION
    "
    Name      : Delay
    Menu Path : /Audio/Audio 6
    Units     : msec
    Precision : 0
    Low Range : -500
    High Range: 500
    Details   : Specify an additional audio delay, relative to video delay.

     NOTE: Precision/Units/Ranges represent the state of the
           parameter during the MIB generation, and does not
           neccessary reflect the current state of the parameter
    "
::= { enc1Params 429 }

enc1P429delayEntry OBJECT-TYPE
    SYNTAX Enc1P429delayEntry
    MAX-ACCESS not-accessible
    STATUS     current
    DESCRIPTION
    "Table Entry for Delay"
    INDEX { slotId }
::= { enc1P429delayTable 1 }

Enc1P429delayEntry ::= SEQUENCE {
    enc1P429delayValue    INTEGER
}

enc1P429delayValue OBJECT-TYPE
    SYNTAX     INTEGER
    MAX-ACCESS read-write
    STATUS     current
    DESCRIPTION
    "Specify an additional audio delay, relative to video delay."
::= { enc1P429delayEntry 1 }

enc1P430gainTable OBJECT-TYPE
    SYNTAX SEQUENCE OF Enc1P430gainEntry
    MAX-ACCESS not-accessible
    STATUS     current
    DESCRIPTION
    "
    Name      : Gain
    Menu Path : /Audio/Audio 6
    Units     : dB
    Precision : 1
    Low Range : -800
    High Range: 400
    Details   : Apply a gain (or attenuation) to all source channels.

     NOTE: Precision/Units/Ranges represent the state of the
           parameter during the MIB generation, and does not
           neccessary reflect the current state of the parameter
    "
::= { enc1Params 430 }

enc1P430gainEntry OBJECT-TYPE
    SYNTAX Enc1P430gainEntry
    MAX-ACCESS not-accessible
    STATUS     current
    DESCRIPTION
    "Table Entry for Gain"
    INDEX { slotId }
::= { enc1P430gainTable 1 }

Enc1P430gainEntry ::= SEQUENCE {
    enc1P430gainValue    INTEGER
}

enc1P430gainValue OBJECT-TYPE
    SYNTAX     INTEGER
    MAX-ACCESS read-write
    STATUS     current
    DESCRIPTION
    "Apply a gain (or attenuation) to all source channels."
::= { enc1P430gainEntry 1 }

enc1P432deemphasisTable OBJECT-TYPE
    SYNTAX SEQUENCE OF Enc1P432deemphasisEntry
    MAX-ACCESS not-accessible
    STATUS     current
    DESCRIPTION
    "
    Name      : Deemphasis
    Menu Path : /Audio/Audio 6
    Details   : Dolby Digital: applies deemphasis, Mpeg: indicates presence of preemphasis. Auto uses AES channel block indication.
    "
::= { enc1Params 432 }

enc1P432deemphasisEntry OBJECT-TYPE
    SYNTAX Enc1P432deemphasisEntry
    MAX-ACCESS not-accessible
    STATUS     current
    DESCRIPTION
    "Table Entry for Deemphasis"
    INDEX { slotId }
::= { enc1P432deemphasisTable 1 }

Enc1P432deemphasisEntry ::= SEQUENCE {
    enc1P432deemphasisValue    Enc1E2enumObj
}

enc1P432deemphasisValue OBJECT-TYPE
    SYNTAX     Enc1E2enumObj
    MAX-ACCESS read-write
    STATUS     current
    DESCRIPTION
    "Dolby Digital: applies deemphasis, Mpeg: indicates presence of preemphasis. Auto uses AES channel block indication."
::= { enc1P432deemphasisEntry 1 }

enc1P433modeTable OBJECT-TYPE
    SYNTAX SEQUENCE OF Enc1P433modeEntry
    MAX-ACCESS not-accessible
    STATUS     current
    DESCRIPTION
    "
    Name      : Mode
    Menu Path : /Audio/Audio 6
    Details   : Specifies the audio coding mode (maximum channel usage)
    "
::= { enc1Params 433 }

enc1P433modeEntry OBJECT-TYPE
    SYNTAX Enc1P433modeEntry
    MAX-ACCESS not-accessible
    STATUS     current
    DESCRIPTION
    "Table Entry for Mode"
    INDEX { slotId }
::= { enc1P433modeTable 1 }

Enc1P433modeEntry ::= SEQUENCE {
    enc1P433modeValue    Enc1E194enumObj
}

enc1P433modeValue OBJECT-TYPE
    SYNTAX     Enc1E194enumObj
    MAX-ACCESS read-write
    STATUS     current
    DESCRIPTION
    "Specifies the audio coding mode (maximum channel usage)"
::= { enc1P433modeEntry 1 }

enc1P434audioFormatTable OBJECT-TYPE
    SYNTAX SEQUENCE OF Enc1P434audioFormatEntry
    MAX-ACCESS not-accessible
    STATUS     current
    DESCRIPTION
    "
    Name      : Audio Format
    Menu Path : /Audio/Audio 6
    Details   : Specifies the audio encoding standard and bitrate.
    "
::= { enc1Params 434 }

enc1P434audioFormatEntry OBJECT-TYPE
    SYNTAX Enc1P434audioFormatEntry
    MAX-ACCESS not-accessible
    STATUS     current
    DESCRIPTION
    "Table Entry for Audio Format"
    INDEX { slotId }
::= { enc1P434audioFormatTable 1 }

Enc1P434audioFormatEntry ::= SEQUENCE {
    enc1P434audioFormatValue    Enc1E73enumObj
}

enc1P434audioFormatValue OBJECT-TYPE
    SYNTAX     Enc1E73enumObj
    MAX-ACCESS read-write
    STATUS     current
    DESCRIPTION
    "Specifies the audio encoding standard and bitrate."
::= { enc1P434audioFormatEntry 1 }

enc1P435languageCodeTable OBJECT-TYPE
    SYNTAX SEQUENCE OF Enc1P435languageCodeEntry
    MAX-ACCESS not-accessible
    STATUS     current
    DESCRIPTION
    "
    Name      : Language Code
    Menu Path : /Audio/Audio 6
    Details   : Specifies the ISO 639-2 (three letter) language code.
    "
::= { enc1Params 435 }

enc1P435languageCodeEntry OBJECT-TYPE
    SYNTAX Enc1P435languageCodeEntry
    MAX-ACCESS not-accessible
    STATUS     current
    DESCRIPTION
    "Table Entry for Language Code"
    INDEX { slotId }
::= { enc1P435languageCodeTable 1 }

Enc1P435languageCodeEntry ::= SEQUENCE {
    enc1P435languageCodeValue    DisplayString
}

enc1P435languageCodeValue OBJECT-TYPE
    SYNTAX     DisplayString
    MAX-ACCESS read-write
    STATUS     current
    DESCRIPTION
    "Specifies the ISO 639-2 (three letter) language code."
::= { enc1P435languageCodeEntry 1 }

enc1P436enableOutputTable OBJECT-TYPE
    SYNTAX SEQUENCE OF Enc1P436enableOutputEntry
    MAX-ACCESS not-accessible
    STATUS     current
    DESCRIPTION
    "
    Name      : Enable Output
    Menu Path : /Audio/Audio 6
    Details   : Specifies which encoded program carries this audio.
    "
::= { enc1Params 436 }

enc1P436enableOutputEntry OBJECT-TYPE
    SYNTAX Enc1P436enableOutputEntry
    MAX-ACCESS not-accessible
    STATUS     current
    DESCRIPTION
    "Table Entry for Enable Output"
    INDEX { slotId }
::= { enc1P436enableOutputTable 1 }

Enc1P436enableOutputEntry ::= SEQUENCE {
    enc1P436enableOutputValue    Enc1E82enumObj
}

enc1P436enableOutputValue OBJECT-TYPE
    SYNTAX     Enc1E82enumObj
    MAX-ACCESS read-write
    STATUS     current
    DESCRIPTION
    "Specifies which encoded program carries this audio."
::= { enc1P436enableOutputEntry 1 }

enc1P437metadataSourceTable OBJECT-TYPE
    SYNTAX SEQUENCE OF Enc1P437metadataSourceEntry
    MAX-ACCESS not-accessible
    STATUS     current
    DESCRIPTION
    "
    Name      : Metadata Source
    Menu Path : /Audio/Audio 6/Metadata
    Details   : Specifies source for Dolby audio metadata
    "
::= { enc1Params 437 }

enc1P437metadataSourceEntry OBJECT-TYPE
    SYNTAX Enc1P437metadataSourceEntry
    MAX-ACCESS not-accessible
    STATUS     current
    DESCRIPTION
    "Table Entry for Metadata Source"
    INDEX { slotId }
::= { enc1P437metadataSourceTable 1 }

Enc1P437metadataSourceEntry ::= SEQUENCE {
    enc1P437metadataSourceValue    Enc1E83enumObj
}

enc1P437metadataSourceValue OBJECT-TYPE
    SYNTAX     Enc1E83enumObj
    MAX-ACCESS read-write
    STATUS     current
    DESCRIPTION
    "Specifies source for Dolby audio metadata"
::= { enc1P437metadataSourceEntry 1 }

enc1P438metadataReversionModeTable OBJECT-TYPE
    SYNTAX SEQUENCE OF Enc1P438metadataReversionModeEntry
    MAX-ACCESS not-accessible
    STATUS     current
    DESCRIPTION
    "
    Name      : Metadata Reversion Mode
    Menu Path : /Audio/Audio 6/Metadata
    Details   : Specifies response to interruption in metadata source
    "
::= { enc1Params 438 }

enc1P438metadataReversionModeEntry OBJECT-TYPE
    SYNTAX Enc1P438metadataReversionModeEntry
    MAX-ACCESS not-accessible
    STATUS     current
    DESCRIPTION
    "Table Entry for Metadata Reversion Mode"
    INDEX { slotId }
::= { enc1P438metadataReversionModeTable 1 }

Enc1P438metadataReversionModeEntry ::= SEQUENCE {
    enc1P438metadataReversionModeValue    Enc1E84enumObj
}

enc1P438metadataReversionModeValue OBJECT-TYPE
    SYNTAX     Enc1E84enumObj
    MAX-ACCESS read-write
    STATUS     current
    DESCRIPTION
    "Specifies response to interruption in metadata source"
::= { enc1P438metadataReversionModeEntry 1 }

enc1P439pssignalingTable OBJECT-TYPE
    SYNTAX SEQUENCE OF Enc1P439pssignalingEntry
    MAX-ACCESS not-accessible
    STATUS     current
    DESCRIPTION
    "
    Name      : PS Signaling
    Menu Path : /Audio/Audio 6/AAC
    Details   : Specifies the parametric stereo signaling for AAC audio encoding.
    "
::= { enc1Params 439 }

enc1P439pssignalingEntry OBJECT-TYPE
    SYNTAX Enc1P439pssignalingEntry
    MAX-ACCESS not-accessible
    STATUS     current
    DESCRIPTION
    "Table Entry for PS Signaling"
    INDEX { slotId }
::= { enc1P439pssignalingTable 1 }

Enc1P439pssignalingEntry ::= SEQUENCE {
    enc1P439pssignalingValue    Enc1E76enumObj
}

enc1P439pssignalingValue OBJECT-TYPE
    SYNTAX     Enc1E76enumObj
    MAX-ACCESS read-write
    STATUS     current
    DESCRIPTION
    "Specifies the parametric stereo signaling for AAC audio encoding."
::= { enc1P439pssignalingEntry 1 }

enc1P440sbrsignalingTable OBJECT-TYPE
    SYNTAX SEQUENCE OF Enc1P440sbrsignalingEntry
    MAX-ACCESS not-accessible
    STATUS     current
    DESCRIPTION
    "
    Name      : SBR Signaling
    Menu Path : /Audio/Audio 6/AAC
    Details   : Specifies the SBR signaling for AAC audio encoding.
    "
::= { enc1Params 440 }

enc1P440sbrsignalingEntry OBJECT-TYPE
    SYNTAX Enc1P440sbrsignalingEntry
    MAX-ACCESS not-accessible
    STATUS     current
    DESCRIPTION
    "Table Entry for SBR Signaling"
    INDEX { slotId }
::= { enc1P440sbrsignalingTable 1 }

Enc1P440sbrsignalingEntry ::= SEQUENCE {
    enc1P440sbrsignalingValue    Enc1E77enumObj
}

enc1P440sbrsignalingValue OBJECT-TYPE
    SYNTAX     Enc1E77enumObj
    MAX-ACCESS read-write
    STATUS     current
    DESCRIPTION
    "Specifies the SBR signaling for AAC audio encoding."
::= { enc1P440sbrsignalingEntry 1 }

enc1P441transportTable OBJECT-TYPE
    SYNTAX SEQUENCE OF Enc1P441transportEntry
    MAX-ACCESS not-accessible
    STATUS     current
    DESCRIPTION
    "
    Name      : Transport
    Menu Path : /Audio/Audio 6/AAC
    Details   : Specifies the transport layer (framing) for AAC audio encoding.
    "
::= { enc1Params 441 }

enc1P441transportEntry OBJECT-TYPE
    SYNTAX Enc1P441transportEntry
    MAX-ACCESS not-accessible
    STATUS     current
    DESCRIPTION
    "Table Entry for Transport"
    INDEX { slotId }
::= { enc1P441transportTable 1 }

Enc1P441transportEntry ::= SEQUENCE {
    enc1P441transportValue    Enc1E78enumObj
}

enc1P441transportValue OBJECT-TYPE
    SYNTAX     Enc1E78enumObj
    MAX-ACCESS read-write
    STATUS     current
    DESCRIPTION
    "Specifies the transport layer (framing) for AAC audio encoding."
::= { enc1P441transportEntry 1 }

enc1P443programConfigurationTable OBJECT-TYPE
    SYNTAX SEQUENCE OF Enc1P443programConfigurationEntry
    MAX-ACCESS not-accessible
    STATUS     current
    DESCRIPTION
    "
    Name      : Program Configuration
    Menu Path : /Audio/Audio 6/Dolby E Encoder
    Details   : Determines how audio channels are grouped into programs within a Dolby E bitstream.
    "
::= { enc1Params 443 }

enc1P443programConfigurationEntry OBJECT-TYPE
    SYNTAX Enc1P443programConfigurationEntry
    MAX-ACCESS not-accessible
    STATUS     current
    DESCRIPTION
    "Table Entry for Program Configuration"
    INDEX { slotId }
::= { enc1P443programConfigurationTable 1 }

Enc1P443programConfigurationEntry ::= SEQUENCE {
    enc1P443programConfigurationValue    Enc1E195enumObj
}

enc1P443programConfigurationValue OBJECT-TYPE
    SYNTAX     Enc1E195enumObj
    MAX-ACCESS read-write
    STATUS     current
    DESCRIPTION
    "Determines how audio channels are grouped into programs within a Dolby E bitstream."
::= { enc1P443programConfigurationEntry 1 }

enc1P473avsyncAdjustCountTable OBJECT-TYPE
    SYNTAX SEQUENCE OF Enc1P473avsyncAdjustCountEntry
    MAX-ACCESS not-accessible
    STATUS     current
    DESCRIPTION
    "
    Name      : AV Sync Adjust Count
    Menu Path : /Audio/Audio 6/Status
    Units     : 
    Precision : 0
    Low Range : 0
    High Range: -1
    Details   : Displays the count of audio/video sync adjustments (lipsync discontinuities).

     NOTE: Precision/Units/Ranges represent the state of the
           parameter during the MIB generation, and does not
           neccessary reflect the current state of the parameter
    "
::= { enc1Params 473 }

enc1P473avsyncAdjustCountEntry OBJECT-TYPE
    SYNTAX Enc1P473avsyncAdjustCountEntry
    MAX-ACCESS not-accessible
    STATUS     current
    DESCRIPTION
    "Table Entry for AV Sync Adjust Count"
    INDEX { slotId }
::= { enc1P473avsyncAdjustCountTable 1 }

Enc1P473avsyncAdjustCountEntry ::= SEQUENCE {
    enc1P473avsyncAdjustCountValue    INTEGER
}

enc1P473avsyncAdjustCountValue OBJECT-TYPE
    SYNTAX     INTEGER
    MAX-ACCESS read-only
    STATUS     current
    DESCRIPTION
    "Displays the count of audio/video sync adjustments (lipsync discontinuities)."
::= { enc1P473avsyncAdjustCountEntry 1 }

enc1P474pmtpositionTable OBJECT-TYPE
    SYNTAX SEQUENCE OF Enc1P474pmtpositionEntry
    MAX-ACCESS not-accessible
    STATUS     current
    DESCRIPTION
    "
    Name      : PMT Position
    Menu Path : /Audio/Audio 6/Status
    Units     : 
    Precision : 0
    Low Range : 0
    High Range: 8
    Details   : Displays the relative position in the PMT of this audio stream

     NOTE: Precision/Units/Ranges represent the state of the
           parameter during the MIB generation, and does not
           neccessary reflect the current state of the parameter
    "
::= { enc1Params 474 }

enc1P474pmtpositionEntry OBJECT-TYPE
    SYNTAX Enc1P474pmtpositionEntry
    MAX-ACCESS not-accessible
    STATUS     current
    DESCRIPTION
    "Table Entry for PMT Position"
    INDEX { slotId }
::= { enc1P474pmtpositionTable 1 }

Enc1P474pmtpositionEntry ::= SEQUENCE {
    enc1P474pmtpositionValue    INTEGER
}

enc1P474pmtpositionValue OBJECT-TYPE
    SYNTAX     INTEGER
    MAX-ACCESS read-only
    STATUS     current
    DESCRIPTION
    "Displays the relative position in the PMT of this audio stream"
::= { enc1P474pmtpositionEntry 1 }

enc1P476lossofSignalTable OBJECT-TYPE
    SYNTAX SEQUENCE OF Enc1P476lossofSignalEntry
    MAX-ACCESS not-accessible
    STATUS     current
    DESCRIPTION
    "
    Name      : Loss of Signal
    Menu Path : /Audio/Audio 6/Status
    Details   : Indicates loss of a selected source signal.
    "
::= { enc1Params 476 }

enc1P476lossofSignalEntry OBJECT-TYPE
    SYNTAX Enc1P476lossofSignalEntry
    MAX-ACCESS not-accessible
    STATUS     current
    DESCRIPTION
    "Table Entry for Loss of Signal"
    INDEX { slotId }
::= { enc1P476lossofSignalTable 1 }

Enc1P476lossofSignalEntry ::= SEQUENCE {
    enc1P476lossofSignalValue    Enc1E5enumObj
}

enc1P476lossofSignalValue OBJECT-TYPE
    SYNTAX     Enc1E5enumObj
    MAX-ACCESS read-only
    STATUS     current
    DESCRIPTION
    "Indicates loss of a selected source signal."
::= { enc1P476lossofSignalEntry 1 }

enc1P477source1Table OBJECT-TYPE
    SYNTAX SEQUENCE OF Enc1P477source1Entry
    MAX-ACCESS not-accessible
    STATUS     current
    DESCRIPTION
    "
    Name      : Source 1
    Menu Path : /Audio/Audio 7
    Details   : Specifies audio source (pair) for this codec.
    "
::= { enc1Params 477 }

enc1P477source1Entry OBJECT-TYPE
    SYNTAX Enc1P477source1Entry
    MAX-ACCESS not-accessible
    STATUS     current
    DESCRIPTION
    "Table Entry for Source 1"
    INDEX { slotId }
::= { enc1P477source1Table 1 }

Enc1P477source1Entry ::= SEQUENCE {
    enc1P477source1Value    Enc1E70enumObj
}

enc1P477source1Value OBJECT-TYPE
    SYNTAX     Enc1E70enumObj
    MAX-ACCESS read-write
    STATUS     current
    DESCRIPTION
    "Specifies audio source (pair) for this codec."
::= { enc1P477source1Entry 1 }

enc1P478source2Table OBJECT-TYPE
    SYNTAX SEQUENCE OF Enc1P478source2Entry
    MAX-ACCESS not-accessible
    STATUS     current
    DESCRIPTION
    "
    Name      : Source 2
    Menu Path : /Audio/Audio 7
    Details   : Specifies second audio source (pair) for this multichannel codec.
    "
::= { enc1Params 478 }

enc1P478source2Entry OBJECT-TYPE
    SYNTAX Enc1P478source2Entry
    MAX-ACCESS not-accessible
    STATUS     current
    DESCRIPTION
    "Table Entry for Source 2"
    INDEX { slotId }
::= { enc1P478source2Table 1 }

Enc1P478source2Entry ::= SEQUENCE {
    enc1P478source2Value    Enc1E70enumObj
}

enc1P478source2Value OBJECT-TYPE
    SYNTAX     Enc1E70enumObj
    MAX-ACCESS read-write
    STATUS     current
    DESCRIPTION
    "Specifies second audio source (pair) for this multichannel codec."
::= { enc1P478source2Entry 1 }

enc1P479source3Table OBJECT-TYPE
    SYNTAX SEQUENCE OF Enc1P479source3Entry
    MAX-ACCESS not-accessible
    STATUS     current
    DESCRIPTION
    "
    Name      : Source 3
    Menu Path : /Audio/Audio 7
    Details   : Specifies third audio source (pair) for this multichannel codec.
    "
::= { enc1Params 479 }

enc1P479source3Entry OBJECT-TYPE
    SYNTAX Enc1P479source3Entry
    MAX-ACCESS not-accessible
    STATUS     current
    DESCRIPTION
    "Table Entry for Source 3"
    INDEX { slotId }
::= { enc1P479source3Table 1 }

Enc1P479source3Entry ::= SEQUENCE {
    enc1P479source3Value    Enc1E70enumObj
}

enc1P479source3Value OBJECT-TYPE
    SYNTAX     Enc1E70enumObj
    MAX-ACCESS read-write
    STATUS     current
    DESCRIPTION
    "Specifies third audio source (pair) for this multichannel codec."
::= { enc1P479source3Entry 1 }

enc1P480source4Table OBJECT-TYPE
    SYNTAX SEQUENCE OF Enc1P480source4Entry
    MAX-ACCESS not-accessible
    STATUS     current
    DESCRIPTION
    "
    Name      : Source 4
    Menu Path : /Audio/Audio 7
    Details   : Specifies fourth audio source (pair) for this multichannel codec.
    "
::= { enc1Params 480 }

enc1P480source4Entry OBJECT-TYPE
    SYNTAX Enc1P480source4Entry
    MAX-ACCESS not-accessible
    STATUS     current
    DESCRIPTION
    "Table Entry for Source 4"
    INDEX { slotId }
::= { enc1P480source4Table 1 }

Enc1P480source4Entry ::= SEQUENCE {
    enc1P480source4Value    Enc1E70enumObj
}

enc1P480source4Value OBJECT-TYPE
    SYNTAX     Enc1E70enumObj
    MAX-ACCESS read-write
    STATUS     current
    DESCRIPTION
    "Specifies fourth audio source (pair) for this multichannel codec."
::= { enc1P480source4Entry 1 }

enc1P481preProcessingTable OBJECT-TYPE
    SYNTAX SEQUENCE OF Enc1P481preProcessingEntry
    MAX-ACCESS not-accessible
    STATUS     current
    DESCRIPTION
    "
    Name      : Pre Processing
    Menu Path : Not Applicable
    Details   : Specifies special processing for audio channel
    "
::= { enc1Params 481 }

enc1P481preProcessingEntry OBJECT-TYPE
    SYNTAX Enc1P481preProcessingEntry
    MAX-ACCESS not-accessible
    STATUS     current
    DESCRIPTION
    "Table Entry for Pre Processing"
    INDEX { slotId }
::= { enc1P481preProcessingTable 1 }

Enc1P481preProcessingEntry ::= SEQUENCE {
    enc1P481preProcessingValue    Enc1E72enumObj
}

enc1P481preProcessingValue OBJECT-TYPE
    SYNTAX     Enc1E72enumObj
    MAX-ACCESS read-write
    STATUS     current
    DESCRIPTION
    "Specifies special processing for audio channel"
::= { enc1P481preProcessingEntry 1 }

enc1P482delayTable OBJECT-TYPE
    SYNTAX SEQUENCE OF Enc1P482delayEntry
    MAX-ACCESS not-accessible
    STATUS     current
    DESCRIPTION
    "
    Name      : Delay
    Menu Path : /Audio/Audio 7
    Units     : msec
    Precision : 0
    Low Range : -500
    High Range: 500
    Details   : Specify an additional audio delay, relative to video delay.

     NOTE: Precision/Units/Ranges represent the state of the
           parameter during the MIB generation, and does not
           neccessary reflect the current state of the parameter
    "
::= { enc1Params 482 }

enc1P482delayEntry OBJECT-TYPE
    SYNTAX Enc1P482delayEntry
    MAX-ACCESS not-accessible
    STATUS     current
    DESCRIPTION
    "Table Entry for Delay"
    INDEX { slotId }
::= { enc1P482delayTable 1 }

Enc1P482delayEntry ::= SEQUENCE {
    enc1P482delayValue    INTEGER
}

enc1P482delayValue OBJECT-TYPE
    SYNTAX     INTEGER
    MAX-ACCESS read-write
    STATUS     current
    DESCRIPTION
    "Specify an additional audio delay, relative to video delay."
::= { enc1P482delayEntry 1 }

enc1P483gainTable OBJECT-TYPE
    SYNTAX SEQUENCE OF Enc1P483gainEntry
    MAX-ACCESS not-accessible
    STATUS     current
    DESCRIPTION
    "
    Name      : Gain
    Menu Path : /Audio/Audio 7
    Units     : dB
    Precision : 1
    Low Range : -800
    High Range: 400
    Details   : Apply a gain (or attenuation) to all source channels.

     NOTE: Precision/Units/Ranges represent the state of the
           parameter during the MIB generation, and does not
           neccessary reflect the current state of the parameter
    "
::= { enc1Params 483 }

enc1P483gainEntry OBJECT-TYPE
    SYNTAX Enc1P483gainEntry
    MAX-ACCESS not-accessible
    STATUS     current
    DESCRIPTION
    "Table Entry for Gain"
    INDEX { slotId }
::= { enc1P483gainTable 1 }

Enc1P483gainEntry ::= SEQUENCE {
    enc1P483gainValue    INTEGER
}

enc1P483gainValue OBJECT-TYPE
    SYNTAX     INTEGER
    MAX-ACCESS read-write
    STATUS     current
    DESCRIPTION
    "Apply a gain (or attenuation) to all source channels."
::= { enc1P483gainEntry 1 }

enc1P485deemphasisTable OBJECT-TYPE
    SYNTAX SEQUENCE OF Enc1P485deemphasisEntry
    MAX-ACCESS not-accessible
    STATUS     current
    DESCRIPTION
    "
    Name      : Deemphasis
    Menu Path : /Audio/Audio 7
    Details   : Dolby Digital: applies deemphasis, Mpeg: indicates presence of preemphasis. Auto uses AES channel block indication.
    "
::= { enc1Params 485 }

enc1P485deemphasisEntry OBJECT-TYPE
    SYNTAX Enc1P485deemphasisEntry
    MAX-ACCESS not-accessible
    STATUS     current
    DESCRIPTION
    "Table Entry for Deemphasis"
    INDEX { slotId }
::= { enc1P485deemphasisTable 1 }

Enc1P485deemphasisEntry ::= SEQUENCE {
    enc1P485deemphasisValue    Enc1E2enumObj
}

enc1P485deemphasisValue OBJECT-TYPE
    SYNTAX     Enc1E2enumObj
    MAX-ACCESS read-write
    STATUS     current
    DESCRIPTION
    "Dolby Digital: applies deemphasis, Mpeg: indicates presence of preemphasis. Auto uses AES channel block indication."
::= { enc1P485deemphasisEntry 1 }

enc1P486modeTable OBJECT-TYPE
    SYNTAX SEQUENCE OF Enc1P486modeEntry
    MAX-ACCESS not-accessible
    STATUS     current
    DESCRIPTION
    "
    Name      : Mode
    Menu Path : /Audio/Audio 7
    Details   : Specifies the audio coding mode (maximum channel usage)
    "
::= { enc1Params 486 }

enc1P486modeEntry OBJECT-TYPE
    SYNTAX Enc1P486modeEntry
    MAX-ACCESS not-accessible
    STATUS     current
    DESCRIPTION
    "Table Entry for Mode"
    INDEX { slotId }
::= { enc1P486modeTable 1 }

Enc1P486modeEntry ::= SEQUENCE {
    enc1P486modeValue    Enc1E197enumObj
}

enc1P486modeValue OBJECT-TYPE
    SYNTAX     Enc1E197enumObj
    MAX-ACCESS read-write
    STATUS     current
    DESCRIPTION
    "Specifies the audio coding mode (maximum channel usage)"
::= { enc1P486modeEntry 1 }

enc1P487audioFormatTable OBJECT-TYPE
    SYNTAX SEQUENCE OF Enc1P487audioFormatEntry
    MAX-ACCESS not-accessible
    STATUS     current
    DESCRIPTION
    "
    Name      : Audio Format
    Menu Path : /Audio/Audio 7
    Details   : Specifies the audio encoding standard and bitrate.
    "
::= { enc1Params 487 }

enc1P487audioFormatEntry OBJECT-TYPE
    SYNTAX Enc1P487audioFormatEntry
    MAX-ACCESS not-accessible
    STATUS     current
    DESCRIPTION
    "Table Entry for Audio Format"
    INDEX { slotId }
::= { enc1P487audioFormatTable 1 }

Enc1P487audioFormatEntry ::= SEQUENCE {
    enc1P487audioFormatValue    Enc1E73enumObj
}

enc1P487audioFormatValue OBJECT-TYPE
    SYNTAX     Enc1E73enumObj
    MAX-ACCESS read-write
    STATUS     current
    DESCRIPTION
    "Specifies the audio encoding standard and bitrate."
::= { enc1P487audioFormatEntry 1 }

enc1P488languageCodeTable OBJECT-TYPE
    SYNTAX SEQUENCE OF Enc1P488languageCodeEntry
    MAX-ACCESS not-accessible
    STATUS     current
    DESCRIPTION
    "
    Name      : Language Code
    Menu Path : /Audio/Audio 7
    Details   : Specifies the ISO 639-2 (three letter) language code.
    "
::= { enc1Params 488 }

enc1P488languageCodeEntry OBJECT-TYPE
    SYNTAX Enc1P488languageCodeEntry
    MAX-ACCESS not-accessible
    STATUS     current
    DESCRIPTION
    "Table Entry for Language Code"
    INDEX { slotId }
::= { enc1P488languageCodeTable 1 }

Enc1P488languageCodeEntry ::= SEQUENCE {
    enc1P488languageCodeValue    DisplayString
}

enc1P488languageCodeValue OBJECT-TYPE
    SYNTAX     DisplayString
    MAX-ACCESS read-write
    STATUS     current
    DESCRIPTION
    "Specifies the ISO 639-2 (three letter) language code."
::= { enc1P488languageCodeEntry 1 }

enc1P489enableOutputTable OBJECT-TYPE
    SYNTAX SEQUENCE OF Enc1P489enableOutputEntry
    MAX-ACCESS not-accessible
    STATUS     current
    DESCRIPTION
    "
    Name      : Enable Output
    Menu Path : /Audio/Audio 7
    Details   : Specifies which encoded program carries this audio.
    "
::= { enc1Params 489 }

enc1P489enableOutputEntry OBJECT-TYPE
    SYNTAX Enc1P489enableOutputEntry
    MAX-ACCESS not-accessible
    STATUS     current
    DESCRIPTION
    "Table Entry for Enable Output"
    INDEX { slotId }
::= { enc1P489enableOutputTable 1 }

Enc1P489enableOutputEntry ::= SEQUENCE {
    enc1P489enableOutputValue    Enc1E82enumObj
}

enc1P489enableOutputValue OBJECT-TYPE
    SYNTAX     Enc1E82enumObj
    MAX-ACCESS read-write
    STATUS     current
    DESCRIPTION
    "Specifies which encoded program carries this audio."
::= { enc1P489enableOutputEntry 1 }

enc1P490metadataSourceTable OBJECT-TYPE
    SYNTAX SEQUENCE OF Enc1P490metadataSourceEntry
    MAX-ACCESS not-accessible
    STATUS     current
    DESCRIPTION
    "
    Name      : Metadata Source
    Menu Path : /Audio/Audio 7/Metadata
    Details   : Specifies source for Dolby audio metadata
    "
::= { enc1Params 490 }

enc1P490metadataSourceEntry OBJECT-TYPE
    SYNTAX Enc1P490metadataSourceEntry
    MAX-ACCESS not-accessible
    STATUS     current
    DESCRIPTION
    "Table Entry for Metadata Source"
    INDEX { slotId }
::= { enc1P490metadataSourceTable 1 }

Enc1P490metadataSourceEntry ::= SEQUENCE {
    enc1P490metadataSourceValue    Enc1E83enumObj
}

enc1P490metadataSourceValue OBJECT-TYPE
    SYNTAX     Enc1E83enumObj
    MAX-ACCESS read-write
    STATUS     current
    DESCRIPTION
    "Specifies source for Dolby audio metadata"
::= { enc1P490metadataSourceEntry 1 }

enc1P491metadataReversionModeTable OBJECT-TYPE
    SYNTAX SEQUENCE OF Enc1P491metadataReversionModeEntry
    MAX-ACCESS not-accessible
    STATUS     current
    DESCRIPTION
    "
    Name      : Metadata Reversion Mode
    Menu Path : /Audio/Audio 7/Metadata
    Details   : Specifies response to interruption in metadata source
    "
::= { enc1Params 491 }

enc1P491metadataReversionModeEntry OBJECT-TYPE
    SYNTAX Enc1P491metadataReversionModeEntry
    MAX-ACCESS not-accessible
    STATUS     current
    DESCRIPTION
    "Table Entry for Metadata Reversion Mode"
    INDEX { slotId }
::= { enc1P491metadataReversionModeTable 1 }

Enc1P491metadataReversionModeEntry ::= SEQUENCE {
    enc1P491metadataReversionModeValue    Enc1E84enumObj
}

enc1P491metadataReversionModeValue OBJECT-TYPE
    SYNTAX     Enc1E84enumObj
    MAX-ACCESS read-write
    STATUS     current
    DESCRIPTION
    "Specifies response to interruption in metadata source"
::= { enc1P491metadataReversionModeEntry 1 }

enc1P492pssignalingTable OBJECT-TYPE
    SYNTAX SEQUENCE OF Enc1P492pssignalingEntry
    MAX-ACCESS not-accessible
    STATUS     current
    DESCRIPTION
    "
    Name      : PS Signaling
    Menu Path : /Audio/Audio 7/AAC
    Details   : Specifies the parametric stereo signaling for AAC audio encoding.
    "
::= { enc1Params 492 }

enc1P492pssignalingEntry OBJECT-TYPE
    SYNTAX Enc1P492pssignalingEntry
    MAX-ACCESS not-accessible
    STATUS     current
    DESCRIPTION
    "Table Entry for PS Signaling"
    INDEX { slotId }
::= { enc1P492pssignalingTable 1 }

Enc1P492pssignalingEntry ::= SEQUENCE {
    enc1P492pssignalingValue    Enc1E76enumObj
}

enc1P492pssignalingValue OBJECT-TYPE
    SYNTAX     Enc1E76enumObj
    MAX-ACCESS read-write
    STATUS     current
    DESCRIPTION
    "Specifies the parametric stereo signaling for AAC audio encoding."
::= { enc1P492pssignalingEntry 1 }

enc1P493sbrsignalingTable OBJECT-TYPE
    SYNTAX SEQUENCE OF Enc1P493sbrsignalingEntry
    MAX-ACCESS not-accessible
    STATUS     current
    DESCRIPTION
    "
    Name      : SBR Signaling
    Menu Path : /Audio/Audio 7/AAC
    Details   : Specifies the SBR signaling for AAC audio encoding.
    "
::= { enc1Params 493 }

enc1P493sbrsignalingEntry OBJECT-TYPE
    SYNTAX Enc1P493sbrsignalingEntry
    MAX-ACCESS not-accessible
    STATUS     current
    DESCRIPTION
    "Table Entry for SBR Signaling"
    INDEX { slotId }
::= { enc1P493sbrsignalingTable 1 }

Enc1P493sbrsignalingEntry ::= SEQUENCE {
    enc1P493sbrsignalingValue    Enc1E77enumObj
}

enc1P493sbrsignalingValue OBJECT-TYPE
    SYNTAX     Enc1E77enumObj
    MAX-ACCESS read-write
    STATUS     current
    DESCRIPTION
    "Specifies the SBR signaling for AAC audio encoding."
::= { enc1P493sbrsignalingEntry 1 }

enc1P494transportTable OBJECT-TYPE
    SYNTAX SEQUENCE OF Enc1P494transportEntry
    MAX-ACCESS not-accessible
    STATUS     current
    DESCRIPTION
    "
    Name      : Transport
    Menu Path : /Audio/Audio 7/AAC
    Details   : Specifies the transport layer (framing) for AAC audio encoding.
    "
::= { enc1Params 494 }

enc1P494transportEntry OBJECT-TYPE
    SYNTAX Enc1P494transportEntry
    MAX-ACCESS not-accessible
    STATUS     current
    DESCRIPTION
    "Table Entry for Transport"
    INDEX { slotId }
::= { enc1P494transportTable 1 }

Enc1P494transportEntry ::= SEQUENCE {
    enc1P494transportValue    Enc1E78enumObj
}

enc1P494transportValue OBJECT-TYPE
    SYNTAX     Enc1E78enumObj
    MAX-ACCESS read-write
    STATUS     current
    DESCRIPTION
    "Specifies the transport layer (framing) for AAC audio encoding."
::= { enc1P494transportEntry 1 }

enc1P496programConfigurationTable OBJECT-TYPE
    SYNTAX SEQUENCE OF Enc1P496programConfigurationEntry
    MAX-ACCESS not-accessible
    STATUS     current
    DESCRIPTION
    "
    Name      : Program Configuration
    Menu Path : /Audio/Audio 7/Dolby E Encoder
    Details   : Determines how audio channels are grouped into programs within a Dolby E bitstream.
    "
::= { enc1Params 496 }

enc1P496programConfigurationEntry OBJECT-TYPE
    SYNTAX Enc1P496programConfigurationEntry
    MAX-ACCESS not-accessible
    STATUS     current
    DESCRIPTION
    "Table Entry for Program Configuration"
    INDEX { slotId }
::= { enc1P496programConfigurationTable 1 }

Enc1P496programConfigurationEntry ::= SEQUENCE {
    enc1P496programConfigurationValue    Enc1E198enumObj
}

enc1P496programConfigurationValue OBJECT-TYPE
    SYNTAX     Enc1E198enumObj
    MAX-ACCESS read-write
    STATUS     current
    DESCRIPTION
    "Determines how audio channels are grouped into programs within a Dolby E bitstream."
::= { enc1P496programConfigurationEntry 1 }

enc1P526avsyncAdjustCountTable OBJECT-TYPE
    SYNTAX SEQUENCE OF Enc1P526avsyncAdjustCountEntry
    MAX-ACCESS not-accessible
    STATUS     current
    DESCRIPTION
    "
    Name      : AV Sync Adjust Count
    Menu Path : /Audio/Audio 7/Status
    Units     : 
    Precision : 0
    Low Range : 0
    High Range: -1
    Details   : Displays the count of audio/video sync adjustments (lipsync discontinuities).

     NOTE: Precision/Units/Ranges represent the state of the
           parameter during the MIB generation, and does not
           neccessary reflect the current state of the parameter
    "
::= { enc1Params 526 }

enc1P526avsyncAdjustCountEntry OBJECT-TYPE
    SYNTAX Enc1P526avsyncAdjustCountEntry
    MAX-ACCESS not-accessible
    STATUS     current
    DESCRIPTION
    "Table Entry for AV Sync Adjust Count"
    INDEX { slotId }
::= { enc1P526avsyncAdjustCountTable 1 }

Enc1P526avsyncAdjustCountEntry ::= SEQUENCE {
    enc1P526avsyncAdjustCountValue    INTEGER
}

enc1P526avsyncAdjustCountValue OBJECT-TYPE
    SYNTAX     INTEGER
    MAX-ACCESS read-only
    STATUS     current
    DESCRIPTION
    "Displays the count of audio/video sync adjustments (lipsync discontinuities)."
::= { enc1P526avsyncAdjustCountEntry 1 }

enc1P527pmtpositionTable OBJECT-TYPE
    SYNTAX SEQUENCE OF Enc1P527pmtpositionEntry
    MAX-ACCESS not-accessible
    STATUS     current
    DESCRIPTION
    "
    Name      : PMT Position
    Menu Path : /Audio/Audio 7/Status
    Units     : 
    Precision : 0
    Low Range : 0
    High Range: 8
    Details   : Displays the relative position in the PMT of this audio stream

     NOTE: Precision/Units/Ranges represent the state of the
           parameter during the MIB generation, and does not
           neccessary reflect the current state of the parameter
    "
::= { enc1Params 527 }

enc1P527pmtpositionEntry OBJECT-TYPE
    SYNTAX Enc1P527pmtpositionEntry
    MAX-ACCESS not-accessible
    STATUS     current
    DESCRIPTION
    "Table Entry for PMT Position"
    INDEX { slotId }
::= { enc1P527pmtpositionTable 1 }

Enc1P527pmtpositionEntry ::= SEQUENCE {
    enc1P527pmtpositionValue    INTEGER
}

enc1P527pmtpositionValue OBJECT-TYPE
    SYNTAX     INTEGER
    MAX-ACCESS read-only
    STATUS     current
    DESCRIPTION
    "Displays the relative position in the PMT of this audio stream"
::= { enc1P527pmtpositionEntry 1 }

enc1P529lossofSignalTable OBJECT-TYPE
    SYNTAX SEQUENCE OF Enc1P529lossofSignalEntry
    MAX-ACCESS not-accessible
    STATUS     current
    DESCRIPTION
    "
    Name      : Loss of Signal
    Menu Path : /Audio/Audio 7/Status
    Details   : Indicates loss of a selected source signal.
    "
::= { enc1Params 529 }

enc1P529lossofSignalEntry OBJECT-TYPE
    SYNTAX Enc1P529lossofSignalEntry
    MAX-ACCESS not-accessible
    STATUS     current
    DESCRIPTION
    "Table Entry for Loss of Signal"
    INDEX { slotId }
::= { enc1P529lossofSignalTable 1 }

Enc1P529lossofSignalEntry ::= SEQUENCE {
    enc1P529lossofSignalValue    Enc1E5enumObj
}

enc1P529lossofSignalValue OBJECT-TYPE
    SYNTAX     Enc1E5enumObj
    MAX-ACCESS read-only
    STATUS     current
    DESCRIPTION
    "Indicates loss of a selected source signal."
::= { enc1P529lossofSignalEntry 1 }

enc1P530source1Table OBJECT-TYPE
    SYNTAX SEQUENCE OF Enc1P530source1Entry
    MAX-ACCESS not-accessible
    STATUS     current
    DESCRIPTION
    "
    Name      : Source 1
    Menu Path : /Audio/Audio 8
    Details   : Specifies audio source (pair) for this codec.
    "
::= { enc1Params 530 }

enc1P530source1Entry OBJECT-TYPE
    SYNTAX Enc1P530source1Entry
    MAX-ACCESS not-accessible
    STATUS     current
    DESCRIPTION
    "Table Entry for Source 1"
    INDEX { slotId }
::= { enc1P530source1Table 1 }

Enc1P530source1Entry ::= SEQUENCE {
    enc1P530source1Value    Enc1E70enumObj
}

enc1P530source1Value OBJECT-TYPE
    SYNTAX     Enc1E70enumObj
    MAX-ACCESS read-write
    STATUS     current
    DESCRIPTION
    "Specifies audio source (pair) for this codec."
::= { enc1P530source1Entry 1 }

enc1P531source2Table OBJECT-TYPE
    SYNTAX SEQUENCE OF Enc1P531source2Entry
    MAX-ACCESS not-accessible
    STATUS     current
    DESCRIPTION
    "
    Name      : Source 2
    Menu Path : /Audio/Audio 8
    Details   : Specifies second audio source (pair) for this multichannel codec.
    "
::= { enc1Params 531 }

enc1P531source2Entry OBJECT-TYPE
    SYNTAX Enc1P531source2Entry
    MAX-ACCESS not-accessible
    STATUS     current
    DESCRIPTION
    "Table Entry for Source 2"
    INDEX { slotId }
::= { enc1P531source2Table 1 }

Enc1P531source2Entry ::= SEQUENCE {
    enc1P531source2Value    Enc1E70enumObj
}

enc1P531source2Value OBJECT-TYPE
    SYNTAX     Enc1E70enumObj
    MAX-ACCESS read-write
    STATUS     current
    DESCRIPTION
    "Specifies second audio source (pair) for this multichannel codec."
::= { enc1P531source2Entry 1 }

enc1P532source3Table OBJECT-TYPE
    SYNTAX SEQUENCE OF Enc1P532source3Entry
    MAX-ACCESS not-accessible
    STATUS     current
    DESCRIPTION
    "
    Name      : Source 3
    Menu Path : /Audio/Audio 8
    Details   : Specifies third audio source (pair) for this multichannel codec.
    "
::= { enc1Params 532 }

enc1P532source3Entry OBJECT-TYPE
    SYNTAX Enc1P532source3Entry
    MAX-ACCESS not-accessible
    STATUS     current
    DESCRIPTION
    "Table Entry for Source 3"
    INDEX { slotId }
::= { enc1P532source3Table 1 }

Enc1P532source3Entry ::= SEQUENCE {
    enc1P532source3Value    Enc1E70enumObj
}

enc1P532source3Value OBJECT-TYPE
    SYNTAX     Enc1E70enumObj
    MAX-ACCESS read-write
    STATUS     current
    DESCRIPTION
    "Specifies third audio source (pair) for this multichannel codec."
::= { enc1P532source3Entry 1 }

enc1P533source4Table OBJECT-TYPE
    SYNTAX SEQUENCE OF Enc1P533source4Entry
    MAX-ACCESS not-accessible
    STATUS     current
    DESCRIPTION
    "
    Name      : Source 4
    Menu Path : /Audio/Audio 8
    Details   : Specifies fourth audio source (pair) for this multichannel codec.
    "
::= { enc1Params 533 }

enc1P533source4Entry OBJECT-TYPE
    SYNTAX Enc1P533source4Entry
    MAX-ACCESS not-accessible
    STATUS     current
    DESCRIPTION
    "Table Entry for Source 4"
    INDEX { slotId }
::= { enc1P533source4Table 1 }

Enc1P533source4Entry ::= SEQUENCE {
    enc1P533source4Value    Enc1E70enumObj
}

enc1P533source4Value OBJECT-TYPE
    SYNTAX     Enc1E70enumObj
    MAX-ACCESS read-write
    STATUS     current
    DESCRIPTION
    "Specifies fourth audio source (pair) for this multichannel codec."
::= { enc1P533source4Entry 1 }

enc1P534preProcessingTable OBJECT-TYPE
    SYNTAX SEQUENCE OF Enc1P534preProcessingEntry
    MAX-ACCESS not-accessible
    STATUS     current
    DESCRIPTION
    "
    Name      : Pre Processing
    Menu Path : Not Applicable
    Details   : Specifies special processing for audio channel
    "
::= { enc1Params 534 }

enc1P534preProcessingEntry OBJECT-TYPE
    SYNTAX Enc1P534preProcessingEntry
    MAX-ACCESS not-accessible
    STATUS     current
    DESCRIPTION
    "Table Entry for Pre Processing"
    INDEX { slotId }
::= { enc1P534preProcessingTable 1 }

Enc1P534preProcessingEntry ::= SEQUENCE {
    enc1P534preProcessingValue    Enc1E72enumObj
}

enc1P534preProcessingValue OBJECT-TYPE
    SYNTAX     Enc1E72enumObj
    MAX-ACCESS read-write
    STATUS     current
    DESCRIPTION
    "Specifies special processing for audio channel"
::= { enc1P534preProcessingEntry 1 }

enc1P535delayTable OBJECT-TYPE
    SYNTAX SEQUENCE OF Enc1P535delayEntry
    MAX-ACCESS not-accessible
    STATUS     current
    DESCRIPTION
    "
    Name      : Delay
    Menu Path : /Audio/Audio 8
    Units     : msec
    Precision : 0
    Low Range : -500
    High Range: 500
    Details   : Specify an additional audio delay, relative to video delay.

     NOTE: Precision/Units/Ranges represent the state of the
           parameter during the MIB generation, and does not
           neccessary reflect the current state of the parameter
    "
::= { enc1Params 535 }

enc1P535delayEntry OBJECT-TYPE
    SYNTAX Enc1P535delayEntry
    MAX-ACCESS not-accessible
    STATUS     current
    DESCRIPTION
    "Table Entry for Delay"
    INDEX { slotId }
::= { enc1P535delayTable 1 }

Enc1P535delayEntry ::= SEQUENCE {
    enc1P535delayValue    INTEGER
}

enc1P535delayValue OBJECT-TYPE
    SYNTAX     INTEGER
    MAX-ACCESS read-write
    STATUS     current
    DESCRIPTION
    "Specify an additional audio delay, relative to video delay."
::= { enc1P535delayEntry 1 }

enc1P536gainTable OBJECT-TYPE
    SYNTAX SEQUENCE OF Enc1P536gainEntry
    MAX-ACCESS not-accessible
    STATUS     current
    DESCRIPTION
    "
    Name      : Gain
    Menu Path : /Audio/Audio 8
    Units     : dB
    Precision : 1
    Low Range : -800
    High Range: 400
    Details   : Apply a gain (or attenuation) to all source channels.

     NOTE: Precision/Units/Ranges represent the state of the
           parameter during the MIB generation, and does not
           neccessary reflect the current state of the parameter
    "
::= { enc1Params 536 }

enc1P536gainEntry OBJECT-TYPE
    SYNTAX Enc1P536gainEntry
    MAX-ACCESS not-accessible
    STATUS     current
    DESCRIPTION
    "Table Entry for Gain"
    INDEX { slotId }
::= { enc1P536gainTable 1 }

Enc1P536gainEntry ::= SEQUENCE {
    enc1P536gainValue    INTEGER
}

enc1P536gainValue OBJECT-TYPE
    SYNTAX     INTEGER
    MAX-ACCESS read-write
    STATUS     current
    DESCRIPTION
    "Apply a gain (or attenuation) to all source channels."
::= { enc1P536gainEntry 1 }

enc1P538deemphasisTable OBJECT-TYPE
    SYNTAX SEQUENCE OF Enc1P538deemphasisEntry
    MAX-ACCESS not-accessible
    STATUS     current
    DESCRIPTION
    "
    Name      : Deemphasis
    Menu Path : /Audio/Audio 8
    Details   : Dolby Digital: applies deemphasis, Mpeg: indicates presence of preemphasis. Auto uses AES channel block indication.
    "
::= { enc1Params 538 }

enc1P538deemphasisEntry OBJECT-TYPE
    SYNTAX Enc1P538deemphasisEntry
    MAX-ACCESS not-accessible
    STATUS     current
    DESCRIPTION
    "Table Entry for Deemphasis"
    INDEX { slotId }
::= { enc1P538deemphasisTable 1 }

Enc1P538deemphasisEntry ::= SEQUENCE {
    enc1P538deemphasisValue    Enc1E2enumObj
}

enc1P538deemphasisValue OBJECT-TYPE
    SYNTAX     Enc1E2enumObj
    MAX-ACCESS read-write
    STATUS     current
    DESCRIPTION
    "Dolby Digital: applies deemphasis, Mpeg: indicates presence of preemphasis. Auto uses AES channel block indication."
::= { enc1P538deemphasisEntry 1 }

enc1P539modeTable OBJECT-TYPE
    SYNTAX SEQUENCE OF Enc1P539modeEntry
    MAX-ACCESS not-accessible
    STATUS     current
    DESCRIPTION
    "
    Name      : Mode
    Menu Path : /Audio/Audio 8
    Details   : Specifies the audio coding mode (maximum channel usage)
    "
::= { enc1Params 539 }

enc1P539modeEntry OBJECT-TYPE
    SYNTAX Enc1P539modeEntry
    MAX-ACCESS not-accessible
    STATUS     current
    DESCRIPTION
    "Table Entry for Mode"
    INDEX { slotId }
::= { enc1P539modeTable 1 }

Enc1P539modeEntry ::= SEQUENCE {
    enc1P539modeValue    Enc1E200enumObj
}

enc1P539modeValue OBJECT-TYPE
    SYNTAX     Enc1E200enumObj
    MAX-ACCESS read-write
    STATUS     current
    DESCRIPTION
    "Specifies the audio coding mode (maximum channel usage)"
::= { enc1P539modeEntry 1 }

enc1P540audioFormatTable OBJECT-TYPE
    SYNTAX SEQUENCE OF Enc1P540audioFormatEntry
    MAX-ACCESS not-accessible
    STATUS     current
    DESCRIPTION
    "
    Name      : Audio Format
    Menu Path : /Audio/Audio 8
    Details   : Specifies the audio encoding standard and bitrate.
    "
::= { enc1Params 540 }

enc1P540audioFormatEntry OBJECT-TYPE
    SYNTAX Enc1P540audioFormatEntry
    MAX-ACCESS not-accessible
    STATUS     current
    DESCRIPTION
    "Table Entry for Audio Format"
    INDEX { slotId }
::= { enc1P540audioFormatTable 1 }

Enc1P540audioFormatEntry ::= SEQUENCE {
    enc1P540audioFormatValue    Enc1E73enumObj
}

enc1P540audioFormatValue OBJECT-TYPE
    SYNTAX     Enc1E73enumObj
    MAX-ACCESS read-write
    STATUS     current
    DESCRIPTION
    "Specifies the audio encoding standard and bitrate."
::= { enc1P540audioFormatEntry 1 }

enc1P541languageCodeTable OBJECT-TYPE
    SYNTAX SEQUENCE OF Enc1P541languageCodeEntry
    MAX-ACCESS not-accessible
    STATUS     current
    DESCRIPTION
    "
    Name      : Language Code
    Menu Path : /Audio/Audio 8
    Details   : Specifies the ISO 639-2 (three letter) language code.
    "
::= { enc1Params 541 }

enc1P541languageCodeEntry OBJECT-TYPE
    SYNTAX Enc1P541languageCodeEntry
    MAX-ACCESS not-accessible
    STATUS     current
    DESCRIPTION
    "Table Entry for Language Code"
    INDEX { slotId }
::= { enc1P541languageCodeTable 1 }

Enc1P541languageCodeEntry ::= SEQUENCE {
    enc1P541languageCodeValue    DisplayString
}

enc1P541languageCodeValue OBJECT-TYPE
    SYNTAX     DisplayString
    MAX-ACCESS read-write
    STATUS     current
    DESCRIPTION
    "Specifies the ISO 639-2 (three letter) language code."
::= { enc1P541languageCodeEntry 1 }

enc1P542enableOutputTable OBJECT-TYPE
    SYNTAX SEQUENCE OF Enc1P542enableOutputEntry
    MAX-ACCESS not-accessible
    STATUS     current
    DESCRIPTION
    "
    Name      : Enable Output
    Menu Path : /Audio/Audio 8
    Details   : Specifies which encoded program carries this audio.
    "
::= { enc1Params 542 }

enc1P542enableOutputEntry OBJECT-TYPE
    SYNTAX Enc1P542enableOutputEntry
    MAX-ACCESS not-accessible
    STATUS     current
    DESCRIPTION
    "Table Entry for Enable Output"
    INDEX { slotId }
::= { enc1P542enableOutputTable 1 }

Enc1P542enableOutputEntry ::= SEQUENCE {
    enc1P542enableOutputValue    Enc1E82enumObj
}

enc1P542enableOutputValue OBJECT-TYPE
    SYNTAX     Enc1E82enumObj
    MAX-ACCESS read-write
    STATUS     current
    DESCRIPTION
    "Specifies which encoded program carries this audio."
::= { enc1P542enableOutputEntry 1 }

enc1P543metadataSourceTable OBJECT-TYPE
    SYNTAX SEQUENCE OF Enc1P543metadataSourceEntry
    MAX-ACCESS not-accessible
    STATUS     current
    DESCRIPTION
    "
    Name      : Metadata Source
    Menu Path : /Audio/Audio 8/Metadata
    Details   : Specifies source for Dolby audio metadata
    "
::= { enc1Params 543 }

enc1P543metadataSourceEntry OBJECT-TYPE
    SYNTAX Enc1P543metadataSourceEntry
    MAX-ACCESS not-accessible
    STATUS     current
    DESCRIPTION
    "Table Entry for Metadata Source"
    INDEX { slotId }
::= { enc1P543metadataSourceTable 1 }

Enc1P543metadataSourceEntry ::= SEQUENCE {
    enc1P543metadataSourceValue    Enc1E83enumObj
}

enc1P543metadataSourceValue OBJECT-TYPE
    SYNTAX     Enc1E83enumObj
    MAX-ACCESS read-write
    STATUS     current
    DESCRIPTION
    "Specifies source for Dolby audio metadata"
::= { enc1P543metadataSourceEntry 1 }

enc1P544metadataReversionModeTable OBJECT-TYPE
    SYNTAX SEQUENCE OF Enc1P544metadataReversionModeEntry
    MAX-ACCESS not-accessible
    STATUS     current
    DESCRIPTION
    "
    Name      : Metadata Reversion Mode
    Menu Path : /Audio/Audio 8/Metadata
    Details   : Specifies response to interruption in metadata source
    "
::= { enc1Params 544 }

enc1P544metadataReversionModeEntry OBJECT-TYPE
    SYNTAX Enc1P544metadataReversionModeEntry
    MAX-ACCESS not-accessible
    STATUS     current
    DESCRIPTION
    "Table Entry for Metadata Reversion Mode"
    INDEX { slotId }
::= { enc1P544metadataReversionModeTable 1 }

Enc1P544metadataReversionModeEntry ::= SEQUENCE {
    enc1P544metadataReversionModeValue    Enc1E84enumObj
}

enc1P544metadataReversionModeValue OBJECT-TYPE
    SYNTAX     Enc1E84enumObj
    MAX-ACCESS read-write
    STATUS     current
    DESCRIPTION
    "Specifies response to interruption in metadata source"
::= { enc1P544metadataReversionModeEntry 1 }

enc1P545pssignalingTable OBJECT-TYPE
    SYNTAX SEQUENCE OF Enc1P545pssignalingEntry
    MAX-ACCESS not-accessible
    STATUS     current
    DESCRIPTION
    "
    Name      : PS Signaling
    Menu Path : /Audio/Audio 8/AAC
    Details   : Specifies the parametric stereo signaling for AAC audio encoding.
    "
::= { enc1Params 545 }

enc1P545pssignalingEntry OBJECT-TYPE
    SYNTAX Enc1P545pssignalingEntry
    MAX-ACCESS not-accessible
    STATUS     current
    DESCRIPTION
    "Table Entry for PS Signaling"
    INDEX { slotId }
::= { enc1P545pssignalingTable 1 }

Enc1P545pssignalingEntry ::= SEQUENCE {
    enc1P545pssignalingValue    Enc1E76enumObj
}

enc1P545pssignalingValue OBJECT-TYPE
    SYNTAX     Enc1E76enumObj
    MAX-ACCESS read-write
    STATUS     current
    DESCRIPTION
    "Specifies the parametric stereo signaling for AAC audio encoding."
::= { enc1P545pssignalingEntry 1 }

enc1P546sbrsignalingTable OBJECT-TYPE
    SYNTAX SEQUENCE OF Enc1P546sbrsignalingEntry
    MAX-ACCESS not-accessible
    STATUS     current
    DESCRIPTION
    "
    Name      : SBR Signaling
    Menu Path : /Audio/Audio 8/AAC
    Details   : Specifies the SBR signaling for AAC audio encoding.
    "
::= { enc1Params 546 }

enc1P546sbrsignalingEntry OBJECT-TYPE
    SYNTAX Enc1P546sbrsignalingEntry
    MAX-ACCESS not-accessible
    STATUS     current
    DESCRIPTION
    "Table Entry for SBR Signaling"
    INDEX { slotId }
::= { enc1P546sbrsignalingTable 1 }

Enc1P546sbrsignalingEntry ::= SEQUENCE {
    enc1P546sbrsignalingValue    Enc1E77enumObj
}

enc1P546sbrsignalingValue OBJECT-TYPE
    SYNTAX     Enc1E77enumObj
    MAX-ACCESS read-write
    STATUS     current
    DESCRIPTION
    "Specifies the SBR signaling for AAC audio encoding."
::= { enc1P546sbrsignalingEntry 1 }

enc1P547transportTable OBJECT-TYPE
    SYNTAX SEQUENCE OF Enc1P547transportEntry
    MAX-ACCESS not-accessible
    STATUS     current
    DESCRIPTION
    "
    Name      : Transport
    Menu Path : /Audio/Audio 8/AAC
    Details   : Specifies the transport layer (framing) for AAC audio encoding.
    "
::= { enc1Params 547 }

enc1P547transportEntry OBJECT-TYPE
    SYNTAX Enc1P547transportEntry
    MAX-ACCESS not-accessible
    STATUS     current
    DESCRIPTION
    "Table Entry for Transport"
    INDEX { slotId }
::= { enc1P547transportTable 1 }

Enc1P547transportEntry ::= SEQUENCE {
    enc1P547transportValue    Enc1E78enumObj
}

enc1P547transportValue OBJECT-TYPE
    SYNTAX     Enc1E78enumObj
    MAX-ACCESS read-write
    STATUS     current
    DESCRIPTION
    "Specifies the transport layer (framing) for AAC audio encoding."
::= { enc1P547transportEntry 1 }

enc1P549programConfigurationTable OBJECT-TYPE
    SYNTAX SEQUENCE OF Enc1P549programConfigurationEntry
    MAX-ACCESS not-accessible
    STATUS     current
    DESCRIPTION
    "
    Name      : Program Configuration
    Menu Path : /Audio/Audio 8/Dolby E Encoder
    Details   : Determines how audio channels are grouped into programs within a Dolby E bitstream.
    "
::= { enc1Params 549 }

enc1P549programConfigurationEntry OBJECT-TYPE
    SYNTAX Enc1P549programConfigurationEntry
    MAX-ACCESS not-accessible
    STATUS     current
    DESCRIPTION
    "Table Entry for Program Configuration"
    INDEX { slotId }
::= { enc1P549programConfigurationTable 1 }

Enc1P549programConfigurationEntry ::= SEQUENCE {
    enc1P549programConfigurationValue    Enc1E201enumObj
}

enc1P549programConfigurationValue OBJECT-TYPE
    SYNTAX     Enc1E201enumObj
    MAX-ACCESS read-write
    STATUS     current
    DESCRIPTION
    "Determines how audio channels are grouped into programs within a Dolby E bitstream."
::= { enc1P549programConfigurationEntry 1 }

enc1P579avsyncAdjustCountTable OBJECT-TYPE
    SYNTAX SEQUENCE OF Enc1P579avsyncAdjustCountEntry
    MAX-ACCESS not-accessible
    STATUS     current
    DESCRIPTION
    "
    Name      : AV Sync Adjust Count
    Menu Path : /Audio/Audio 8/Status
    Units     : 
    Precision : 0
    Low Range : 0
    High Range: -1
    Details   : Displays the count of audio/video sync adjustments (lipsync discontinuities).

     NOTE: Precision/Units/Ranges represent the state of the
           parameter during the MIB generation, and does not
           neccessary reflect the current state of the parameter
    "
::= { enc1Params 579 }

enc1P579avsyncAdjustCountEntry OBJECT-TYPE
    SYNTAX Enc1P579avsyncAdjustCountEntry
    MAX-ACCESS not-accessible
    STATUS     current
    DESCRIPTION
    "Table Entry for AV Sync Adjust Count"
    INDEX { slotId }
::= { enc1P579avsyncAdjustCountTable 1 }

Enc1P579avsyncAdjustCountEntry ::= SEQUENCE {
    enc1P579avsyncAdjustCountValue    INTEGER
}

enc1P579avsyncAdjustCountValue OBJECT-TYPE
    SYNTAX     INTEGER
    MAX-ACCESS read-only
    STATUS     current
    DESCRIPTION
    "Displays the count of audio/video sync adjustments (lipsync discontinuities)."
::= { enc1P579avsyncAdjustCountEntry 1 }

enc1P580pmtpositionTable OBJECT-TYPE
    SYNTAX SEQUENCE OF Enc1P580pmtpositionEntry
    MAX-ACCESS not-accessible
    STATUS     current
    DESCRIPTION
    "
    Name      : PMT Position
    Menu Path : /Audio/Audio 8/Status
    Units     : 
    Precision : 0
    Low Range : 0
    High Range: 8
    Details   : Displays the relative position in the PMT of this audio stream

     NOTE: Precision/Units/Ranges represent the state of the
           parameter during the MIB generation, and does not
           neccessary reflect the current state of the parameter
    "
::= { enc1Params 580 }

enc1P580pmtpositionEntry OBJECT-TYPE
    SYNTAX Enc1P580pmtpositionEntry
    MAX-ACCESS not-accessible
    STATUS     current
    DESCRIPTION
    "Table Entry for PMT Position"
    INDEX { slotId }
::= { enc1P580pmtpositionTable 1 }

Enc1P580pmtpositionEntry ::= SEQUENCE {
    enc1P580pmtpositionValue    INTEGER
}

enc1P580pmtpositionValue OBJECT-TYPE
    SYNTAX     INTEGER
    MAX-ACCESS read-only
    STATUS     current
    DESCRIPTION
    "Displays the relative position in the PMT of this audio stream"
::= { enc1P580pmtpositionEntry 1 }

enc1P582lossofSignalTable OBJECT-TYPE
    SYNTAX SEQUENCE OF Enc1P582lossofSignalEntry
    MAX-ACCESS not-accessible
    STATUS     current
    DESCRIPTION
    "
    Name      : Loss of Signal
    Menu Path : /Audio/Audio 8/Status
    Details   : Indicates loss of a selected source signal.
    "
::= { enc1Params 582 }

enc1P582lossofSignalEntry OBJECT-TYPE
    SYNTAX Enc1P582lossofSignalEntry
    MAX-ACCESS not-accessible
    STATUS     current
    DESCRIPTION
    "Table Entry for Loss of Signal"
    INDEX { slotId }
::= { enc1P582lossofSignalTable 1 }

Enc1P582lossofSignalEntry ::= SEQUENCE {
    enc1P582lossofSignalValue    Enc1E5enumObj
}

enc1P582lossofSignalValue OBJECT-TYPE
    SYNTAX     Enc1E5enumObj
    MAX-ACCESS read-only
    STATUS     current
    DESCRIPTION
    "Indicates loss of a selected source signal."
::= { enc1P582lossofSignalEntry 1 }

enc1P583sourceTable OBJECT-TYPE
    SYNTAX SEQUENCE OF Enc1P583sourceEntry
    MAX-ACCESS not-accessible
    STATUS     current
    DESCRIPTION
    "
    Name      : Source
    Menu Path : /Data/Ext Data
    Details   : Specifies source (None, UDP, Serial) for out of band data.
    "
::= { enc1Params 583 }

enc1P583sourceEntry OBJECT-TYPE
    SYNTAX Enc1P583sourceEntry
    MAX-ACCESS not-accessible
    STATUS     current
    DESCRIPTION
    "Table Entry for Source"
    INDEX { slotId }
::= { enc1P583sourceTable 1 }

Enc1P583sourceEntry ::= SEQUENCE {
    enc1P583sourceValue    Enc1E123enumObj
}

enc1P583sourceValue OBJECT-TYPE
    SYNTAX     Enc1E123enumObj
    MAX-ACCESS read-write
    STATUS     current
    DESCRIPTION
    "Specifies source (None, UDP, Serial) for out of band data."
::= { enc1P583sourceEntry 1 }

enc1P584rateTable OBJECT-TYPE
    SYNTAX SEQUENCE OF Enc1P584rateEntry
    MAX-ACCESS not-accessible
    STATUS     current
    DESCRIPTION
    "
    Name      : Rate
    Menu Path : /Data/Ext Data
    Units     : bits/sec
    Precision : 0
    Low Range : 0
    High Range: 125000
    Details   : Specifies maximum data rate, including overhead, for out of band data.

     NOTE: Precision/Units/Ranges represent the state of the
           parameter during the MIB generation, and does not
           neccessary reflect the current state of the parameter
    "
::= { enc1Params 584 }

enc1P584rateEntry OBJECT-TYPE
    SYNTAX Enc1P584rateEntry
    MAX-ACCESS not-accessible
    STATUS     current
    DESCRIPTION
    "Table Entry for Rate"
    INDEX { slotId }
::= { enc1P584rateTable 1 }

Enc1P584rateEntry ::= SEQUENCE {
    enc1P584rateValue    INTEGER
}

enc1P584rateValue OBJECT-TYPE
    SYNTAX     INTEGER
    MAX-ACCESS read-write
    STATUS     current
    DESCRIPTION
    "Specifies maximum data rate, including overhead, for out of band data."
::= { enc1P584rateEntry 1 }

enc1P585field1Line6FunctionTable OBJECT-TYPE
    SYNTAX SEQUENCE OF Enc1P585field1Line6FunctionEntry
    MAX-ACCESS not-accessible
    STATUS     current
    DESCRIPTION
    "
    Name      : Field 1 Line 6 Function
    Menu Path : /Data/VBI
    Details   : Specifies the VBI line processing function.
    "
::= { enc1Params 585 }

enc1P585field1Line6FunctionEntry OBJECT-TYPE
    SYNTAX Enc1P585field1Line6FunctionEntry
    MAX-ACCESS not-accessible
    STATUS     current
    DESCRIPTION
    "Table Entry for Field 1 Line 6 Function"
    INDEX { slotId }
::= { enc1P585field1Line6FunctionTable 1 }

Enc1P585field1Line6FunctionEntry ::= SEQUENCE {
    enc1P585field1Line6FunctionValue    Enc1E112enumObj
}

enc1P585field1Line6FunctionValue OBJECT-TYPE
    SYNTAX     Enc1E112enumObj
    MAX-ACCESS read-write
    STATUS     current
    DESCRIPTION
    "Specifies the VBI line processing function."
::= { enc1P585field1Line6FunctionEntry 1 }

enc1P586field1Line7FunctionTable OBJECT-TYPE
    SYNTAX SEQUENCE OF Enc1P586field1Line7FunctionEntry
    MAX-ACCESS not-accessible
    STATUS     current
    DESCRIPTION
    "
    Name      : Field 1 Line 7 Function
    Menu Path : /Data/VBI
    Details   : Specifies the VBI line processing function.
    "
::= { enc1Params 586 }

enc1P586field1Line7FunctionEntry OBJECT-TYPE
    SYNTAX Enc1P586field1Line7FunctionEntry
    MAX-ACCESS not-accessible
    STATUS     current
    DESCRIPTION
    "Table Entry for Field 1 Line 7 Function"
    INDEX { slotId }
::= { enc1P586field1Line7FunctionTable 1 }

Enc1P586field1Line7FunctionEntry ::= SEQUENCE {
    enc1P586field1Line7FunctionValue    Enc1E112enumObj
}

enc1P586field1Line7FunctionValue OBJECT-TYPE
    SYNTAX     Enc1E112enumObj
    MAX-ACCESS read-write
    STATUS     current
    DESCRIPTION
    "Specifies the VBI line processing function."
::= { enc1P586field1Line7FunctionEntry 1 }

enc1P587field1Line8FunctionTable OBJECT-TYPE
    SYNTAX SEQUENCE OF Enc1P587field1Line8FunctionEntry
    MAX-ACCESS not-accessible
    STATUS     current
    DESCRIPTION
    "
    Name      : Field 1 Line 8 Function
    Menu Path : /Data/VBI
    Details   : Specifies the VBI line processing function.
    "
::= { enc1Params 587 }

enc1P587field1Line8FunctionEntry OBJECT-TYPE
    SYNTAX Enc1P587field1Line8FunctionEntry
    MAX-ACCESS not-accessible
    STATUS     current
    DESCRIPTION
    "Table Entry for Field 1 Line 8 Function"
    INDEX { slotId }
::= { enc1P587field1Line8FunctionTable 1 }

Enc1P587field1Line8FunctionEntry ::= SEQUENCE {
    enc1P587field1Line8FunctionValue    Enc1E112enumObj
}

enc1P587field1Line8FunctionValue OBJECT-TYPE
    SYNTAX     Enc1E112enumObj
    MAX-ACCESS read-write
    STATUS     current
    DESCRIPTION
    "Specifies the VBI line processing function."
::= { enc1P587field1Line8FunctionEntry 1 }

enc1P588field1Line9FunctionTable OBJECT-TYPE
    SYNTAX SEQUENCE OF Enc1P588field1Line9FunctionEntry
    MAX-ACCESS not-accessible
    STATUS     current
    DESCRIPTION
    "
    Name      : Field 1 Line 9 Function
    Menu Path : /Data/VBI
    Details   : Specifies the VBI line processing function.
    "
::= { enc1Params 588 }

enc1P588field1Line9FunctionEntry OBJECT-TYPE
    SYNTAX Enc1P588field1Line9FunctionEntry
    MAX-ACCESS not-accessible
    STATUS     current
    DESCRIPTION
    "Table Entry for Field 1 Line 9 Function"
    INDEX { slotId }
::= { enc1P588field1Line9FunctionTable 1 }

Enc1P588field1Line9FunctionEntry ::= SEQUENCE {
    enc1P588field1Line9FunctionValue    Enc1E112enumObj
}

enc1P588field1Line9FunctionValue OBJECT-TYPE
    SYNTAX     Enc1E112enumObj
    MAX-ACCESS read-write
    STATUS     current
    DESCRIPTION
    "Specifies the VBI line processing function."
::= { enc1P588field1Line9FunctionEntry 1 }

enc1P589field1Line10FunctionTable OBJECT-TYPE
    SYNTAX SEQUENCE OF Enc1P589field1Line10FunctionEntry
    MAX-ACCESS not-accessible
    STATUS     current
    DESCRIPTION
    "
    Name      : Field 1 Line 10 Function
    Menu Path : /Data/VBI
    Details   : Specifies the VBI line processing function.
    "
::= { enc1Params 589 }

enc1P589field1Line10FunctionEntry OBJECT-TYPE
    SYNTAX Enc1P589field1Line10FunctionEntry
    MAX-ACCESS not-accessible
    STATUS     current
    DESCRIPTION
    "Table Entry for Field 1 Line 10 Function"
    INDEX { slotId }
::= { enc1P589field1Line10FunctionTable 1 }

Enc1P589field1Line10FunctionEntry ::= SEQUENCE {
    enc1P589field1Line10FunctionValue    Enc1E112enumObj
}

enc1P589field1Line10FunctionValue OBJECT-TYPE
    SYNTAX     Enc1E112enumObj
    MAX-ACCESS read-write
    STATUS     current
    DESCRIPTION
    "Specifies the VBI line processing function."
::= { enc1P589field1Line10FunctionEntry 1 }

enc1P590field1Line11FunctionTable OBJECT-TYPE
    SYNTAX SEQUENCE OF Enc1P590field1Line11FunctionEntry
    MAX-ACCESS not-accessible
    STATUS     current
    DESCRIPTION
    "
    Name      : Field 1 Line 11 Function
    Menu Path : /Data/VBI
    Details   : Specifies the VBI line processing function.
    "
::= { enc1Params 590 }

enc1P590field1Line11FunctionEntry OBJECT-TYPE
    SYNTAX Enc1P590field1Line11FunctionEntry
    MAX-ACCESS not-accessible
    STATUS     current
    DESCRIPTION
    "Table Entry for Field 1 Line 11 Function"
    INDEX { slotId }
::= { enc1P590field1Line11FunctionTable 1 }

Enc1P590field1Line11FunctionEntry ::= SEQUENCE {
    enc1P590field1Line11FunctionValue    Enc1E112enumObj
}

enc1P590field1Line11FunctionValue OBJECT-TYPE
    SYNTAX     Enc1E112enumObj
    MAX-ACCESS read-write
    STATUS     current
    DESCRIPTION
    "Specifies the VBI line processing function."
::= { enc1P590field1Line11FunctionEntry 1 }

enc1P591field1Line12FunctionTable OBJECT-TYPE
    SYNTAX SEQUENCE OF Enc1P591field1Line12FunctionEntry
    MAX-ACCESS not-accessible
    STATUS     current
    DESCRIPTION
    "
    Name      : Field 1 Line 12 Function
    Menu Path : /Data/VBI
    Details   : Specifies the VBI line processing function.
    "
::= { enc1Params 591 }

enc1P591field1Line12FunctionEntry OBJECT-TYPE
    SYNTAX Enc1P591field1Line12FunctionEntry
    MAX-ACCESS not-accessible
    STATUS     current
    DESCRIPTION
    "Table Entry for Field 1 Line 12 Function"
    INDEX { slotId }
::= { enc1P591field1Line12FunctionTable 1 }

Enc1P591field1Line12FunctionEntry ::= SEQUENCE {
    enc1P591field1Line12FunctionValue    Enc1E112enumObj
}

enc1P591field1Line12FunctionValue OBJECT-TYPE
    SYNTAX     Enc1E112enumObj
    MAX-ACCESS read-write
    STATUS     current
    DESCRIPTION
    "Specifies the VBI line processing function."
::= { enc1P591field1Line12FunctionEntry 1 }

enc1P592field1Line13FunctionTable OBJECT-TYPE
    SYNTAX SEQUENCE OF Enc1P592field1Line13FunctionEntry
    MAX-ACCESS not-accessible
    STATUS     current
    DESCRIPTION
    "
    Name      : Field 1 Line 13 Function
    Menu Path : /Data/VBI
    Details   : Specifies the VBI line processing function.
    "
::= { enc1Params 592 }

enc1P592field1Line13FunctionEntry OBJECT-TYPE
    SYNTAX Enc1P592field1Line13FunctionEntry
    MAX-ACCESS not-accessible
    STATUS     current
    DESCRIPTION
    "Table Entry for Field 1 Line 13 Function"
    INDEX { slotId }
::= { enc1P592field1Line13FunctionTable 1 }

Enc1P592field1Line13FunctionEntry ::= SEQUENCE {
    enc1P592field1Line13FunctionValue    Enc1E112enumObj
}

enc1P592field1Line13FunctionValue OBJECT-TYPE
    SYNTAX     Enc1E112enumObj
    MAX-ACCESS read-write
    STATUS     current
    DESCRIPTION
    "Specifies the VBI line processing function."
::= { enc1P592field1Line13FunctionEntry 1 }

enc1P593field1Line14FunctionTable OBJECT-TYPE
    SYNTAX SEQUENCE OF Enc1P593field1Line14FunctionEntry
    MAX-ACCESS not-accessible
    STATUS     current
    DESCRIPTION
    "
    Name      : Field 1 Line 14 Function
    Menu Path : /Data/VBI
    Details   : Specifies the VBI line processing function.
    "
::= { enc1Params 593 }

enc1P593field1Line14FunctionEntry OBJECT-TYPE
    SYNTAX Enc1P593field1Line14FunctionEntry
    MAX-ACCESS not-accessible
    STATUS     current
    DESCRIPTION
    "Table Entry for Field 1 Line 14 Function"
    INDEX { slotId }
::= { enc1P593field1Line14FunctionTable 1 }

Enc1P593field1Line14FunctionEntry ::= SEQUENCE {
    enc1P593field1Line14FunctionValue    Enc1E112enumObj
}

enc1P593field1Line14FunctionValue OBJECT-TYPE
    SYNTAX     Enc1E112enumObj
    MAX-ACCESS read-write
    STATUS     current
    DESCRIPTION
    "Specifies the VBI line processing function."
::= { enc1P593field1Line14FunctionEntry 1 }

enc1P594field1Line15FunctionTable OBJECT-TYPE
    SYNTAX SEQUENCE OF Enc1P594field1Line15FunctionEntry
    MAX-ACCESS not-accessible
    STATUS     current
    DESCRIPTION
    "
    Name      : Field 1 Line 15 Function
    Menu Path : /Data/VBI
    Details   : Specifies the VBI line processing function.
    "
::= { enc1Params 594 }

enc1P594field1Line15FunctionEntry OBJECT-TYPE
    SYNTAX Enc1P594field1Line15FunctionEntry
    MAX-ACCESS not-accessible
    STATUS     current
    DESCRIPTION
    "Table Entry for Field 1 Line 15 Function"
    INDEX { slotId }
::= { enc1P594field1Line15FunctionTable 1 }

Enc1P594field1Line15FunctionEntry ::= SEQUENCE {
    enc1P594field1Line15FunctionValue    Enc1E112enumObj
}

enc1P594field1Line15FunctionValue OBJECT-TYPE
    SYNTAX     Enc1E112enumObj
    MAX-ACCESS read-write
    STATUS     current
    DESCRIPTION
    "Specifies the VBI line processing function."
::= { enc1P594field1Line15FunctionEntry 1 }

enc1P595field1Line16FunctionTable OBJECT-TYPE
    SYNTAX SEQUENCE OF Enc1P595field1Line16FunctionEntry
    MAX-ACCESS not-accessible
    STATUS     current
    DESCRIPTION
    "
    Name      : Field 1 Line 16 Function
    Menu Path : /Data/VBI
    Details   : Specifies the VBI line processing function.
    "
::= { enc1Params 595 }

enc1P595field1Line16FunctionEntry OBJECT-TYPE
    SYNTAX Enc1P595field1Line16FunctionEntry
    MAX-ACCESS not-accessible
    STATUS     current
    DESCRIPTION
    "Table Entry for Field 1 Line 16 Function"
    INDEX { slotId }
::= { enc1P595field1Line16FunctionTable 1 }

Enc1P595field1Line16FunctionEntry ::= SEQUENCE {
    enc1P595field1Line16FunctionValue    Enc1E112enumObj
}

enc1P595field1Line16FunctionValue OBJECT-TYPE
    SYNTAX     Enc1E112enumObj
    MAX-ACCESS read-write
    STATUS     current
    DESCRIPTION
    "Specifies the VBI line processing function."
::= { enc1P595field1Line16FunctionEntry 1 }

enc1P596field1Line17FunctionTable OBJECT-TYPE
    SYNTAX SEQUENCE OF Enc1P596field1Line17FunctionEntry
    MAX-ACCESS not-accessible
    STATUS     current
    DESCRIPTION
    "
    Name      : Field 1 Line 17 Function
    Menu Path : /Data/VBI
    Details   : Specifies the VBI line processing function.
    "
::= { enc1Params 596 }

enc1P596field1Line17FunctionEntry OBJECT-TYPE
    SYNTAX Enc1P596field1Line17FunctionEntry
    MAX-ACCESS not-accessible
    STATUS     current
    DESCRIPTION
    "Table Entry for Field 1 Line 17 Function"
    INDEX { slotId }
::= { enc1P596field1Line17FunctionTable 1 }

Enc1P596field1Line17FunctionEntry ::= SEQUENCE {
    enc1P596field1Line17FunctionValue    Enc1E112enumObj
}

enc1P596field1Line17FunctionValue OBJECT-TYPE
    SYNTAX     Enc1E112enumObj
    MAX-ACCESS read-write
    STATUS     current
    DESCRIPTION
    "Specifies the VBI line processing function."
::= { enc1P596field1Line17FunctionEntry 1 }

enc1P597field1Line18FunctionTable OBJECT-TYPE
    SYNTAX SEQUENCE OF Enc1P597field1Line18FunctionEntry
    MAX-ACCESS not-accessible
    STATUS     current
    DESCRIPTION
    "
    Name      : Field 1 Line 18 Function
    Menu Path : /Data/VBI
    Details   : Specifies the VBI line processing function.
    "
::= { enc1Params 597 }

enc1P597field1Line18FunctionEntry OBJECT-TYPE
    SYNTAX Enc1P597field1Line18FunctionEntry
    MAX-ACCESS not-accessible
    STATUS     current
    DESCRIPTION
    "Table Entry for Field 1 Line 18 Function"
    INDEX { slotId }
::= { enc1P597field1Line18FunctionTable 1 }

Enc1P597field1Line18FunctionEntry ::= SEQUENCE {
    enc1P597field1Line18FunctionValue    Enc1E112enumObj
}

enc1P597field1Line18FunctionValue OBJECT-TYPE
    SYNTAX     Enc1E112enumObj
    MAX-ACCESS read-write
    STATUS     current
    DESCRIPTION
    "Specifies the VBI line processing function."
::= { enc1P597field1Line18FunctionEntry 1 }

enc1P598field1Line19FunctionTable OBJECT-TYPE
    SYNTAX SEQUENCE OF Enc1P598field1Line19FunctionEntry
    MAX-ACCESS not-accessible
    STATUS     current
    DESCRIPTION
    "
    Name      : Field 1 Line 19 Function
    Menu Path : /Data/VBI
    Details   : Specifies the VBI line processing function.
    "
::= { enc1Params 598 }

enc1P598field1Line19FunctionEntry OBJECT-TYPE
    SYNTAX Enc1P598field1Line19FunctionEntry
    MAX-ACCESS not-accessible
    STATUS     current
    DESCRIPTION
    "Table Entry for Field 1 Line 19 Function"
    INDEX { slotId }
::= { enc1P598field1Line19FunctionTable 1 }

Enc1P598field1Line19FunctionEntry ::= SEQUENCE {
    enc1P598field1Line19FunctionValue    Enc1E112enumObj
}

enc1P598field1Line19FunctionValue OBJECT-TYPE
    SYNTAX     Enc1E112enumObj
    MAX-ACCESS read-write
    STATUS     current
    DESCRIPTION
    "Specifies the VBI line processing function."
::= { enc1P598field1Line19FunctionEntry 1 }

enc1P599field1Line20FunctionTable OBJECT-TYPE
    SYNTAX SEQUENCE OF Enc1P599field1Line20FunctionEntry
    MAX-ACCESS not-accessible
    STATUS     current
    DESCRIPTION
    "
    Name      : Field 1 Line 20 Function
    Menu Path : /Data/VBI
    Details   : Specifies the VBI line processing function.
    "
::= { enc1Params 599 }

enc1P599field1Line20FunctionEntry OBJECT-TYPE
    SYNTAX Enc1P599field1Line20FunctionEntry
    MAX-ACCESS not-accessible
    STATUS     current
    DESCRIPTION
    "Table Entry for Field 1 Line 20 Function"
    INDEX { slotId }
::= { enc1P599field1Line20FunctionTable 1 }

Enc1P599field1Line20FunctionEntry ::= SEQUENCE {
    enc1P599field1Line20FunctionValue    Enc1E112enumObj
}

enc1P599field1Line20FunctionValue OBJECT-TYPE
    SYNTAX     Enc1E112enumObj
    MAX-ACCESS read-write
    STATUS     current
    DESCRIPTION
    "Specifies the VBI line processing function."
::= { enc1P599field1Line20FunctionEntry 1 }

enc1P600field1Line21FunctionTable OBJECT-TYPE
    SYNTAX SEQUENCE OF Enc1P600field1Line21FunctionEntry
    MAX-ACCESS not-accessible
    STATUS     current
    DESCRIPTION
    "
    Name      : Field 1 Line 21 Function
    Menu Path : /Data/VBI
    Details   : Specifies the VBI line processing function.
    "
::= { enc1Params 600 }

enc1P600field1Line21FunctionEntry OBJECT-TYPE
    SYNTAX Enc1P600field1Line21FunctionEntry
    MAX-ACCESS not-accessible
    STATUS     current
    DESCRIPTION
    "Table Entry for Field 1 Line 21 Function"
    INDEX { slotId }
::= { enc1P600field1Line21FunctionTable 1 }

Enc1P600field1Line21FunctionEntry ::= SEQUENCE {
    enc1P600field1Line21FunctionValue    Enc1E112enumObj
}

enc1P600field1Line21FunctionValue OBJECT-TYPE
    SYNTAX     Enc1E112enumObj
    MAX-ACCESS read-write
    STATUS     current
    DESCRIPTION
    "Specifies the VBI line processing function."
::= { enc1P600field1Line21FunctionEntry 1 }

enc1P601field1Line22FunctionTable OBJECT-TYPE
    SYNTAX SEQUENCE OF Enc1P601field1Line22FunctionEntry
    MAX-ACCESS not-accessible
    STATUS     current
    DESCRIPTION
    "
    Name      : Field 1 Line 22 Function
    Menu Path : /Data/VBI
    Details   : Specifies the VBI line processing function.
    "
::= { enc1Params 601 }

enc1P601field1Line22FunctionEntry OBJECT-TYPE
    SYNTAX Enc1P601field1Line22FunctionEntry
    MAX-ACCESS not-accessible
    STATUS     current
    DESCRIPTION
    "Table Entry for Field 1 Line 22 Function"
    INDEX { slotId }
::= { enc1P601field1Line22FunctionTable 1 }

Enc1P601field1Line22FunctionEntry ::= SEQUENCE {
    enc1P601field1Line22FunctionValue    Enc1E112enumObj
}

enc1P601field1Line22FunctionValue OBJECT-TYPE
    SYNTAX     Enc1E112enumObj
    MAX-ACCESS read-write
    STATUS     current
    DESCRIPTION
    "Specifies the VBI line processing function."
::= { enc1P601field1Line22FunctionEntry 1 }

enc1P602field1Line23FunctionTable OBJECT-TYPE
    SYNTAX SEQUENCE OF Enc1P602field1Line23FunctionEntry
    MAX-ACCESS not-accessible
    STATUS     current
    DESCRIPTION
    "
    Name      : Field 1 Line 23 Function
    Menu Path : /Data/VBI
    Details   : Specifies the VBI line processing function.
    "
::= { enc1Params 602 }

enc1P602field1Line23FunctionEntry OBJECT-TYPE
    SYNTAX Enc1P602field1Line23FunctionEntry
    MAX-ACCESS not-accessible
    STATUS     current
    DESCRIPTION
    "Table Entry for Field 1 Line 23 Function"
    INDEX { slotId }
::= { enc1P602field1Line23FunctionTable 1 }

Enc1P602field1Line23FunctionEntry ::= SEQUENCE {
    enc1P602field1Line23FunctionValue    Enc1E111enumObj
}

enc1P602field1Line23FunctionValue OBJECT-TYPE
    SYNTAX     Enc1E111enumObj
    MAX-ACCESS read-write
    STATUS     current
    DESCRIPTION
    "Specifies the VBI line processing function."
::= { enc1P602field1Line23FunctionEntry 1 }

enc1P603field2Line5FunctionTable OBJECT-TYPE
    SYNTAX SEQUENCE OF Enc1P603field2Line5FunctionEntry
    MAX-ACCESS not-accessible
    STATUS     current
    DESCRIPTION
    "
    Name      : Field 2 Line 5 Function
    Menu Path : /Data/VBI
    Details   : Specifies the VBI line processing function.
    "
::= { enc1Params 603 }

enc1P603field2Line5FunctionEntry OBJECT-TYPE
    SYNTAX Enc1P603field2Line5FunctionEntry
    MAX-ACCESS not-accessible
    STATUS     current
    DESCRIPTION
    "Table Entry for Field 2 Line 5 Function"
    INDEX { slotId }
::= { enc1P603field2Line5FunctionTable 1 }

Enc1P603field2Line5FunctionEntry ::= SEQUENCE {
    enc1P603field2Line5FunctionValue    Enc1E112enumObj
}

enc1P603field2Line5FunctionValue OBJECT-TYPE
    SYNTAX     Enc1E112enumObj
    MAX-ACCESS read-write
    STATUS     current
    DESCRIPTION
    "Specifies the VBI line processing function."
::= { enc1P603field2Line5FunctionEntry 1 }

enc1P604field2Line6FunctionTable OBJECT-TYPE
    SYNTAX SEQUENCE OF Enc1P604field2Line6FunctionEntry
    MAX-ACCESS not-accessible
    STATUS     current
    DESCRIPTION
    "
    Name      : Field 2 Line 6 Function
    Menu Path : /Data/VBI
    Details   : Specifies the VBI line processing function.
    "
::= { enc1Params 604 }

enc1P604field2Line6FunctionEntry OBJECT-TYPE
    SYNTAX Enc1P604field2Line6FunctionEntry
    MAX-ACCESS not-accessible
    STATUS     current
    DESCRIPTION
    "Table Entry for Field 2 Line 6 Function"
    INDEX { slotId }
::= { enc1P604field2Line6FunctionTable 1 }

Enc1P604field2Line6FunctionEntry ::= SEQUENCE {
    enc1P604field2Line6FunctionValue    Enc1E112enumObj
}

enc1P604field2Line6FunctionValue OBJECT-TYPE
    SYNTAX     Enc1E112enumObj
    MAX-ACCESS read-write
    STATUS     current
    DESCRIPTION
    "Specifies the VBI line processing function."
::= { enc1P604field2Line6FunctionEntry 1 }

enc1P605field2Line7FunctionTable OBJECT-TYPE
    SYNTAX SEQUENCE OF Enc1P605field2Line7FunctionEntry
    MAX-ACCESS not-accessible
    STATUS     current
    DESCRIPTION
    "
    Name      : Field 2 Line 7 Function
    Menu Path : /Data/VBI
    Details   : Specifies the VBI line processing function.
    "
::= { enc1Params 605 }

enc1P605field2Line7FunctionEntry OBJECT-TYPE
    SYNTAX Enc1P605field2Line7FunctionEntry
    MAX-ACCESS not-accessible
    STATUS     current
    DESCRIPTION
    "Table Entry for Field 2 Line 7 Function"
    INDEX { slotId }
::= { enc1P605field2Line7FunctionTable 1 }

Enc1P605field2Line7FunctionEntry ::= SEQUENCE {
    enc1P605field2Line7FunctionValue    Enc1E112enumObj
}

enc1P605field2Line7FunctionValue OBJECT-TYPE
    SYNTAX     Enc1E112enumObj
    MAX-ACCESS read-write
    STATUS     current
    DESCRIPTION
    "Specifies the VBI line processing function."
::= { enc1P605field2Line7FunctionEntry 1 }

enc1P606field2Line8FunctionTable OBJECT-TYPE
    SYNTAX SEQUENCE OF Enc1P606field2Line8FunctionEntry
    MAX-ACCESS not-accessible
    STATUS     current
    DESCRIPTION
    "
    Name      : Field 2 Line 8 Function
    Menu Path : /Data/VBI
    Details   : Specifies the VBI line processing function.
    "
::= { enc1Params 606 }

enc1P606field2Line8FunctionEntry OBJECT-TYPE
    SYNTAX Enc1P606field2Line8FunctionEntry
    MAX-ACCESS not-accessible
    STATUS     current
    DESCRIPTION
    "Table Entry for Field 2 Line 8 Function"
    INDEX { slotId }
::= { enc1P606field2Line8FunctionTable 1 }

Enc1P606field2Line8FunctionEntry ::= SEQUENCE {
    enc1P606field2Line8FunctionValue    Enc1E112enumObj
}

enc1P606field2Line8FunctionValue OBJECT-TYPE
    SYNTAX     Enc1E112enumObj
    MAX-ACCESS read-write
    STATUS     current
    DESCRIPTION
    "Specifies the VBI line processing function."
::= { enc1P606field2Line8FunctionEntry 1 }

enc1P607field2Line9FunctionTable OBJECT-TYPE
    SYNTAX SEQUENCE OF Enc1P607field2Line9FunctionEntry
    MAX-ACCESS not-accessible
    STATUS     current
    DESCRIPTION
    "
    Name      : Field 2 Line 9 Function
    Menu Path : /Data/VBI
    Details   : Specifies the VBI line processing function.
    "
::= { enc1Params 607 }

enc1P607field2Line9FunctionEntry OBJECT-TYPE
    SYNTAX Enc1P607field2Line9FunctionEntry
    MAX-ACCESS not-accessible
    STATUS     current
    DESCRIPTION
    "Table Entry for Field 2 Line 9 Function"
    INDEX { slotId }
::= { enc1P607field2Line9FunctionTable 1 }

Enc1P607field2Line9FunctionEntry ::= SEQUENCE {
    enc1P607field2Line9FunctionValue    Enc1E112enumObj
}

enc1P607field2Line9FunctionValue OBJECT-TYPE
    SYNTAX     Enc1E112enumObj
    MAX-ACCESS read-write
    STATUS     current
    DESCRIPTION
    "Specifies the VBI line processing function."
::= { enc1P607field2Line9FunctionEntry 1 }

enc1P608field2Line10FunctionTable OBJECT-TYPE
    SYNTAX SEQUENCE OF Enc1P608field2Line10FunctionEntry
    MAX-ACCESS not-accessible
    STATUS     current
    DESCRIPTION
    "
    Name      : Field 2 Line 10 Function
    Menu Path : /Data/VBI
    Details   : Specifies the VBI line processing function.
    "
::= { enc1Params 608 }

enc1P608field2Line10FunctionEntry OBJECT-TYPE
    SYNTAX Enc1P608field2Line10FunctionEntry
    MAX-ACCESS not-accessible
    STATUS     current
    DESCRIPTION
    "Table Entry for Field 2 Line 10 Function"
    INDEX { slotId }
::= { enc1P608field2Line10FunctionTable 1 }

Enc1P608field2Line10FunctionEntry ::= SEQUENCE {
    enc1P608field2Line10FunctionValue    Enc1E112enumObj
}

enc1P608field2Line10FunctionValue OBJECT-TYPE
    SYNTAX     Enc1E112enumObj
    MAX-ACCESS read-write
    STATUS     current
    DESCRIPTION
    "Specifies the VBI line processing function."
::= { enc1P608field2Line10FunctionEntry 1 }

enc1P609field2Line11FunctionTable OBJECT-TYPE
    SYNTAX SEQUENCE OF Enc1P609field2Line11FunctionEntry
    MAX-ACCESS not-accessible
    STATUS     current
    DESCRIPTION
    "
    Name      : Field 2 Line 11 Function
    Menu Path : /Data/VBI
    Details   : Specifies the VBI line processing function.
    "
::= { enc1Params 609 }

enc1P609field2Line11FunctionEntry OBJECT-TYPE
    SYNTAX Enc1P609field2Line11FunctionEntry
    MAX-ACCESS not-accessible
    STATUS     current
    DESCRIPTION
    "Table Entry for Field 2 Line 11 Function"
    INDEX { slotId }
::= { enc1P609field2Line11FunctionTable 1 }

Enc1P609field2Line11FunctionEntry ::= SEQUENCE {
    enc1P609field2Line11FunctionValue    Enc1E112enumObj
}

enc1P609field2Line11FunctionValue OBJECT-TYPE
    SYNTAX     Enc1E112enumObj
    MAX-ACCESS read-write
    STATUS     current
    DESCRIPTION
    "Specifies the VBI line processing function."
::= { enc1P609field2Line11FunctionEntry 1 }

enc1P610field2Line12FunctionTable OBJECT-TYPE
    SYNTAX SEQUENCE OF Enc1P610field2Line12FunctionEntry
    MAX-ACCESS not-accessible
    STATUS     current
    DESCRIPTION
    "
    Name      : Field 2 Line 12 Function
    Menu Path : /Data/VBI
    Details   : Specifies the VBI line processing function.
    "
::= { enc1Params 610 }

enc1P610field2Line12FunctionEntry OBJECT-TYPE
    SYNTAX Enc1P610field2Line12FunctionEntry
    MAX-ACCESS not-accessible
    STATUS     current
    DESCRIPTION
    "Table Entry for Field 2 Line 12 Function"
    INDEX { slotId }
::= { enc1P610field2Line12FunctionTable 1 }

Enc1P610field2Line12FunctionEntry ::= SEQUENCE {
    enc1P610field2Line12FunctionValue    Enc1E112enumObj
}

enc1P610field2Line12FunctionValue OBJECT-TYPE
    SYNTAX     Enc1E112enumObj
    MAX-ACCESS read-write
    STATUS     current
    DESCRIPTION
    "Specifies the VBI line processing function."
::= { enc1P610field2Line12FunctionEntry 1 }

enc1P611field2Line13FunctionTable OBJECT-TYPE
    SYNTAX SEQUENCE OF Enc1P611field2Line13FunctionEntry
    MAX-ACCESS not-accessible
    STATUS     current
    DESCRIPTION
    "
    Name      : Field 2 Line 13 Function
    Menu Path : /Data/VBI
    Details   : Specifies the VBI line processing function.
    "
::= { enc1Params 611 }

enc1P611field2Line13FunctionEntry OBJECT-TYPE
    SYNTAX Enc1P611field2Line13FunctionEntry
    MAX-ACCESS not-accessible
    STATUS     current
    DESCRIPTION
    "Table Entry for Field 2 Line 13 Function"
    INDEX { slotId }
::= { enc1P611field2Line13FunctionTable 1 }

Enc1P611field2Line13FunctionEntry ::= SEQUENCE {
    enc1P611field2Line13FunctionValue    Enc1E112enumObj
}

enc1P611field2Line13FunctionValue OBJECT-TYPE
    SYNTAX     Enc1E112enumObj
    MAX-ACCESS read-write
    STATUS     current
    DESCRIPTION
    "Specifies the VBI line processing function."
::= { enc1P611field2Line13FunctionEntry 1 }

enc1P612field2Line14FunctionTable OBJECT-TYPE
    SYNTAX SEQUENCE OF Enc1P612field2Line14FunctionEntry
    MAX-ACCESS not-accessible
    STATUS     current
    DESCRIPTION
    "
    Name      : Field 2 Line 14 Function
    Menu Path : /Data/VBI
    Details   : Specifies the VBI line processing function.
    "
::= { enc1Params 612 }

enc1P612field2Line14FunctionEntry OBJECT-TYPE
    SYNTAX Enc1P612field2Line14FunctionEntry
    MAX-ACCESS not-accessible
    STATUS     current
    DESCRIPTION
    "Table Entry for Field 2 Line 14 Function"
    INDEX { slotId }
::= { enc1P612field2Line14FunctionTable 1 }

Enc1P612field2Line14FunctionEntry ::= SEQUENCE {
    enc1P612field2Line14FunctionValue    Enc1E112enumObj
}

enc1P612field2Line14FunctionValue OBJECT-TYPE
    SYNTAX     Enc1E112enumObj
    MAX-ACCESS read-write
    STATUS     current
    DESCRIPTION
    "Specifies the VBI line processing function."
::= { enc1P612field2Line14FunctionEntry 1 }

enc1P613field2Line15FunctionTable OBJECT-TYPE
    SYNTAX SEQUENCE OF Enc1P613field2Line15FunctionEntry
    MAX-ACCESS not-accessible
    STATUS     current
    DESCRIPTION
    "
    Name      : Field 2 Line 15 Function
    Menu Path : /Data/VBI
    Details   : Specifies the VBI line processing function.
    "
::= { enc1Params 613 }

enc1P613field2Line15FunctionEntry OBJECT-TYPE
    SYNTAX Enc1P613field2Line15FunctionEntry
    MAX-ACCESS not-accessible
    STATUS     current
    DESCRIPTION
    "Table Entry for Field 2 Line 15 Function"
    INDEX { slotId }
::= { enc1P613field2Line15FunctionTable 1 }

Enc1P613field2Line15FunctionEntry ::= SEQUENCE {
    enc1P613field2Line15FunctionValue    Enc1E112enumObj
}

enc1P613field2Line15FunctionValue OBJECT-TYPE
    SYNTAX     Enc1E112enumObj
    MAX-ACCESS read-write
    STATUS     current
    DESCRIPTION
    "Specifies the VBI line processing function."
::= { enc1P613field2Line15FunctionEntry 1 }

enc1P614field2Line16FunctionTable OBJECT-TYPE
    SYNTAX SEQUENCE OF Enc1P614field2Line16FunctionEntry
    MAX-ACCESS not-accessible
    STATUS     current
    DESCRIPTION
    "
    Name      : Field 2 Line 16 Function
    Menu Path : /Data/VBI
    Details   : Specifies the VBI line processing function.
    "
::= { enc1Params 614 }

enc1P614field2Line16FunctionEntry OBJECT-TYPE
    SYNTAX Enc1P614field2Line16FunctionEntry
    MAX-ACCESS not-accessible
    STATUS     current
    DESCRIPTION
    "Table Entry for Field 2 Line 16 Function"
    INDEX { slotId }
::= { enc1P614field2Line16FunctionTable 1 }

Enc1P614field2Line16FunctionEntry ::= SEQUENCE {
    enc1P614field2Line16FunctionValue    Enc1E112enumObj
}

enc1P614field2Line16FunctionValue OBJECT-TYPE
    SYNTAX     Enc1E112enumObj
    MAX-ACCESS read-write
    STATUS     current
    DESCRIPTION
    "Specifies the VBI line processing function."
::= { enc1P614field2Line16FunctionEntry 1 }

enc1P615field2Line17FunctionTable OBJECT-TYPE
    SYNTAX SEQUENCE OF Enc1P615field2Line17FunctionEntry
    MAX-ACCESS not-accessible
    STATUS     current
    DESCRIPTION
    "
    Name      : Field 2 Line 17 Function
    Menu Path : /Data/VBI
    Details   : Specifies the VBI line processing function.
    "
::= { enc1Params 615 }

enc1P615field2Line17FunctionEntry OBJECT-TYPE
    SYNTAX Enc1P615field2Line17FunctionEntry
    MAX-ACCESS not-accessible
    STATUS     current
    DESCRIPTION
    "Table Entry for Field 2 Line 17 Function"
    INDEX { slotId }
::= { enc1P615field2Line17FunctionTable 1 }

Enc1P615field2Line17FunctionEntry ::= SEQUENCE {
    enc1P615field2Line17FunctionValue    Enc1E112enumObj
}

enc1P615field2Line17FunctionValue OBJECT-TYPE
    SYNTAX     Enc1E112enumObj
    MAX-ACCESS read-write
    STATUS     current
    DESCRIPTION
    "Specifies the VBI line processing function."
::= { enc1P615field2Line17FunctionEntry 1 }

enc1P616field2Line18FunctionTable OBJECT-TYPE
    SYNTAX SEQUENCE OF Enc1P616field2Line18FunctionEntry
    MAX-ACCESS not-accessible
    STATUS     current
    DESCRIPTION
    "
    Name      : Field 2 Line 18 Function
    Menu Path : /Data/VBI
    Details   : Specifies the VBI line processing function.
    "
::= { enc1Params 616 }

enc1P616field2Line18FunctionEntry OBJECT-TYPE
    SYNTAX Enc1P616field2Line18FunctionEntry
    MAX-ACCESS not-accessible
    STATUS     current
    DESCRIPTION
    "Table Entry for Field 2 Line 18 Function"
    INDEX { slotId }
::= { enc1P616field2Line18FunctionTable 1 }

Enc1P616field2Line18FunctionEntry ::= SEQUENCE {
    enc1P616field2Line18FunctionValue    Enc1E112enumObj
}

enc1P616field2Line18FunctionValue OBJECT-TYPE
    SYNTAX     Enc1E112enumObj
    MAX-ACCESS read-write
    STATUS     current
    DESCRIPTION
    "Specifies the VBI line processing function."
::= { enc1P616field2Line18FunctionEntry 1 }

enc1P617field2Line19FunctionTable OBJECT-TYPE
    SYNTAX SEQUENCE OF Enc1P617field2Line19FunctionEntry
    MAX-ACCESS not-accessible
    STATUS     current
    DESCRIPTION
    "
    Name      : Field 2 Line 19 Function
    Menu Path : /Data/VBI
    Details   : Specifies the VBI line processing function.
    "
::= { enc1Params 617 }

enc1P617field2Line19FunctionEntry OBJECT-TYPE
    SYNTAX Enc1P617field2Line19FunctionEntry
    MAX-ACCESS not-accessible
    STATUS     current
    DESCRIPTION
    "Table Entry for Field 2 Line 19 Function"
    INDEX { slotId }
::= { enc1P617field2Line19FunctionTable 1 }

Enc1P617field2Line19FunctionEntry ::= SEQUENCE {
    enc1P617field2Line19FunctionValue    Enc1E112enumObj
}

enc1P617field2Line19FunctionValue OBJECT-TYPE
    SYNTAX     Enc1E112enumObj
    MAX-ACCESS read-write
    STATUS     current
    DESCRIPTION
    "Specifies the VBI line processing function."
::= { enc1P617field2Line19FunctionEntry 1 }

enc1P618field2Line20FunctionTable OBJECT-TYPE
    SYNTAX SEQUENCE OF Enc1P618field2Line20FunctionEntry
    MAX-ACCESS not-accessible
    STATUS     current
    DESCRIPTION
    "
    Name      : Field 2 Line 20 Function
    Menu Path : /Data/VBI
    Details   : Specifies the VBI line processing function.
    "
::= { enc1Params 618 }

enc1P618field2Line20FunctionEntry OBJECT-TYPE
    SYNTAX Enc1P618field2Line20FunctionEntry
    MAX-ACCESS not-accessible
    STATUS     current
    DESCRIPTION
    "Table Entry for Field 2 Line 20 Function"
    INDEX { slotId }
::= { enc1P618field2Line20FunctionTable 1 }

Enc1P618field2Line20FunctionEntry ::= SEQUENCE {
    enc1P618field2Line20FunctionValue    Enc1E112enumObj
}

enc1P618field2Line20FunctionValue OBJECT-TYPE
    SYNTAX     Enc1E112enumObj
    MAX-ACCESS read-write
    STATUS     current
    DESCRIPTION
    "Specifies the VBI line processing function."
::= { enc1P618field2Line20FunctionEntry 1 }

enc1P619field2Line21FunctionTable OBJECT-TYPE
    SYNTAX SEQUENCE OF Enc1P619field2Line21FunctionEntry
    MAX-ACCESS not-accessible
    STATUS     current
    DESCRIPTION
    "
    Name      : Field 2 Line 21 Function
    Menu Path : /Data/VBI
    Details   : Specifies the VBI line processing function.
    "
::= { enc1Params 619 }

enc1P619field2Line21FunctionEntry OBJECT-TYPE
    SYNTAX Enc1P619field2Line21FunctionEntry
    MAX-ACCESS not-accessible
    STATUS     current
    DESCRIPTION
    "Table Entry for Field 2 Line 21 Function"
    INDEX { slotId }
::= { enc1P619field2Line21FunctionTable 1 }

Enc1P619field2Line21FunctionEntry ::= SEQUENCE {
    enc1P619field2Line21FunctionValue    Enc1E112enumObj
}

enc1P619field2Line21FunctionValue OBJECT-TYPE
    SYNTAX     Enc1E112enumObj
    MAX-ACCESS read-write
    STATUS     current
    DESCRIPTION
    "Specifies the VBI line processing function."
::= { enc1P619field2Line21FunctionEntry 1 }

enc1P620field2Line22FunctionTable OBJECT-TYPE
    SYNTAX SEQUENCE OF Enc1P620field2Line22FunctionEntry
    MAX-ACCESS not-accessible
    STATUS     current
    DESCRIPTION
    "
    Name      : Field 2 Line 22 Function
    Menu Path : /Data/VBI
    Details   : Specifies the VBI line processing function.
    "
::= { enc1Params 620 }

enc1P620field2Line22FunctionEntry OBJECT-TYPE
    SYNTAX Enc1P620field2Line22FunctionEntry
    MAX-ACCESS not-accessible
    STATUS     current
    DESCRIPTION
    "Table Entry for Field 2 Line 22 Function"
    INDEX { slotId }
::= { enc1P620field2Line22FunctionTable 1 }

Enc1P620field2Line22FunctionEntry ::= SEQUENCE {
    enc1P620field2Line22FunctionValue    Enc1E112enumObj
}

enc1P620field2Line22FunctionValue OBJECT-TYPE
    SYNTAX     Enc1E112enumObj
    MAX-ACCESS read-write
    STATUS     current
    DESCRIPTION
    "Specifies the VBI line processing function."
::= { enc1P620field2Line22FunctionEntry 1 }

enc1P621errorStatusTable OBJECT-TYPE
    SYNTAX SEQUENCE OF Enc1P621errorStatusEntry
    MAX-ACCESS not-accessible
    STATUS     current
    DESCRIPTION
    "
    Name      : Error Status
    Menu Path : /Data/VBI Status
    Details   : Shows the fault condition for excessive errors in incoming VBI data.
    "
::= { enc1Params 621 }

enc1P621errorStatusEntry OBJECT-TYPE
    SYNTAX Enc1P621errorStatusEntry
    MAX-ACCESS not-accessible
    STATUS     current
    DESCRIPTION
    "Table Entry for Error Status"
    INDEX { slotId }
::= { enc1P621errorStatusTable 1 }

Enc1P621errorStatusEntry ::= SEQUENCE {
    enc1P621errorStatusValue    Enc1E6enumObj
}

enc1P621errorStatusValue OBJECT-TYPE
    SYNTAX     Enc1E6enumObj
    MAX-ACCESS read-only
    STATUS     current
    DESCRIPTION
    "Shows the fault condition for excessive errors in incoming VBI data."
::= { enc1P621errorStatusEntry 1 }

enc1P622field1Line6ErrorTable OBJECT-TYPE
    SYNTAX SEQUENCE OF Enc1P622field1Line6ErrorEntry
    MAX-ACCESS not-accessible
    STATUS     current
    DESCRIPTION
    "
    Name      : Field 1 Line 6 Error
    Menu Path : /Data/VBI Status
    Units     : 
    Precision : 0
    Low Range : 0
    High Range: -1
    Details   : Shows the error count for this VBI line.

     NOTE: Precision/Units/Ranges represent the state of the
           parameter during the MIB generation, and does not
           neccessary reflect the current state of the parameter
    "
::= { enc1Params 622 }

enc1P622field1Line6ErrorEntry OBJECT-TYPE
    SYNTAX Enc1P622field1Line6ErrorEntry
    MAX-ACCESS not-accessible
    STATUS     current
    DESCRIPTION
    "Table Entry for Field 1 Line 6 Error"
    INDEX { slotId }
::= { enc1P622field1Line6ErrorTable 1 }

Enc1P622field1Line6ErrorEntry ::= SEQUENCE {
    enc1P622field1Line6ErrorValue    INTEGER
}

enc1P622field1Line6ErrorValue OBJECT-TYPE
    SYNTAX     INTEGER
    MAX-ACCESS read-only
    STATUS     current
    DESCRIPTION
    "Shows the error count for this VBI line."
::= { enc1P622field1Line6ErrorEntry 1 }

enc1P623field1Line6ServiceTable OBJECT-TYPE
    SYNTAX SEQUENCE OF Enc1P623field1Line6ServiceEntry
    MAX-ACCESS not-accessible
    STATUS     current
    DESCRIPTION
    "
    Name      : Field 1 Line 6 Service
    Menu Path : /Data/VBI Status
    Details   : Shows whether or not this line's service is present.
    "
::= { enc1Params 623 }

enc1P623field1Line6ServiceEntry OBJECT-TYPE
    SYNTAX Enc1P623field1Line6ServiceEntry
    MAX-ACCESS not-accessible
    STATUS     current
    DESCRIPTION
    "Table Entry for Field 1 Line 6 Service"
    INDEX { slotId }
::= { enc1P623field1Line6ServiceTable 1 }

Enc1P623field1Line6ServiceEntry ::= SEQUENCE {
    enc1P623field1Line6ServiceValue    Enc1E9enumObj
}

enc1P623field1Line6ServiceValue OBJECT-TYPE
    SYNTAX     Enc1E9enumObj
    MAX-ACCESS read-only
    STATUS     current
    DESCRIPTION
    "Shows whether or not this line's service is present."
::= { enc1P623field1Line6ServiceEntry 1 }

enc1P624field1Line7ErrorTable OBJECT-TYPE
    SYNTAX SEQUENCE OF Enc1P624field1Line7ErrorEntry
    MAX-ACCESS not-accessible
    STATUS     current
    DESCRIPTION
    "
    Name      : Field 1 Line 7 Error
    Menu Path : /Data/VBI Status
    Units     : 
    Precision : 0
    Low Range : 0
    High Range: -1
    Details   : Shows the error count for this VBI line.

     NOTE: Precision/Units/Ranges represent the state of the
           parameter during the MIB generation, and does not
           neccessary reflect the current state of the parameter
    "
::= { enc1Params 624 }

enc1P624field1Line7ErrorEntry OBJECT-TYPE
    SYNTAX Enc1P624field1Line7ErrorEntry
    MAX-ACCESS not-accessible
    STATUS     current
    DESCRIPTION
    "Table Entry for Field 1 Line 7 Error"
    INDEX { slotId }
::= { enc1P624field1Line7ErrorTable 1 }

Enc1P624field1Line7ErrorEntry ::= SEQUENCE {
    enc1P624field1Line7ErrorValue    INTEGER
}

enc1P624field1Line7ErrorValue OBJECT-TYPE
    SYNTAX     INTEGER
    MAX-ACCESS read-only
    STATUS     current
    DESCRIPTION
    "Shows the error count for this VBI line."
::= { enc1P624field1Line7ErrorEntry 1 }

enc1P625field1Line7ServiceTable OBJECT-TYPE
    SYNTAX SEQUENCE OF Enc1P625field1Line7ServiceEntry
    MAX-ACCESS not-accessible
    STATUS     current
    DESCRIPTION
    "
    Name      : Field 1 Line 7 Service
    Menu Path : /Data/VBI Status
    Details   : Shows whether or not this line's service is present.
    "
::= { enc1Params 625 }

enc1P625field1Line7ServiceEntry OBJECT-TYPE
    SYNTAX Enc1P625field1Line7ServiceEntry
    MAX-ACCESS not-accessible
    STATUS     current
    DESCRIPTION
    "Table Entry for Field 1 Line 7 Service"
    INDEX { slotId }
::= { enc1P625field1Line7ServiceTable 1 }

Enc1P625field1Line7ServiceEntry ::= SEQUENCE {
    enc1P625field1Line7ServiceValue    Enc1E9enumObj
}

enc1P625field1Line7ServiceValue OBJECT-TYPE
    SYNTAX     Enc1E9enumObj
    MAX-ACCESS read-only
    STATUS     current
    DESCRIPTION
    "Shows whether or not this line's service is present."
::= { enc1P625field1Line7ServiceEntry 1 }

enc1P626field1Line8ErrorTable OBJECT-TYPE
    SYNTAX SEQUENCE OF Enc1P626field1Line8ErrorEntry
    MAX-ACCESS not-accessible
    STATUS     current
    DESCRIPTION
    "
    Name      : Field 1 Line 8 Error
    Menu Path : /Data/VBI Status
    Units     : 
    Precision : 0
    Low Range : 0
    High Range: -1
    Details   : Shows the error count for this VBI line.

     NOTE: Precision/Units/Ranges represent the state of the
           parameter during the MIB generation, and does not
           neccessary reflect the current state of the parameter
    "
::= { enc1Params 626 }

enc1P626field1Line8ErrorEntry OBJECT-TYPE
    SYNTAX Enc1P626field1Line8ErrorEntry
    MAX-ACCESS not-accessible
    STATUS     current
    DESCRIPTION
    "Table Entry for Field 1 Line 8 Error"
    INDEX { slotId }
::= { enc1P626field1Line8ErrorTable 1 }

Enc1P626field1Line8ErrorEntry ::= SEQUENCE {
    enc1P626field1Line8ErrorValue    INTEGER
}

enc1P626field1Line8ErrorValue OBJECT-TYPE
    SYNTAX     INTEGER
    MAX-ACCESS read-only
    STATUS     current
    DESCRIPTION
    "Shows the error count for this VBI line."
::= { enc1P626field1Line8ErrorEntry 1 }

enc1P627field1Line8ServiceTable OBJECT-TYPE
    SYNTAX SEQUENCE OF Enc1P627field1Line8ServiceEntry
    MAX-ACCESS not-accessible
    STATUS     current
    DESCRIPTION
    "
    Name      : Field 1 Line 8 Service
    Menu Path : /Data/VBI Status
    Details   : Shows whether or not this line's service is present.
    "
::= { enc1Params 627 }

enc1P627field1Line8ServiceEntry OBJECT-TYPE
    SYNTAX Enc1P627field1Line8ServiceEntry
    MAX-ACCESS not-accessible
    STATUS     current
    DESCRIPTION
    "Table Entry for Field 1 Line 8 Service"
    INDEX { slotId }
::= { enc1P627field1Line8ServiceTable 1 }

Enc1P627field1Line8ServiceEntry ::= SEQUENCE {
    enc1P627field1Line8ServiceValue    Enc1E9enumObj
}

enc1P627field1Line8ServiceValue OBJECT-TYPE
    SYNTAX     Enc1E9enumObj
    MAX-ACCESS read-only
    STATUS     current
    DESCRIPTION
    "Shows whether or not this line's service is present."
::= { enc1P627field1Line8ServiceEntry 1 }

enc1P628field1Line9ErrorTable OBJECT-TYPE
    SYNTAX SEQUENCE OF Enc1P628field1Line9ErrorEntry
    MAX-ACCESS not-accessible
    STATUS     current
    DESCRIPTION
    "
    Name      : Field 1 Line 9 Error
    Menu Path : /Data/VBI Status
    Units     : 
    Precision : 0
    Low Range : 0
    High Range: -1
    Details   : Shows the error count for this VBI line.

     NOTE: Precision/Units/Ranges represent the state of the
           parameter during the MIB generation, and does not
           neccessary reflect the current state of the parameter
    "
::= { enc1Params 628 }

enc1P628field1Line9ErrorEntry OBJECT-TYPE
    SYNTAX Enc1P628field1Line9ErrorEntry
    MAX-ACCESS not-accessible
    STATUS     current
    DESCRIPTION
    "Table Entry for Field 1 Line 9 Error"
    INDEX { slotId }
::= { enc1P628field1Line9ErrorTable 1 }

Enc1P628field1Line9ErrorEntry ::= SEQUENCE {
    enc1P628field1Line9ErrorValue    INTEGER
}

enc1P628field1Line9ErrorValue OBJECT-TYPE
    SYNTAX     INTEGER
    MAX-ACCESS read-only
    STATUS     current
    DESCRIPTION
    "Shows the error count for this VBI line."
::= { enc1P628field1Line9ErrorEntry 1 }

enc1P629field1Line9ServiceTable OBJECT-TYPE
    SYNTAX SEQUENCE OF Enc1P629field1Line9ServiceEntry
    MAX-ACCESS not-accessible
    STATUS     current
    DESCRIPTION
    "
    Name      : Field 1 Line 9 Service
    Menu Path : /Data/VBI Status
    Details   : Shows whether or not this line's service is present.
    "
::= { enc1Params 629 }

enc1P629field1Line9ServiceEntry OBJECT-TYPE
    SYNTAX Enc1P629field1Line9ServiceEntry
    MAX-ACCESS not-accessible
    STATUS     current
    DESCRIPTION
    "Table Entry for Field 1 Line 9 Service"
    INDEX { slotId }
::= { enc1P629field1Line9ServiceTable 1 }

Enc1P629field1Line9ServiceEntry ::= SEQUENCE {
    enc1P629field1Line9ServiceValue    Enc1E9enumObj
}

enc1P629field1Line9ServiceValue OBJECT-TYPE
    SYNTAX     Enc1E9enumObj
    MAX-ACCESS read-only
    STATUS     current
    DESCRIPTION
    "Shows whether or not this line's service is present."
::= { enc1P629field1Line9ServiceEntry 1 }

enc1P630field1Line10ErrorTable OBJECT-TYPE
    SYNTAX SEQUENCE OF Enc1P630field1Line10ErrorEntry
    MAX-ACCESS not-accessible
    STATUS     current
    DESCRIPTION
    "
    Name      : Field 1 Line 10 Error
    Menu Path : /Data/VBI Status
    Units     : 
    Precision : 0
    Low Range : 0
    High Range: -1
    Details   : Shows the error count for this VBI line.

     NOTE: Precision/Units/Ranges represent the state of the
           parameter during the MIB generation, and does not
           neccessary reflect the current state of the parameter
    "
::= { enc1Params 630 }

enc1P630field1Line10ErrorEntry OBJECT-TYPE
    SYNTAX Enc1P630field1Line10ErrorEntry
    MAX-ACCESS not-accessible
    STATUS     current
    DESCRIPTION
    "Table Entry for Field 1 Line 10 Error"
    INDEX { slotId }
::= { enc1P630field1Line10ErrorTable 1 }

Enc1P630field1Line10ErrorEntry ::= SEQUENCE {
    enc1P630field1Line10ErrorValue    INTEGER
}

enc1P630field1Line10ErrorValue OBJECT-TYPE
    SYNTAX     INTEGER
    MAX-ACCESS read-only
    STATUS     current
    DESCRIPTION
    "Shows the error count for this VBI line."
::= { enc1P630field1Line10ErrorEntry 1 }

enc1P631field1Line10ServiceTable OBJECT-TYPE
    SYNTAX SEQUENCE OF Enc1P631field1Line10ServiceEntry
    MAX-ACCESS not-accessible
    STATUS     current
    DESCRIPTION
    "
    Name      : Field 1 Line 10 Service
    Menu Path : /Data/VBI Status
    Details   : Shows whether or not this line's service is present.
    "
::= { enc1Params 631 }

enc1P631field1Line10ServiceEntry OBJECT-TYPE
    SYNTAX Enc1P631field1Line10ServiceEntry
    MAX-ACCESS not-accessible
    STATUS     current
    DESCRIPTION
    "Table Entry for Field 1 Line 10 Service"
    INDEX { slotId }
::= { enc1P631field1Line10ServiceTable 1 }

Enc1P631field1Line10ServiceEntry ::= SEQUENCE {
    enc1P631field1Line10ServiceValue    Enc1E9enumObj
}

enc1P631field1Line10ServiceValue OBJECT-TYPE
    SYNTAX     Enc1E9enumObj
    MAX-ACCESS read-only
    STATUS     current
    DESCRIPTION
    "Shows whether or not this line's service is present."
::= { enc1P631field1Line10ServiceEntry 1 }

enc1P632field1Line11ErrorTable OBJECT-TYPE
    SYNTAX SEQUENCE OF Enc1P632field1Line11ErrorEntry
    MAX-ACCESS not-accessible
    STATUS     current
    DESCRIPTION
    "
    Name      : Field 1 Line 11 Error
    Menu Path : /Data/VBI Status
    Units     : 
    Precision : 0
    Low Range : 0
    High Range: -1
    Details   : Shows the error count for this VBI line.

     NOTE: Precision/Units/Ranges represent the state of the
           parameter during the MIB generation, and does not
           neccessary reflect the current state of the parameter
    "
::= { enc1Params 632 }

enc1P632field1Line11ErrorEntry OBJECT-TYPE
    SYNTAX Enc1P632field1Line11ErrorEntry
    MAX-ACCESS not-accessible
    STATUS     current
    DESCRIPTION
    "Table Entry for Field 1 Line 11 Error"
    INDEX { slotId }
::= { enc1P632field1Line11ErrorTable 1 }

Enc1P632field1Line11ErrorEntry ::= SEQUENCE {
    enc1P632field1Line11ErrorValue    INTEGER
}

enc1P632field1Line11ErrorValue OBJECT-TYPE
    SYNTAX     INTEGER
    MAX-ACCESS read-only
    STATUS     current
    DESCRIPTION
    "Shows the error count for this VBI line."
::= { enc1P632field1Line11ErrorEntry 1 }

enc1P633field1Line11ServiceTable OBJECT-TYPE
    SYNTAX SEQUENCE OF Enc1P633field1Line11ServiceEntry
    MAX-ACCESS not-accessible
    STATUS     current
    DESCRIPTION
    "
    Name      : Field 1 Line 11 Service
    Menu Path : /Data/VBI Status
    Details   : Shows whether or not this line's service is present.
    "
::= { enc1Params 633 }

enc1P633field1Line11ServiceEntry OBJECT-TYPE
    SYNTAX Enc1P633field1Line11ServiceEntry
    MAX-ACCESS not-accessible
    STATUS     current
    DESCRIPTION
    "Table Entry for Field 1 Line 11 Service"
    INDEX { slotId }
::= { enc1P633field1Line11ServiceTable 1 }

Enc1P633field1Line11ServiceEntry ::= SEQUENCE {
    enc1P633field1Line11ServiceValue    Enc1E9enumObj
}

enc1P633field1Line11ServiceValue OBJECT-TYPE
    SYNTAX     Enc1E9enumObj
    MAX-ACCESS read-only
    STATUS     current
    DESCRIPTION
    "Shows whether or not this line's service is present."
::= { enc1P633field1Line11ServiceEntry 1 }

enc1P634field1Line12ErrorTable OBJECT-TYPE
    SYNTAX SEQUENCE OF Enc1P634field1Line12ErrorEntry
    MAX-ACCESS not-accessible
    STATUS     current
    DESCRIPTION
    "
    Name      : Field 1 Line 12 Error
    Menu Path : /Data/VBI Status
    Units     : 
    Precision : 0
    Low Range : 0
    High Range: -1
    Details   : Shows the error count for this VBI line.

     NOTE: Precision/Units/Ranges represent the state of the
           parameter during the MIB generation, and does not
           neccessary reflect the current state of the parameter
    "
::= { enc1Params 634 }

enc1P634field1Line12ErrorEntry OBJECT-TYPE
    SYNTAX Enc1P634field1Line12ErrorEntry
    MAX-ACCESS not-accessible
    STATUS     current
    DESCRIPTION
    "Table Entry for Field 1 Line 12 Error"
    INDEX { slotId }
::= { enc1P634field1Line12ErrorTable 1 }

Enc1P634field1Line12ErrorEntry ::= SEQUENCE {
    enc1P634field1Line12ErrorValue    INTEGER
}

enc1P634field1Line12ErrorValue OBJECT-TYPE
    SYNTAX     INTEGER
    MAX-ACCESS read-only
    STATUS     current
    DESCRIPTION
    "Shows the error count for this VBI line."
::= { enc1P634field1Line12ErrorEntry 1 }

enc1P635field1Line12ServiceTable OBJECT-TYPE
    SYNTAX SEQUENCE OF Enc1P635field1Line12ServiceEntry
    MAX-ACCESS not-accessible
    STATUS     current
    DESCRIPTION
    "
    Name      : Field 1 Line 12 Service
    Menu Path : /Data/VBI Status
    Details   : Shows whether or not this line's service is present.
    "
::= { enc1Params 635 }

enc1P635field1Line12ServiceEntry OBJECT-TYPE
    SYNTAX Enc1P635field1Line12ServiceEntry
    MAX-ACCESS not-accessible
    STATUS     current
    DESCRIPTION
    "Table Entry for Field 1 Line 12 Service"
    INDEX { slotId }
::= { enc1P635field1Line12ServiceTable 1 }

Enc1P635field1Line12ServiceEntry ::= SEQUENCE {
    enc1P635field1Line12ServiceValue    Enc1E9enumObj
}

enc1P635field1Line12ServiceValue OBJECT-TYPE
    SYNTAX     Enc1E9enumObj
    MAX-ACCESS read-only
    STATUS     current
    DESCRIPTION
    "Shows whether or not this line's service is present."
::= { enc1P635field1Line12ServiceEntry 1 }

enc1P636field1Line13ErrorTable OBJECT-TYPE
    SYNTAX SEQUENCE OF Enc1P636field1Line13ErrorEntry
    MAX-ACCESS not-accessible
    STATUS     current
    DESCRIPTION
    "
    Name      : Field 1 Line 13 Error
    Menu Path : /Data/VBI Status
    Units     : 
    Precision : 0
    Low Range : 0
    High Range: -1
    Details   : Shows the error count for this VBI line.

     NOTE: Precision/Units/Ranges represent the state of the
           parameter during the MIB generation, and does not
           neccessary reflect the current state of the parameter
    "
::= { enc1Params 636 }

enc1P636field1Line13ErrorEntry OBJECT-TYPE
    SYNTAX Enc1P636field1Line13ErrorEntry
    MAX-ACCESS not-accessible
    STATUS     current
    DESCRIPTION
    "Table Entry for Field 1 Line 13 Error"
    INDEX { slotId }
::= { enc1P636field1Line13ErrorTable 1 }

Enc1P636field1Line13ErrorEntry ::= SEQUENCE {
    enc1P636field1Line13ErrorValue    INTEGER
}

enc1P636field1Line13ErrorValue OBJECT-TYPE
    SYNTAX     INTEGER
    MAX-ACCESS read-only
    STATUS     current
    DESCRIPTION
    "Shows the error count for this VBI line."
::= { enc1P636field1Line13ErrorEntry 1 }

enc1P637field1Line13ServiceTable OBJECT-TYPE
    SYNTAX SEQUENCE OF Enc1P637field1Line13ServiceEntry
    MAX-ACCESS not-accessible
    STATUS     current
    DESCRIPTION
    "
    Name      : Field 1 Line 13 Service
    Menu Path : /Data/VBI Status
    Details   : Shows whether or not this line's service is present.
    "
::= { enc1Params 637 }

enc1P637field1Line13ServiceEntry OBJECT-TYPE
    SYNTAX Enc1P637field1Line13ServiceEntry
    MAX-ACCESS not-accessible
    STATUS     current
    DESCRIPTION
    "Table Entry for Field 1 Line 13 Service"
    INDEX { slotId }
::= { enc1P637field1Line13ServiceTable 1 }

Enc1P637field1Line13ServiceEntry ::= SEQUENCE {
    enc1P637field1Line13ServiceValue    Enc1E9enumObj
}

enc1P637field1Line13ServiceValue OBJECT-TYPE
    SYNTAX     Enc1E9enumObj
    MAX-ACCESS read-only
    STATUS     current
    DESCRIPTION
    "Shows whether or not this line's service is present."
::= { enc1P637field1Line13ServiceEntry 1 }

enc1P638field1Line14ErrorTable OBJECT-TYPE
    SYNTAX SEQUENCE OF Enc1P638field1Line14ErrorEntry
    MAX-ACCESS not-accessible
    STATUS     current
    DESCRIPTION
    "
    Name      : Field 1 Line 14 Error
    Menu Path : /Data/VBI Status
    Units     : 
    Precision : 0
    Low Range : 0
    High Range: -1
    Details   : Shows the error count for this VBI line.

     NOTE: Precision/Units/Ranges represent the state of the
           parameter during the MIB generation, and does not
           neccessary reflect the current state of the parameter
    "
::= { enc1Params 638 }

enc1P638field1Line14ErrorEntry OBJECT-TYPE
    SYNTAX Enc1P638field1Line14ErrorEntry
    MAX-ACCESS not-accessible
    STATUS     current
    DESCRIPTION
    "Table Entry for Field 1 Line 14 Error"
    INDEX { slotId }
::= { enc1P638field1Line14ErrorTable 1 }

Enc1P638field1Line14ErrorEntry ::= SEQUENCE {
    enc1P638field1Line14ErrorValue    INTEGER
}

enc1P638field1Line14ErrorValue OBJECT-TYPE
    SYNTAX     INTEGER
    MAX-ACCESS read-only
    STATUS     current
    DESCRIPTION
    "Shows the error count for this VBI line."
::= { enc1P638field1Line14ErrorEntry 1 }

enc1P639field1Line14ServiceTable OBJECT-TYPE
    SYNTAX SEQUENCE OF Enc1P639field1Line14ServiceEntry
    MAX-ACCESS not-accessible
    STATUS     current
    DESCRIPTION
    "
    Name      : Field 1 Line 14 Service
    Menu Path : /Data/VBI Status
    Details   : Shows whether or not this line's service is present.
    "
::= { enc1Params 639 }

enc1P639field1Line14ServiceEntry OBJECT-TYPE
    SYNTAX Enc1P639field1Line14ServiceEntry
    MAX-ACCESS not-accessible
    STATUS     current
    DESCRIPTION
    "Table Entry for Field 1 Line 14 Service"
    INDEX { slotId }
::= { enc1P639field1Line14ServiceTable 1 }

Enc1P639field1Line14ServiceEntry ::= SEQUENCE {
    enc1P639field1Line14ServiceValue    Enc1E9enumObj
}

enc1P639field1Line14ServiceValue OBJECT-TYPE
    SYNTAX     Enc1E9enumObj
    MAX-ACCESS read-only
    STATUS     current
    DESCRIPTION
    "Shows whether or not this line's service is present."
::= { enc1P639field1Line14ServiceEntry 1 }

enc1P640field1Line15ErrorTable OBJECT-TYPE
    SYNTAX SEQUENCE OF Enc1P640field1Line15ErrorEntry
    MAX-ACCESS not-accessible
    STATUS     current
    DESCRIPTION
    "
    Name      : Field 1 Line 15 Error
    Menu Path : /Data/VBI Status
    Units     : 
    Precision : 0
    Low Range : 0
    High Range: -1
    Details   : Shows the error count for this VBI line.

     NOTE: Precision/Units/Ranges represent the state of the
           parameter during the MIB generation, and does not
           neccessary reflect the current state of the parameter
    "
::= { enc1Params 640 }

enc1P640field1Line15ErrorEntry OBJECT-TYPE
    SYNTAX Enc1P640field1Line15ErrorEntry
    MAX-ACCESS not-accessible
    STATUS     current
    DESCRIPTION
    "Table Entry for Field 1 Line 15 Error"
    INDEX { slotId }
::= { enc1P640field1Line15ErrorTable 1 }

Enc1P640field1Line15ErrorEntry ::= SEQUENCE {
    enc1P640field1Line15ErrorValue    INTEGER
}

enc1P640field1Line15ErrorValue OBJECT-TYPE
    SYNTAX     INTEGER
    MAX-ACCESS read-only
    STATUS     current
    DESCRIPTION
    "Shows the error count for this VBI line."
::= { enc1P640field1Line15ErrorEntry 1 }

enc1P641field1Line15ServiceTable OBJECT-TYPE
    SYNTAX SEQUENCE OF Enc1P641field1Line15ServiceEntry
    MAX-ACCESS not-accessible
    STATUS     current
    DESCRIPTION
    "
    Name      : Field 1 Line 15 Service
    Menu Path : /Data/VBI Status
    Details   : Shows whether or not this line's service is present.
    "
::= { enc1Params 641 }

enc1P641field1Line15ServiceEntry OBJECT-TYPE
    SYNTAX Enc1P641field1Line15ServiceEntry
    MAX-ACCESS not-accessible
    STATUS     current
    DESCRIPTION
    "Table Entry for Field 1 Line 15 Service"
    INDEX { slotId }
::= { enc1P641field1Line15ServiceTable 1 }

Enc1P641field1Line15ServiceEntry ::= SEQUENCE {
    enc1P641field1Line15ServiceValue    Enc1E9enumObj
}

enc1P641field1Line15ServiceValue OBJECT-TYPE
    SYNTAX     Enc1E9enumObj
    MAX-ACCESS read-only
    STATUS     current
    DESCRIPTION
    "Shows whether or not this line's service is present."
::= { enc1P641field1Line15ServiceEntry 1 }

enc1P642field1Line16ErrorTable OBJECT-TYPE
    SYNTAX SEQUENCE OF Enc1P642field1Line16ErrorEntry
    MAX-ACCESS not-accessible
    STATUS     current
    DESCRIPTION
    "
    Name      : Field 1 Line 16 Error
    Menu Path : /Data/VBI Status
    Units     : 
    Precision : 0
    Low Range : 0
    High Range: -1
    Details   : Shows the error count for this VBI line.

     NOTE: Precision/Units/Ranges represent the state of the
           parameter during the MIB generation, and does not
           neccessary reflect the current state of the parameter
    "
::= { enc1Params 642 }

enc1P642field1Line16ErrorEntry OBJECT-TYPE
    SYNTAX Enc1P642field1Line16ErrorEntry
    MAX-ACCESS not-accessible
    STATUS     current
    DESCRIPTION
    "Table Entry for Field 1 Line 16 Error"
    INDEX { slotId }
::= { enc1P642field1Line16ErrorTable 1 }

Enc1P642field1Line16ErrorEntry ::= SEQUENCE {
    enc1P642field1Line16ErrorValue    INTEGER
}

enc1P642field1Line16ErrorValue OBJECT-TYPE
    SYNTAX     INTEGER
    MAX-ACCESS read-only
    STATUS     current
    DESCRIPTION
    "Shows the error count for this VBI line."
::= { enc1P642field1Line16ErrorEntry 1 }

enc1P643field1Line16ServiceTable OBJECT-TYPE
    SYNTAX SEQUENCE OF Enc1P643field1Line16ServiceEntry
    MAX-ACCESS not-accessible
    STATUS     current
    DESCRIPTION
    "
    Name      : Field 1 Line 16 Service
    Menu Path : /Data/VBI Status
    Details   : Shows whether or not this line's service is present.
    "
::= { enc1Params 643 }

enc1P643field1Line16ServiceEntry OBJECT-TYPE
    SYNTAX Enc1P643field1Line16ServiceEntry
    MAX-ACCESS not-accessible
    STATUS     current
    DESCRIPTION
    "Table Entry for Field 1 Line 16 Service"
    INDEX { slotId }
::= { enc1P643field1Line16ServiceTable 1 }

Enc1P643field1Line16ServiceEntry ::= SEQUENCE {
    enc1P643field1Line16ServiceValue    Enc1E9enumObj
}

enc1P643field1Line16ServiceValue OBJECT-TYPE
    SYNTAX     Enc1E9enumObj
    MAX-ACCESS read-only
    STATUS     current
    DESCRIPTION
    "Shows whether or not this line's service is present."
::= { enc1P643field1Line16ServiceEntry 1 }

enc1P644field1Line17ErrorTable OBJECT-TYPE
    SYNTAX SEQUENCE OF Enc1P644field1Line17ErrorEntry
    MAX-ACCESS not-accessible
    STATUS     current
    DESCRIPTION
    "
    Name      : Field 1 Line 17 Error
    Menu Path : /Data/VBI Status
    Units     : 
    Precision : 0
    Low Range : 0
    High Range: -1
    Details   : Shows the error count for this VBI line.

     NOTE: Precision/Units/Ranges represent the state of the
           parameter during the MIB generation, and does not
           neccessary reflect the current state of the parameter
    "
::= { enc1Params 644 }

enc1P644field1Line17ErrorEntry OBJECT-TYPE
    SYNTAX Enc1P644field1Line17ErrorEntry
    MAX-ACCESS not-accessible
    STATUS     current
    DESCRIPTION
    "Table Entry for Field 1 Line 17 Error"
    INDEX { slotId }
::= { enc1P644field1Line17ErrorTable 1 }

Enc1P644field1Line17ErrorEntry ::= SEQUENCE {
    enc1P644field1Line17ErrorValue    INTEGER
}

enc1P644field1Line17ErrorValue OBJECT-TYPE
    SYNTAX     INTEGER
    MAX-ACCESS read-only
    STATUS     current
    DESCRIPTION
    "Shows the error count for this VBI line."
::= { enc1P644field1Line17ErrorEntry 1 }

enc1P645field1Line17ServiceTable OBJECT-TYPE
    SYNTAX SEQUENCE OF Enc1P645field1Line17ServiceEntry
    MAX-ACCESS not-accessible
    STATUS     current
    DESCRIPTION
    "
    Name      : Field 1 Line 17 Service
    Menu Path : /Data/VBI Status
    Details   : Shows whether or not this line's service is present.
    "
::= { enc1Params 645 }

enc1P645field1Line17ServiceEntry OBJECT-TYPE
    SYNTAX Enc1P645field1Line17ServiceEntry
    MAX-ACCESS not-accessible
    STATUS     current
    DESCRIPTION
    "Table Entry for Field 1 Line 17 Service"
    INDEX { slotId }
::= { enc1P645field1Line17ServiceTable 1 }

Enc1P645field1Line17ServiceEntry ::= SEQUENCE {
    enc1P645field1Line17ServiceValue    Enc1E9enumObj
}

enc1P645field1Line17ServiceValue OBJECT-TYPE
    SYNTAX     Enc1E9enumObj
    MAX-ACCESS read-only
    STATUS     current
    DESCRIPTION
    "Shows whether or not this line's service is present."
::= { enc1P645field1Line17ServiceEntry 1 }

enc1P646field1Line18ErrorTable OBJECT-TYPE
    SYNTAX SEQUENCE OF Enc1P646field1Line18ErrorEntry
    MAX-ACCESS not-accessible
    STATUS     current
    DESCRIPTION
    "
    Name      : Field 1 Line 18 Error
    Menu Path : /Data/VBI Status
    Units     : 
    Precision : 0
    Low Range : 0
    High Range: -1
    Details   : Shows the error count for this VBI line.

     NOTE: Precision/Units/Ranges represent the state of the
           parameter during the MIB generation, and does not
           neccessary reflect the current state of the parameter
    "
::= { enc1Params 646 }

enc1P646field1Line18ErrorEntry OBJECT-TYPE
    SYNTAX Enc1P646field1Line18ErrorEntry
    MAX-ACCESS not-accessible
    STATUS     current
    DESCRIPTION
    "Table Entry for Field 1 Line 18 Error"
    INDEX { slotId }
::= { enc1P646field1Line18ErrorTable 1 }

Enc1P646field1Line18ErrorEntry ::= SEQUENCE {
    enc1P646field1Line18ErrorValue    INTEGER
}

enc1P646field1Line18ErrorValue OBJECT-TYPE
    SYNTAX     INTEGER
    MAX-ACCESS read-only
    STATUS     current
    DESCRIPTION
    "Shows the error count for this VBI line."
::= { enc1P646field1Line18ErrorEntry 1 }

enc1P647field1Line18ServiceTable OBJECT-TYPE
    SYNTAX SEQUENCE OF Enc1P647field1Line18ServiceEntry
    MAX-ACCESS not-accessible
    STATUS     current
    DESCRIPTION
    "
    Name      : Field 1 Line 18 Service
    Menu Path : /Data/VBI Status
    Details   : Shows whether or not this line's service is present.
    "
::= { enc1Params 647 }

enc1P647field1Line18ServiceEntry OBJECT-TYPE
    SYNTAX Enc1P647field1Line18ServiceEntry
    MAX-ACCESS not-accessible
    STATUS     current
    DESCRIPTION
    "Table Entry for Field 1 Line 18 Service"
    INDEX { slotId }
::= { enc1P647field1Line18ServiceTable 1 }

Enc1P647field1Line18ServiceEntry ::= SEQUENCE {
    enc1P647field1Line18ServiceValue    Enc1E9enumObj
}

enc1P647field1Line18ServiceValue OBJECT-TYPE
    SYNTAX     Enc1E9enumObj
    MAX-ACCESS read-only
    STATUS     current
    DESCRIPTION
    "Shows whether or not this line's service is present."
::= { enc1P647field1Line18ServiceEntry 1 }

enc1P648field1Line19ErrorTable OBJECT-TYPE
    SYNTAX SEQUENCE OF Enc1P648field1Line19ErrorEntry
    MAX-ACCESS not-accessible
    STATUS     current
    DESCRIPTION
    "
    Name      : Field 1 Line 19 Error
    Menu Path : /Data/VBI Status
    Units     : 
    Precision : 0
    Low Range : 0
    High Range: -1
    Details   : Shows the error count for this VBI line.

     NOTE: Precision/Units/Ranges represent the state of the
           parameter during the MIB generation, and does not
           neccessary reflect the current state of the parameter
    "
::= { enc1Params 648 }

enc1P648field1Line19ErrorEntry OBJECT-TYPE
    SYNTAX Enc1P648field1Line19ErrorEntry
    MAX-ACCESS not-accessible
    STATUS     current
    DESCRIPTION
    "Table Entry for Field 1 Line 19 Error"
    INDEX { slotId }
::= { enc1P648field1Line19ErrorTable 1 }

Enc1P648field1Line19ErrorEntry ::= SEQUENCE {
    enc1P648field1Line19ErrorValue    INTEGER
}

enc1P648field1Line19ErrorValue OBJECT-TYPE
    SYNTAX     INTEGER
    MAX-ACCESS read-only
    STATUS     current
    DESCRIPTION
    "Shows the error count for this VBI line."
::= { enc1P648field1Line19ErrorEntry 1 }

enc1P649field1Line19ServiceTable OBJECT-TYPE
    SYNTAX SEQUENCE OF Enc1P649field1Line19ServiceEntry
    MAX-ACCESS not-accessible
    STATUS     current
    DESCRIPTION
    "
    Name      : Field 1 Line 19 Service
    Menu Path : /Data/VBI Status
    Details   : Shows whether or not this line's service is present.
    "
::= { enc1Params 649 }

enc1P649field1Line19ServiceEntry OBJECT-TYPE
    SYNTAX Enc1P649field1Line19ServiceEntry
    MAX-ACCESS not-accessible
    STATUS     current
    DESCRIPTION
    "Table Entry for Field 1 Line 19 Service"
    INDEX { slotId }
::= { enc1P649field1Line19ServiceTable 1 }

Enc1P649field1Line19ServiceEntry ::= SEQUENCE {
    enc1P649field1Line19ServiceValue    Enc1E9enumObj
}

enc1P649field1Line19ServiceValue OBJECT-TYPE
    SYNTAX     Enc1E9enumObj
    MAX-ACCESS read-only
    STATUS     current
    DESCRIPTION
    "Shows whether or not this line's service is present."
::= { enc1P649field1Line19ServiceEntry 1 }

enc1P650field1Line20ErrorTable OBJECT-TYPE
    SYNTAX SEQUENCE OF Enc1P650field1Line20ErrorEntry
    MAX-ACCESS not-accessible
    STATUS     current
    DESCRIPTION
    "
    Name      : Field 1 Line 20 Error
    Menu Path : /Data/VBI Status
    Units     : 
    Precision : 0
    Low Range : 0
    High Range: -1
    Details   : Shows the error count for this VBI line.

     NOTE: Precision/Units/Ranges represent the state of the
           parameter during the MIB generation, and does not
           neccessary reflect the current state of the parameter
    "
::= { enc1Params 650 }

enc1P650field1Line20ErrorEntry OBJECT-TYPE
    SYNTAX Enc1P650field1Line20ErrorEntry
    MAX-ACCESS not-accessible
    STATUS     current
    DESCRIPTION
    "Table Entry for Field 1 Line 20 Error"
    INDEX { slotId }
::= { enc1P650field1Line20ErrorTable 1 }

Enc1P650field1Line20ErrorEntry ::= SEQUENCE {
    enc1P650field1Line20ErrorValue    INTEGER
}

enc1P650field1Line20ErrorValue OBJECT-TYPE
    SYNTAX     INTEGER
    MAX-ACCESS read-only
    STATUS     current
    DESCRIPTION
    "Shows the error count for this VBI line."
::= { enc1P650field1Line20ErrorEntry 1 }

enc1P651field1Line20ServiceTable OBJECT-TYPE
    SYNTAX SEQUENCE OF Enc1P651field1Line20ServiceEntry
    MAX-ACCESS not-accessible
    STATUS     current
    DESCRIPTION
    "
    Name      : Field 1 Line 20 Service
    Menu Path : /Data/VBI Status
    Details   : Shows whether or not this line's service is present.
    "
::= { enc1Params 651 }

enc1P651field1Line20ServiceEntry OBJECT-TYPE
    SYNTAX Enc1P651field1Line20ServiceEntry
    MAX-ACCESS not-accessible
    STATUS     current
    DESCRIPTION
    "Table Entry for Field 1 Line 20 Service"
    INDEX { slotId }
::= { enc1P651field1Line20ServiceTable 1 }

Enc1P651field1Line20ServiceEntry ::= SEQUENCE {
    enc1P651field1Line20ServiceValue    Enc1E9enumObj
}

enc1P651field1Line20ServiceValue OBJECT-TYPE
    SYNTAX     Enc1E9enumObj
    MAX-ACCESS read-only
    STATUS     current
    DESCRIPTION
    "Shows whether or not this line's service is present."
::= { enc1P651field1Line20ServiceEntry 1 }

enc1P652field1Line21ErrorTable OBJECT-TYPE
    SYNTAX SEQUENCE OF Enc1P652field1Line21ErrorEntry
    MAX-ACCESS not-accessible
    STATUS     current
    DESCRIPTION
    "
    Name      : Field 1 Line 21 Error
    Menu Path : /Data/VBI Status
    Units     : 
    Precision : 0
    Low Range : 0
    High Range: -1
    Details   : Shows the error count for this VBI line.

     NOTE: Precision/Units/Ranges represent the state of the
           parameter during the MIB generation, and does not
           neccessary reflect the current state of the parameter
    "
::= { enc1Params 652 }

enc1P652field1Line21ErrorEntry OBJECT-TYPE
    SYNTAX Enc1P652field1Line21ErrorEntry
    MAX-ACCESS not-accessible
    STATUS     current
    DESCRIPTION
    "Table Entry for Field 1 Line 21 Error"
    INDEX { slotId }
::= { enc1P652field1Line21ErrorTable 1 }

Enc1P652field1Line21ErrorEntry ::= SEQUENCE {
    enc1P652field1Line21ErrorValue    INTEGER
}

enc1P652field1Line21ErrorValue OBJECT-TYPE
    SYNTAX     INTEGER
    MAX-ACCESS read-only
    STATUS     current
    DESCRIPTION
    "Shows the error count for this VBI line."
::= { enc1P652field1Line21ErrorEntry 1 }

enc1P653field1Line21ServiceTable OBJECT-TYPE
    SYNTAX SEQUENCE OF Enc1P653field1Line21ServiceEntry
    MAX-ACCESS not-accessible
    STATUS     current
    DESCRIPTION
    "
    Name      : Field 1 Line 21 Service
    Menu Path : /Data/VBI Status
    Details   : Shows whether or not this line's service is present.
    "
::= { enc1Params 653 }

enc1P653field1Line21ServiceEntry OBJECT-TYPE
    SYNTAX Enc1P653field1Line21ServiceEntry
    MAX-ACCESS not-accessible
    STATUS     current
    DESCRIPTION
    "Table Entry for Field 1 Line 21 Service"
    INDEX { slotId }
::= { enc1P653field1Line21ServiceTable 1 }

Enc1P653field1Line21ServiceEntry ::= SEQUENCE {
    enc1P653field1Line21ServiceValue    Enc1E9enumObj
}

enc1P653field1Line21ServiceValue OBJECT-TYPE
    SYNTAX     Enc1E9enumObj
    MAX-ACCESS read-only
    STATUS     current
    DESCRIPTION
    "Shows whether or not this line's service is present."
::= { enc1P653field1Line21ServiceEntry 1 }

enc1P654field1Line22ErrorTable OBJECT-TYPE
    SYNTAX SEQUENCE OF Enc1P654field1Line22ErrorEntry
    MAX-ACCESS not-accessible
    STATUS     current
    DESCRIPTION
    "
    Name      : Field 1 Line 22 Error
    Menu Path : /Data/VBI Status
    Units     : 
    Precision : 0
    Low Range : 0
    High Range: -1
    Details   : Shows the error count for this VBI line.

     NOTE: Precision/Units/Ranges represent the state of the
           parameter during the MIB generation, and does not
           neccessary reflect the current state of the parameter
    "
::= { enc1Params 654 }

enc1P654field1Line22ErrorEntry OBJECT-TYPE
    SYNTAX Enc1P654field1Line22ErrorEntry
    MAX-ACCESS not-accessible
    STATUS     current
    DESCRIPTION
    "Table Entry for Field 1 Line 22 Error"
    INDEX { slotId }
::= { enc1P654field1Line22ErrorTable 1 }

Enc1P654field1Line22ErrorEntry ::= SEQUENCE {
    enc1P654field1Line22ErrorValue    INTEGER
}

enc1P654field1Line22ErrorValue OBJECT-TYPE
    SYNTAX     INTEGER
    MAX-ACCESS read-only
    STATUS     current
    DESCRIPTION
    "Shows the error count for this VBI line."
::= { enc1P654field1Line22ErrorEntry 1 }

enc1P655field1Line22ServiceTable OBJECT-TYPE
    SYNTAX SEQUENCE OF Enc1P655field1Line22ServiceEntry
    MAX-ACCESS not-accessible
    STATUS     current
    DESCRIPTION
    "
    Name      : Field 1 Line 22 Service
    Menu Path : /Data/VBI Status
    Details   : Shows whether or not this line's service is present.
    "
::= { enc1Params 655 }

enc1P655field1Line22ServiceEntry OBJECT-TYPE
    SYNTAX Enc1P655field1Line22ServiceEntry
    MAX-ACCESS not-accessible
    STATUS     current
    DESCRIPTION
    "Table Entry for Field 1 Line 22 Service"
    INDEX { slotId }
::= { enc1P655field1Line22ServiceTable 1 }

Enc1P655field1Line22ServiceEntry ::= SEQUENCE {
    enc1P655field1Line22ServiceValue    Enc1E9enumObj
}

enc1P655field1Line22ServiceValue OBJECT-TYPE
    SYNTAX     Enc1E9enumObj
    MAX-ACCESS read-only
    STATUS     current
    DESCRIPTION
    "Shows whether or not this line's service is present."
::= { enc1P655field1Line22ServiceEntry 1 }

enc1P656field1Line23ErrorTable OBJECT-TYPE
    SYNTAX SEQUENCE OF Enc1P656field1Line23ErrorEntry
    MAX-ACCESS not-accessible
    STATUS     current
    DESCRIPTION
    "
    Name      : Field 1 Line 23 Error
    Menu Path : /Data/VBI Status
    Units     : 
    Precision : 0
    Low Range : 0
    High Range: -1
    Details   : Shows the error count for this VBI line.

     NOTE: Precision/Units/Ranges represent the state of the
           parameter during the MIB generation, and does not
           neccessary reflect the current state of the parameter
    "
::= { enc1Params 656 }

enc1P656field1Line23ErrorEntry OBJECT-TYPE
    SYNTAX Enc1P656field1Line23ErrorEntry
    MAX-ACCESS not-accessible
    STATUS     current
    DESCRIPTION
    "Table Entry for Field 1 Line 23 Error"
    INDEX { slotId }
::= { enc1P656field1Line23ErrorTable 1 }

Enc1P656field1Line23ErrorEntry ::= SEQUENCE {
    enc1P656field1Line23ErrorValue    INTEGER
}

enc1P656field1Line23ErrorValue OBJECT-TYPE
    SYNTAX     INTEGER
    MAX-ACCESS read-only
    STATUS     current
    DESCRIPTION
    "Shows the error count for this VBI line."
::= { enc1P656field1Line23ErrorEntry 1 }

enc1P657field1Line23ServiceTable OBJECT-TYPE
    SYNTAX SEQUENCE OF Enc1P657field1Line23ServiceEntry
    MAX-ACCESS not-accessible
    STATUS     current
    DESCRIPTION
    "
    Name      : Field 1 Line 23 Service
    Menu Path : /Data/VBI Status
    Details   : Shows whether or not this line's service is present.
    "
::= { enc1Params 657 }

enc1P657field1Line23ServiceEntry OBJECT-TYPE
    SYNTAX Enc1P657field1Line23ServiceEntry
    MAX-ACCESS not-accessible
    STATUS     current
    DESCRIPTION
    "Table Entry for Field 1 Line 23 Service"
    INDEX { slotId }
::= { enc1P657field1Line23ServiceTable 1 }

Enc1P657field1Line23ServiceEntry ::= SEQUENCE {
    enc1P657field1Line23ServiceValue    Enc1E9enumObj
}

enc1P657field1Line23ServiceValue OBJECT-TYPE
    SYNTAX     Enc1E9enumObj
    MAX-ACCESS read-only
    STATUS     current
    DESCRIPTION
    "Shows whether or not this line's service is present."
::= { enc1P657field1Line23ServiceEntry 1 }

enc1P658field2Line5ErrorTable OBJECT-TYPE
    SYNTAX SEQUENCE OF Enc1P658field2Line5ErrorEntry
    MAX-ACCESS not-accessible
    STATUS     current
    DESCRIPTION
    "
    Name      : Field 2 Line 5 Error
    Menu Path : /Data/VBI Status
    Units     : 
    Precision : 0
    Low Range : 0
    High Range: -1
    Details   : Shows the error count for this VBI line.

     NOTE: Precision/Units/Ranges represent the state of the
           parameter during the MIB generation, and does not
           neccessary reflect the current state of the parameter
    "
::= { enc1Params 658 }

enc1P658field2Line5ErrorEntry OBJECT-TYPE
    SYNTAX Enc1P658field2Line5ErrorEntry
    MAX-ACCESS not-accessible
    STATUS     current
    DESCRIPTION
    "Table Entry for Field 2 Line 5 Error"
    INDEX { slotId }
::= { enc1P658field2Line5ErrorTable 1 }

Enc1P658field2Line5ErrorEntry ::= SEQUENCE {
    enc1P658field2Line5ErrorValue    INTEGER
}

enc1P658field2Line5ErrorValue OBJECT-TYPE
    SYNTAX     INTEGER
    MAX-ACCESS read-only
    STATUS     current
    DESCRIPTION
    "Shows the error count for this VBI line."
::= { enc1P658field2Line5ErrorEntry 1 }

enc1P659field2Line5ServiceTable OBJECT-TYPE
    SYNTAX SEQUENCE OF Enc1P659field2Line5ServiceEntry
    MAX-ACCESS not-accessible
    STATUS     current
    DESCRIPTION
    "
    Name      : Field 2 Line 5 Service
    Menu Path : /Data/VBI Status
    Details   : Shows whether or not this line's service is present.
    "
::= { enc1Params 659 }

enc1P659field2Line5ServiceEntry OBJECT-TYPE
    SYNTAX Enc1P659field2Line5ServiceEntry
    MAX-ACCESS not-accessible
    STATUS     current
    DESCRIPTION
    "Table Entry for Field 2 Line 5 Service"
    INDEX { slotId }
::= { enc1P659field2Line5ServiceTable 1 }

Enc1P659field2Line5ServiceEntry ::= SEQUENCE {
    enc1P659field2Line5ServiceValue    Enc1E9enumObj
}

enc1P659field2Line5ServiceValue OBJECT-TYPE
    SYNTAX     Enc1E9enumObj
    MAX-ACCESS read-only
    STATUS     current
    DESCRIPTION
    "Shows whether or not this line's service is present."
::= { enc1P659field2Line5ServiceEntry 1 }

enc1P660field2Line6ErrorTable OBJECT-TYPE
    SYNTAX SEQUENCE OF Enc1P660field2Line6ErrorEntry
    MAX-ACCESS not-accessible
    STATUS     current
    DESCRIPTION
    "
    Name      : Field 2 Line 6 Error
    Menu Path : /Data/VBI Status
    Units     : 
    Precision : 0
    Low Range : 0
    High Range: -1
    Details   : Shows the error count for this VBI line.

     NOTE: Precision/Units/Ranges represent the state of the
           parameter during the MIB generation, and does not
           neccessary reflect the current state of the parameter
    "
::= { enc1Params 660 }

enc1P660field2Line6ErrorEntry OBJECT-TYPE
    SYNTAX Enc1P660field2Line6ErrorEntry
    MAX-ACCESS not-accessible
    STATUS     current
    DESCRIPTION
    "Table Entry for Field 2 Line 6 Error"
    INDEX { slotId }
::= { enc1P660field2Line6ErrorTable 1 }

Enc1P660field2Line6ErrorEntry ::= SEQUENCE {
    enc1P660field2Line6ErrorValue    INTEGER
}

enc1P660field2Line6ErrorValue OBJECT-TYPE
    SYNTAX     INTEGER
    MAX-ACCESS read-only
    STATUS     current
    DESCRIPTION
    "Shows the error count for this VBI line."
::= { enc1P660field2Line6ErrorEntry 1 }

enc1P661field2Line6ServiceTable OBJECT-TYPE
    SYNTAX SEQUENCE OF Enc1P661field2Line6ServiceEntry
    MAX-ACCESS not-accessible
    STATUS     current
    DESCRIPTION
    "
    Name      : Field 2 Line 6 Service
    Menu Path : /Data/VBI Status
    Details   : Shows whether or not this line's service is present.
    "
::= { enc1Params 661 }

enc1P661field2Line6ServiceEntry OBJECT-TYPE
    SYNTAX Enc1P661field2Line6ServiceEntry
    MAX-ACCESS not-accessible
    STATUS     current
    DESCRIPTION
    "Table Entry for Field 2 Line 6 Service"
    INDEX { slotId }
::= { enc1P661field2Line6ServiceTable 1 }

Enc1P661field2Line6ServiceEntry ::= SEQUENCE {
    enc1P661field2Line6ServiceValue    Enc1E9enumObj
}

enc1P661field2Line6ServiceValue OBJECT-TYPE
    SYNTAX     Enc1E9enumObj
    MAX-ACCESS read-only
    STATUS     current
    DESCRIPTION
    "Shows whether or not this line's service is present."
::= { enc1P661field2Line6ServiceEntry 1 }

enc1P662field2Line7ErrorTable OBJECT-TYPE
    SYNTAX SEQUENCE OF Enc1P662field2Line7ErrorEntry
    MAX-ACCESS not-accessible
    STATUS     current
    DESCRIPTION
    "
    Name      : Field 2 Line 7 Error
    Menu Path : /Data/VBI Status
    Units     : 
    Precision : 0
    Low Range : 0
    High Range: -1
    Details   : Shows the error count for this VBI line.

     NOTE: Precision/Units/Ranges represent the state of the
           parameter during the MIB generation, and does not
           neccessary reflect the current state of the parameter
    "
::= { enc1Params 662 }

enc1P662field2Line7ErrorEntry OBJECT-TYPE
    SYNTAX Enc1P662field2Line7ErrorEntry
    MAX-ACCESS not-accessible
    STATUS     current
    DESCRIPTION
    "Table Entry for Field 2 Line 7 Error"
    INDEX { slotId }
::= { enc1P662field2Line7ErrorTable 1 }

Enc1P662field2Line7ErrorEntry ::= SEQUENCE {
    enc1P662field2Line7ErrorValue    INTEGER
}

enc1P662field2Line7ErrorValue OBJECT-TYPE
    SYNTAX     INTEGER
    MAX-ACCESS read-only
    STATUS     current
    DESCRIPTION
    "Shows the error count for this VBI line."
::= { enc1P662field2Line7ErrorEntry 1 }

enc1P663field2Line7ServiceTable OBJECT-TYPE
    SYNTAX SEQUENCE OF Enc1P663field2Line7ServiceEntry
    MAX-ACCESS not-accessible
    STATUS     current
    DESCRIPTION
    "
    Name      : Field 2 Line 7 Service
    Menu Path : /Data/VBI Status
    Details   : Shows whether or not this line's service is present.
    "
::= { enc1Params 663 }

enc1P663field2Line7ServiceEntry OBJECT-TYPE
    SYNTAX Enc1P663field2Line7ServiceEntry
    MAX-ACCESS not-accessible
    STATUS     current
    DESCRIPTION
    "Table Entry for Field 2 Line 7 Service"
    INDEX { slotId }
::= { enc1P663field2Line7ServiceTable 1 }

Enc1P663field2Line7ServiceEntry ::= SEQUENCE {
    enc1P663field2Line7ServiceValue    Enc1E9enumObj
}

enc1P663field2Line7ServiceValue OBJECT-TYPE
    SYNTAX     Enc1E9enumObj
    MAX-ACCESS read-only
    STATUS     current
    DESCRIPTION
    "Shows whether or not this line's service is present."
::= { enc1P663field2Line7ServiceEntry 1 }

enc1P664field2Line8ErrorTable OBJECT-TYPE
    SYNTAX SEQUENCE OF Enc1P664field2Line8ErrorEntry
    MAX-ACCESS not-accessible
    STATUS     current
    DESCRIPTION
    "
    Name      : Field 2 Line 8 Error
    Menu Path : /Data/VBI Status
    Units     : 
    Precision : 0
    Low Range : 0
    High Range: -1
    Details   : Shows the error count for this VBI line.

     NOTE: Precision/Units/Ranges represent the state of the
           parameter during the MIB generation, and does not
           neccessary reflect the current state of the parameter
    "
::= { enc1Params 664 }

enc1P664field2Line8ErrorEntry OBJECT-TYPE
    SYNTAX Enc1P664field2Line8ErrorEntry
    MAX-ACCESS not-accessible
    STATUS     current
    DESCRIPTION
    "Table Entry for Field 2 Line 8 Error"
    INDEX { slotId }
::= { enc1P664field2Line8ErrorTable 1 }

Enc1P664field2Line8ErrorEntry ::= SEQUENCE {
    enc1P664field2Line8ErrorValue    INTEGER
}

enc1P664field2Line8ErrorValue OBJECT-TYPE
    SYNTAX     INTEGER
    MAX-ACCESS read-only
    STATUS     current
    DESCRIPTION
    "Shows the error count for this VBI line."
::= { enc1P664field2Line8ErrorEntry 1 }

enc1P665field2Line8ServiceTable OBJECT-TYPE
    SYNTAX SEQUENCE OF Enc1P665field2Line8ServiceEntry
    MAX-ACCESS not-accessible
    STATUS     current
    DESCRIPTION
    "
    Name      : Field 2 Line 8 Service
    Menu Path : /Data/VBI Status
    Details   : Shows whether or not this line's service is present.
    "
::= { enc1Params 665 }

enc1P665field2Line8ServiceEntry OBJECT-TYPE
    SYNTAX Enc1P665field2Line8ServiceEntry
    MAX-ACCESS not-accessible
    STATUS     current
    DESCRIPTION
    "Table Entry for Field 2 Line 8 Service"
    INDEX { slotId }
::= { enc1P665field2Line8ServiceTable 1 }

Enc1P665field2Line8ServiceEntry ::= SEQUENCE {
    enc1P665field2Line8ServiceValue    Enc1E9enumObj
}

enc1P665field2Line8ServiceValue OBJECT-TYPE
    SYNTAX     Enc1E9enumObj
    MAX-ACCESS read-only
    STATUS     current
    DESCRIPTION
    "Shows whether or not this line's service is present."
::= { enc1P665field2Line8ServiceEntry 1 }

enc1P666field2Line9ErrorTable OBJECT-TYPE
    SYNTAX SEQUENCE OF Enc1P666field2Line9ErrorEntry
    MAX-ACCESS not-accessible
    STATUS     current
    DESCRIPTION
    "
    Name      : Field 2 Line 9 Error
    Menu Path : /Data/VBI Status
    Units     : 
    Precision : 0
    Low Range : 0
    High Range: -1
    Details   : Shows the error count for this VBI line.

     NOTE: Precision/Units/Ranges represent the state of the
           parameter during the MIB generation, and does not
           neccessary reflect the current state of the parameter
    "
::= { enc1Params 666 }

enc1P666field2Line9ErrorEntry OBJECT-TYPE
    SYNTAX Enc1P666field2Line9ErrorEntry
    MAX-ACCESS not-accessible
    STATUS     current
    DESCRIPTION
    "Table Entry for Field 2 Line 9 Error"
    INDEX { slotId }
::= { enc1P666field2Line9ErrorTable 1 }

Enc1P666field2Line9ErrorEntry ::= SEQUENCE {
    enc1P666field2Line9ErrorValue    INTEGER
}

enc1P666field2Line9ErrorValue OBJECT-TYPE
    SYNTAX     INTEGER
    MAX-ACCESS read-only
    STATUS     current
    DESCRIPTION
    "Shows the error count for this VBI line."
::= { enc1P666field2Line9ErrorEntry 1 }

enc1P667field2Line9ServiceTable OBJECT-TYPE
    SYNTAX SEQUENCE OF Enc1P667field2Line9ServiceEntry
    MAX-ACCESS not-accessible
    STATUS     current
    DESCRIPTION
    "
    Name      : Field 2 Line 9 Service
    Menu Path : /Data/VBI Status
    Details   : Shows whether or not this line's service is present.
    "
::= { enc1Params 667 }

enc1P667field2Line9ServiceEntry OBJECT-TYPE
    SYNTAX Enc1P667field2Line9ServiceEntry
    MAX-ACCESS not-accessible
    STATUS     current
    DESCRIPTION
    "Table Entry for Field 2 Line 9 Service"
    INDEX { slotId }
::= { enc1P667field2Line9ServiceTable 1 }

Enc1P667field2Line9ServiceEntry ::= SEQUENCE {
    enc1P667field2Line9ServiceValue    Enc1E9enumObj
}

enc1P667field2Line9ServiceValue OBJECT-TYPE
    SYNTAX     Enc1E9enumObj
    MAX-ACCESS read-only
    STATUS     current
    DESCRIPTION
    "Shows whether or not this line's service is present."
::= { enc1P667field2Line9ServiceEntry 1 }

enc1P668field2Line10ErrorTable OBJECT-TYPE
    SYNTAX SEQUENCE OF Enc1P668field2Line10ErrorEntry
    MAX-ACCESS not-accessible
    STATUS     current
    DESCRIPTION
    "
    Name      : Field 2 Line 10 Error
    Menu Path : /Data/VBI Status
    Units     : 
    Precision : 0
    Low Range : 0
    High Range: -1
    Details   : Shows the error count for this VBI line.

     NOTE: Precision/Units/Ranges represent the state of the
           parameter during the MIB generation, and does not
           neccessary reflect the current state of the parameter
    "
::= { enc1Params 668 }

enc1P668field2Line10ErrorEntry OBJECT-TYPE
    SYNTAX Enc1P668field2Line10ErrorEntry
    MAX-ACCESS not-accessible
    STATUS     current
    DESCRIPTION
    "Table Entry for Field 2 Line 10 Error"
    INDEX { slotId }
::= { enc1P668field2Line10ErrorTable 1 }

Enc1P668field2Line10ErrorEntry ::= SEQUENCE {
    enc1P668field2Line10ErrorValue    INTEGER
}

enc1P668field2Line10ErrorValue OBJECT-TYPE
    SYNTAX     INTEGER
    MAX-ACCESS read-only
    STATUS     current
    DESCRIPTION
    "Shows the error count for this VBI line."
::= { enc1P668field2Line10ErrorEntry 1 }

enc1P669field2Line10ServiceTable OBJECT-TYPE
    SYNTAX SEQUENCE OF Enc1P669field2Line10ServiceEntry
    MAX-ACCESS not-accessible
    STATUS     current
    DESCRIPTION
    "
    Name      : Field 2 Line 10 Service
    Menu Path : /Data/VBI Status
    Details   : Shows whether or not this line's service is present.
    "
::= { enc1Params 669 }

enc1P669field2Line10ServiceEntry OBJECT-TYPE
    SYNTAX Enc1P669field2Line10ServiceEntry
    MAX-ACCESS not-accessible
    STATUS     current
    DESCRIPTION
    "Table Entry for Field 2 Line 10 Service"
    INDEX { slotId }
::= { enc1P669field2Line10ServiceTable 1 }

Enc1P669field2Line10ServiceEntry ::= SEQUENCE {
    enc1P669field2Line10ServiceValue    Enc1E9enumObj
}

enc1P669field2Line10ServiceValue OBJECT-TYPE
    SYNTAX     Enc1E9enumObj
    MAX-ACCESS read-only
    STATUS     current
    DESCRIPTION
    "Shows whether or not this line's service is present."
::= { enc1P669field2Line10ServiceEntry 1 }

enc1P670field2Line11ErrorTable OBJECT-TYPE
    SYNTAX SEQUENCE OF Enc1P670field2Line11ErrorEntry
    MAX-ACCESS not-accessible
    STATUS     current
    DESCRIPTION
    "
    Name      : Field 2 Line 11 Error
    Menu Path : /Data/VBI Status
    Units     : 
    Precision : 0
    Low Range : 0
    High Range: -1
    Details   : Shows the error count for this VBI line.

     NOTE: Precision/Units/Ranges represent the state of the
           parameter during the MIB generation, and does not
           neccessary reflect the current state of the parameter
    "
::= { enc1Params 670 }

enc1P670field2Line11ErrorEntry OBJECT-TYPE
    SYNTAX Enc1P670field2Line11ErrorEntry
    MAX-ACCESS not-accessible
    STATUS     current
    DESCRIPTION
    "Table Entry for Field 2 Line 11 Error"
    INDEX { slotId }
::= { enc1P670field2Line11ErrorTable 1 }

Enc1P670field2Line11ErrorEntry ::= SEQUENCE {
    enc1P670field2Line11ErrorValue    INTEGER
}

enc1P670field2Line11ErrorValue OBJECT-TYPE
    SYNTAX     INTEGER
    MAX-ACCESS read-only
    STATUS     current
    DESCRIPTION
    "Shows the error count for this VBI line."
::= { enc1P670field2Line11ErrorEntry 1 }

enc1P671field2Line11ServiceTable OBJECT-TYPE
    SYNTAX SEQUENCE OF Enc1P671field2Line11ServiceEntry
    MAX-ACCESS not-accessible
    STATUS     current
    DESCRIPTION
    "
    Name      : Field 2 Line 11 Service
    Menu Path : /Data/VBI Status
    Details   : Shows whether or not this line's service is present.
    "
::= { enc1Params 671 }

enc1P671field2Line11ServiceEntry OBJECT-TYPE
    SYNTAX Enc1P671field2Line11ServiceEntry
    MAX-ACCESS not-accessible
    STATUS     current
    DESCRIPTION
    "Table Entry for Field 2 Line 11 Service"
    INDEX { slotId }
::= { enc1P671field2Line11ServiceTable 1 }

Enc1P671field2Line11ServiceEntry ::= SEQUENCE {
    enc1P671field2Line11ServiceValue    Enc1E9enumObj
}

enc1P671field2Line11ServiceValue OBJECT-TYPE
    SYNTAX     Enc1E9enumObj
    MAX-ACCESS read-only
    STATUS     current
    DESCRIPTION
    "Shows whether or not this line's service is present."
::= { enc1P671field2Line11ServiceEntry 1 }

enc1P672field2Line12ErrorTable OBJECT-TYPE
    SYNTAX SEQUENCE OF Enc1P672field2Line12ErrorEntry
    MAX-ACCESS not-accessible
    STATUS     current
    DESCRIPTION
    "
    Name      : Field 2 Line 12 Error
    Menu Path : /Data/VBI Status
    Units     : 
    Precision : 0
    Low Range : 0
    High Range: -1
    Details   : Shows the error count for this VBI line.

     NOTE: Precision/Units/Ranges represent the state of the
           parameter during the MIB generation, and does not
           neccessary reflect the current state of the parameter
    "
::= { enc1Params 672 }

enc1P672field2Line12ErrorEntry OBJECT-TYPE
    SYNTAX Enc1P672field2Line12ErrorEntry
    MAX-ACCESS not-accessible
    STATUS     current
    DESCRIPTION
    "Table Entry for Field 2 Line 12 Error"
    INDEX { slotId }
::= { enc1P672field2Line12ErrorTable 1 }

Enc1P672field2Line12ErrorEntry ::= SEQUENCE {
    enc1P672field2Line12ErrorValue    INTEGER
}

enc1P672field2Line12ErrorValue OBJECT-TYPE
    SYNTAX     INTEGER
    MAX-ACCESS read-only
    STATUS     current
    DESCRIPTION
    "Shows the error count for this VBI line."
::= { enc1P672field2Line12ErrorEntry 1 }

enc1P673field2Line12ServiceTable OBJECT-TYPE
    SYNTAX SEQUENCE OF Enc1P673field2Line12ServiceEntry
    MAX-ACCESS not-accessible
    STATUS     current
    DESCRIPTION
    "
    Name      : Field 2 Line 12 Service
    Menu Path : /Data/VBI Status
    Details   : Shows whether or not this line's service is present.
    "
::= { enc1Params 673 }

enc1P673field2Line12ServiceEntry OBJECT-TYPE
    SYNTAX Enc1P673field2Line12ServiceEntry
    MAX-ACCESS not-accessible
    STATUS     current
    DESCRIPTION
    "Table Entry for Field 2 Line 12 Service"
    INDEX { slotId }
::= { enc1P673field2Line12ServiceTable 1 }

Enc1P673field2Line12ServiceEntry ::= SEQUENCE {
    enc1P673field2Line12ServiceValue    Enc1E9enumObj
}

enc1P673field2Line12ServiceValue OBJECT-TYPE
    SYNTAX     Enc1E9enumObj
    MAX-ACCESS read-only
    STATUS     current
    DESCRIPTION
    "Shows whether or not this line's service is present."
::= { enc1P673field2Line12ServiceEntry 1 }

enc1P674field2Line13ErrorTable OBJECT-TYPE
    SYNTAX SEQUENCE OF Enc1P674field2Line13ErrorEntry
    MAX-ACCESS not-accessible
    STATUS     current
    DESCRIPTION
    "
    Name      : Field 2 Line 13 Error
    Menu Path : /Data/VBI Status
    Units     : 
    Precision : 0
    Low Range : 0
    High Range: -1
    Details   : Shows the error count for this VBI line.

     NOTE: Precision/Units/Ranges represent the state of the
           parameter during the MIB generation, and does not
           neccessary reflect the current state of the parameter
    "
::= { enc1Params 674 }

enc1P674field2Line13ErrorEntry OBJECT-TYPE
    SYNTAX Enc1P674field2Line13ErrorEntry
    MAX-ACCESS not-accessible
    STATUS     current
    DESCRIPTION
    "Table Entry for Field 2 Line 13 Error"
    INDEX { slotId }
::= { enc1P674field2Line13ErrorTable 1 }

Enc1P674field2Line13ErrorEntry ::= SEQUENCE {
    enc1P674field2Line13ErrorValue    INTEGER
}

enc1P674field2Line13ErrorValue OBJECT-TYPE
    SYNTAX     INTEGER
    MAX-ACCESS read-only
    STATUS     current
    DESCRIPTION
    "Shows the error count for this VBI line."
::= { enc1P674field2Line13ErrorEntry 1 }

enc1P675field2Line13ServiceTable OBJECT-TYPE
    SYNTAX SEQUENCE OF Enc1P675field2Line13ServiceEntry
    MAX-ACCESS not-accessible
    STATUS     current
    DESCRIPTION
    "
    Name      : Field 2 Line 13 Service
    Menu Path : /Data/VBI Status
    Details   : Shows whether or not this line's service is present.
    "
::= { enc1Params 675 }

enc1P675field2Line13ServiceEntry OBJECT-TYPE
    SYNTAX Enc1P675field2Line13ServiceEntry
    MAX-ACCESS not-accessible
    STATUS     current
    DESCRIPTION
    "Table Entry for Field 2 Line 13 Service"
    INDEX { slotId }
::= { enc1P675field2Line13ServiceTable 1 }

Enc1P675field2Line13ServiceEntry ::= SEQUENCE {
    enc1P675field2Line13ServiceValue    Enc1E9enumObj
}

enc1P675field2Line13ServiceValue OBJECT-TYPE
    SYNTAX     Enc1E9enumObj
    MAX-ACCESS read-only
    STATUS     current
    DESCRIPTION
    "Shows whether or not this line's service is present."
::= { enc1P675field2Line13ServiceEntry 1 }

enc1P676field2Line14ErrorTable OBJECT-TYPE
    SYNTAX SEQUENCE OF Enc1P676field2Line14ErrorEntry
    MAX-ACCESS not-accessible
    STATUS     current
    DESCRIPTION
    "
    Name      : Field 2 Line 14 Error
    Menu Path : /Data/VBI Status
    Units     : 
    Precision : 0
    Low Range : 0
    High Range: -1
    Details   : Shows the error count for this VBI line.

     NOTE: Precision/Units/Ranges represent the state of the
           parameter during the MIB generation, and does not
           neccessary reflect the current state of the parameter
    "
::= { enc1Params 676 }

enc1P676field2Line14ErrorEntry OBJECT-TYPE
    SYNTAX Enc1P676field2Line14ErrorEntry
    MAX-ACCESS not-accessible
    STATUS     current
    DESCRIPTION
    "Table Entry for Field 2 Line 14 Error"
    INDEX { slotId }
::= { enc1P676field2Line14ErrorTable 1 }

Enc1P676field2Line14ErrorEntry ::= SEQUENCE {
    enc1P676field2Line14ErrorValue    INTEGER
}

enc1P676field2Line14ErrorValue OBJECT-TYPE
    SYNTAX     INTEGER
    MAX-ACCESS read-only
    STATUS     current
    DESCRIPTION
    "Shows the error count for this VBI line."
::= { enc1P676field2Line14ErrorEntry 1 }

enc1P677field2Line14ServiceTable OBJECT-TYPE
    SYNTAX SEQUENCE OF Enc1P677field2Line14ServiceEntry
    MAX-ACCESS not-accessible
    STATUS     current
    DESCRIPTION
    "
    Name      : Field 2 Line 14 Service
    Menu Path : /Data/VBI Status
    Details   : Shows whether or not this line's service is present.
    "
::= { enc1Params 677 }

enc1P677field2Line14ServiceEntry OBJECT-TYPE
    SYNTAX Enc1P677field2Line14ServiceEntry
    MAX-ACCESS not-accessible
    STATUS     current
    DESCRIPTION
    "Table Entry for Field 2 Line 14 Service"
    INDEX { slotId }
::= { enc1P677field2Line14ServiceTable 1 }

Enc1P677field2Line14ServiceEntry ::= SEQUENCE {
    enc1P677field2Line14ServiceValue    Enc1E9enumObj
}

enc1P677field2Line14ServiceValue OBJECT-TYPE
    SYNTAX     Enc1E9enumObj
    MAX-ACCESS read-only
    STATUS     current
    DESCRIPTION
    "Shows whether or not this line's service is present."
::= { enc1P677field2Line14ServiceEntry 1 }

enc1P678field2Line15ErrorTable OBJECT-TYPE
    SYNTAX SEQUENCE OF Enc1P678field2Line15ErrorEntry
    MAX-ACCESS not-accessible
    STATUS     current
    DESCRIPTION
    "
    Name      : Field 2 Line 15 Error
    Menu Path : /Data/VBI Status
    Units     : 
    Precision : 0
    Low Range : 0
    High Range: -1
    Details   : Shows the error count for this VBI line.

     NOTE: Precision/Units/Ranges represent the state of the
           parameter during the MIB generation, and does not
           neccessary reflect the current state of the parameter
    "
::= { enc1Params 678 }

enc1P678field2Line15ErrorEntry OBJECT-TYPE
    SYNTAX Enc1P678field2Line15ErrorEntry
    MAX-ACCESS not-accessible
    STATUS     current
    DESCRIPTION
    "Table Entry for Field 2 Line 15 Error"
    INDEX { slotId }
::= { enc1P678field2Line15ErrorTable 1 }

Enc1P678field2Line15ErrorEntry ::= SEQUENCE {
    enc1P678field2Line15ErrorValue    INTEGER
}

enc1P678field2Line15ErrorValue OBJECT-TYPE
    SYNTAX     INTEGER
    MAX-ACCESS read-only
    STATUS     current
    DESCRIPTION
    "Shows the error count for this VBI line."
::= { enc1P678field2Line15ErrorEntry 1 }

enc1P679field2Line15ServiceTable OBJECT-TYPE
    SYNTAX SEQUENCE OF Enc1P679field2Line15ServiceEntry
    MAX-ACCESS not-accessible
    STATUS     current
    DESCRIPTION
    "
    Name      : Field 2 Line 15 Service
    Menu Path : /Data/VBI Status
    Details   : Shows whether or not this line's service is present.
    "
::= { enc1Params 679 }

enc1P679field2Line15ServiceEntry OBJECT-TYPE
    SYNTAX Enc1P679field2Line15ServiceEntry
    MAX-ACCESS not-accessible
    STATUS     current
    DESCRIPTION
    "Table Entry for Field 2 Line 15 Service"
    INDEX { slotId }
::= { enc1P679field2Line15ServiceTable 1 }

Enc1P679field2Line15ServiceEntry ::= SEQUENCE {
    enc1P679field2Line15ServiceValue    Enc1E9enumObj
}

enc1P679field2Line15ServiceValue OBJECT-TYPE
    SYNTAX     Enc1E9enumObj
    MAX-ACCESS read-only
    STATUS     current
    DESCRIPTION
    "Shows whether or not this line's service is present."
::= { enc1P679field2Line15ServiceEntry 1 }

enc1P680field2Line16ErrorTable OBJECT-TYPE
    SYNTAX SEQUENCE OF Enc1P680field2Line16ErrorEntry
    MAX-ACCESS not-accessible
    STATUS     current
    DESCRIPTION
    "
    Name      : Field 2 Line 16 Error
    Menu Path : /Data/VBI Status
    Units     : 
    Precision : 0
    Low Range : 0
    High Range: -1
    Details   : Shows the error count for this VBI line.

     NOTE: Precision/Units/Ranges represent the state of the
           parameter during the MIB generation, and does not
           neccessary reflect the current state of the parameter
    "
::= { enc1Params 680 }

enc1P680field2Line16ErrorEntry OBJECT-TYPE
    SYNTAX Enc1P680field2Line16ErrorEntry
    MAX-ACCESS not-accessible
    STATUS     current
    DESCRIPTION
    "Table Entry for Field 2 Line 16 Error"
    INDEX { slotId }
::= { enc1P680field2Line16ErrorTable 1 }

Enc1P680field2Line16ErrorEntry ::= SEQUENCE {
    enc1P680field2Line16ErrorValue    INTEGER
}

enc1P680field2Line16ErrorValue OBJECT-TYPE
    SYNTAX     INTEGER
    MAX-ACCESS read-only
    STATUS     current
    DESCRIPTION
    "Shows the error count for this VBI line."
::= { enc1P680field2Line16ErrorEntry 1 }

enc1P681field2Line16ServiceTable OBJECT-TYPE
    SYNTAX SEQUENCE OF Enc1P681field2Line16ServiceEntry
    MAX-ACCESS not-accessible
    STATUS     current
    DESCRIPTION
    "
    Name      : Field 2 Line 16 Service
    Menu Path : /Data/VBI Status
    Details   : Shows whether or not this line's service is present.
    "
::= { enc1Params 681 }

enc1P681field2Line16ServiceEntry OBJECT-TYPE
    SYNTAX Enc1P681field2Line16ServiceEntry
    MAX-ACCESS not-accessible
    STATUS     current
    DESCRIPTION
    "Table Entry for Field 2 Line 16 Service"
    INDEX { slotId }
::= { enc1P681field2Line16ServiceTable 1 }

Enc1P681field2Line16ServiceEntry ::= SEQUENCE {
    enc1P681field2Line16ServiceValue    Enc1E9enumObj
}

enc1P681field2Line16ServiceValue OBJECT-TYPE
    SYNTAX     Enc1E9enumObj
    MAX-ACCESS read-only
    STATUS     current
    DESCRIPTION
    "Shows whether or not this line's service is present."
::= { enc1P681field2Line16ServiceEntry 1 }

enc1P682field2Line17ErrorTable OBJECT-TYPE
    SYNTAX SEQUENCE OF Enc1P682field2Line17ErrorEntry
    MAX-ACCESS not-accessible
    STATUS     current
    DESCRIPTION
    "
    Name      : Field 2 Line 17 Error
    Menu Path : /Data/VBI Status
    Units     : 
    Precision : 0
    Low Range : 0
    High Range: -1
    Details   : Shows the error count for this VBI line.

     NOTE: Precision/Units/Ranges represent the state of the
           parameter during the MIB generation, and does not
           neccessary reflect the current state of the parameter
    "
::= { enc1Params 682 }

enc1P682field2Line17ErrorEntry OBJECT-TYPE
    SYNTAX Enc1P682field2Line17ErrorEntry
    MAX-ACCESS not-accessible
    STATUS     current
    DESCRIPTION
    "Table Entry for Field 2 Line 17 Error"
    INDEX { slotId }
::= { enc1P682field2Line17ErrorTable 1 }

Enc1P682field2Line17ErrorEntry ::= SEQUENCE {
    enc1P682field2Line17ErrorValue    INTEGER
}

enc1P682field2Line17ErrorValue OBJECT-TYPE
    SYNTAX     INTEGER
    MAX-ACCESS read-only
    STATUS     current
    DESCRIPTION
    "Shows the error count for this VBI line."
::= { enc1P682field2Line17ErrorEntry 1 }

enc1P683field2Line17ServiceTable OBJECT-TYPE
    SYNTAX SEQUENCE OF Enc1P683field2Line17ServiceEntry
    MAX-ACCESS not-accessible
    STATUS     current
    DESCRIPTION
    "
    Name      : Field 2 Line 17 Service
    Menu Path : /Data/VBI Status
    Details   : Shows whether or not this line's service is present.
    "
::= { enc1Params 683 }

enc1P683field2Line17ServiceEntry OBJECT-TYPE
    SYNTAX Enc1P683field2Line17ServiceEntry
    MAX-ACCESS not-accessible
    STATUS     current
    DESCRIPTION
    "Table Entry for Field 2 Line 17 Service"
    INDEX { slotId }
::= { enc1P683field2Line17ServiceTable 1 }

Enc1P683field2Line17ServiceEntry ::= SEQUENCE {
    enc1P683field2Line17ServiceValue    Enc1E9enumObj
}

enc1P683field2Line17ServiceValue OBJECT-TYPE
    SYNTAX     Enc1E9enumObj
    MAX-ACCESS read-only
    STATUS     current
    DESCRIPTION
    "Shows whether or not this line's service is present."
::= { enc1P683field2Line17ServiceEntry 1 }

enc1P684field2Line18ErrorTable OBJECT-TYPE
    SYNTAX SEQUENCE OF Enc1P684field2Line18ErrorEntry
    MAX-ACCESS not-accessible
    STATUS     current
    DESCRIPTION
    "
    Name      : Field 2 Line 18 Error
    Menu Path : /Data/VBI Status
    Units     : 
    Precision : 0
    Low Range : 0
    High Range: -1
    Details   : Shows the error count for this VBI line.

     NOTE: Precision/Units/Ranges represent the state of the
           parameter during the MIB generation, and does not
           neccessary reflect the current state of the parameter
    "
::= { enc1Params 684 }

enc1P684field2Line18ErrorEntry OBJECT-TYPE
    SYNTAX Enc1P684field2Line18ErrorEntry
    MAX-ACCESS not-accessible
    STATUS     current
    DESCRIPTION
    "Table Entry for Field 2 Line 18 Error"
    INDEX { slotId }
::= { enc1P684field2Line18ErrorTable 1 }

Enc1P684field2Line18ErrorEntry ::= SEQUENCE {
    enc1P684field2Line18ErrorValue    INTEGER
}

enc1P684field2Line18ErrorValue OBJECT-TYPE
    SYNTAX     INTEGER
    MAX-ACCESS read-only
    STATUS     current
    DESCRIPTION
    "Shows the error count for this VBI line."
::= { enc1P684field2Line18ErrorEntry 1 }

enc1P685field2Line18ServiceTable OBJECT-TYPE
    SYNTAX SEQUENCE OF Enc1P685field2Line18ServiceEntry
    MAX-ACCESS not-accessible
    STATUS     current
    DESCRIPTION
    "
    Name      : Field 2 Line 18 Service
    Menu Path : /Data/VBI Status
    Details   : Shows whether or not this line's service is present.
    "
::= { enc1Params 685 }

enc1P685field2Line18ServiceEntry OBJECT-TYPE
    SYNTAX Enc1P685field2Line18ServiceEntry
    MAX-ACCESS not-accessible
    STATUS     current
    DESCRIPTION
    "Table Entry for Field 2 Line 18 Service"
    INDEX { slotId }
::= { enc1P685field2Line18ServiceTable 1 }

Enc1P685field2Line18ServiceEntry ::= SEQUENCE {
    enc1P685field2Line18ServiceValue    Enc1E9enumObj
}

enc1P685field2Line18ServiceValue OBJECT-TYPE
    SYNTAX     Enc1E9enumObj
    MAX-ACCESS read-only
    STATUS     current
    DESCRIPTION
    "Shows whether or not this line's service is present."
::= { enc1P685field2Line18ServiceEntry 1 }

enc1P686field2Line19ErrorTable OBJECT-TYPE
    SYNTAX SEQUENCE OF Enc1P686field2Line19ErrorEntry
    MAX-ACCESS not-accessible
    STATUS     current
    DESCRIPTION
    "
    Name      : Field 2 Line 19 Error
    Menu Path : /Data/VBI Status
    Units     : 
    Precision : 0
    Low Range : 0
    High Range: -1
    Details   : Shows the error count for this VBI line.

     NOTE: Precision/Units/Ranges represent the state of the
           parameter during the MIB generation, and does not
           neccessary reflect the current state of the parameter
    "
::= { enc1Params 686 }

enc1P686field2Line19ErrorEntry OBJECT-TYPE
    SYNTAX Enc1P686field2Line19ErrorEntry
    MAX-ACCESS not-accessible
    STATUS     current
    DESCRIPTION
    "Table Entry for Field 2 Line 19 Error"
    INDEX { slotId }
::= { enc1P686field2Line19ErrorTable 1 }

Enc1P686field2Line19ErrorEntry ::= SEQUENCE {
    enc1P686field2Line19ErrorValue    INTEGER
}

enc1P686field2Line19ErrorValue OBJECT-TYPE
    SYNTAX     INTEGER
    MAX-ACCESS read-only
    STATUS     current
    DESCRIPTION
    "Shows the error count for this VBI line."
::= { enc1P686field2Line19ErrorEntry 1 }

enc1P687field2Line19ServiceTable OBJECT-TYPE
    SYNTAX SEQUENCE OF Enc1P687field2Line19ServiceEntry
    MAX-ACCESS not-accessible
    STATUS     current
    DESCRIPTION
    "
    Name      : Field 2 Line 19 Service
    Menu Path : /Data/VBI Status
    Details   : Shows whether or not this line's service is present.
    "
::= { enc1Params 687 }

enc1P687field2Line19ServiceEntry OBJECT-TYPE
    SYNTAX Enc1P687field2Line19ServiceEntry
    MAX-ACCESS not-accessible
    STATUS     current
    DESCRIPTION
    "Table Entry for Field 2 Line 19 Service"
    INDEX { slotId }
::= { enc1P687field2Line19ServiceTable 1 }

Enc1P687field2Line19ServiceEntry ::= SEQUENCE {
    enc1P687field2Line19ServiceValue    Enc1E9enumObj
}

enc1P687field2Line19ServiceValue OBJECT-TYPE
    SYNTAX     Enc1E9enumObj
    MAX-ACCESS read-only
    STATUS     current
    DESCRIPTION
    "Shows whether or not this line's service is present."
::= { enc1P687field2Line19ServiceEntry 1 }

enc1P688field2Line20ErrorTable OBJECT-TYPE
    SYNTAX SEQUENCE OF Enc1P688field2Line20ErrorEntry
    MAX-ACCESS not-accessible
    STATUS     current
    DESCRIPTION
    "
    Name      : Field 2 Line 20 Error
    Menu Path : /Data/VBI Status
    Units     : 
    Precision : 0
    Low Range : 0
    High Range: -1
    Details   : Shows the error count for this VBI line.

     NOTE: Precision/Units/Ranges represent the state of the
           parameter during the MIB generation, and does not
           neccessary reflect the current state of the parameter
    "
::= { enc1Params 688 }

enc1P688field2Line20ErrorEntry OBJECT-TYPE
    SYNTAX Enc1P688field2Line20ErrorEntry
    MAX-ACCESS not-accessible
    STATUS     current
    DESCRIPTION
    "Table Entry for Field 2 Line 20 Error"
    INDEX { slotId }
::= { enc1P688field2Line20ErrorTable 1 }

Enc1P688field2Line20ErrorEntry ::= SEQUENCE {
    enc1P688field2Line20ErrorValue    INTEGER
}

enc1P688field2Line20ErrorValue OBJECT-TYPE
    SYNTAX     INTEGER
    MAX-ACCESS read-only
    STATUS     current
    DESCRIPTION
    "Shows the error count for this VBI line."
::= { enc1P688field2Line20ErrorEntry 1 }

enc1P689field2Line20ServiceTable OBJECT-TYPE
    SYNTAX SEQUENCE OF Enc1P689field2Line20ServiceEntry
    MAX-ACCESS not-accessible
    STATUS     current
    DESCRIPTION
    "
    Name      : Field 2 Line 20 Service
    Menu Path : /Data/VBI Status
    Details   : Shows whether or not this line's service is present.
    "
::= { enc1Params 689 }

enc1P689field2Line20ServiceEntry OBJECT-TYPE
    SYNTAX Enc1P689field2Line20ServiceEntry
    MAX-ACCESS not-accessible
    STATUS     current
    DESCRIPTION
    "Table Entry for Field 2 Line 20 Service"
    INDEX { slotId }
::= { enc1P689field2Line20ServiceTable 1 }

Enc1P689field2Line20ServiceEntry ::= SEQUENCE {
    enc1P689field2Line20ServiceValue    Enc1E9enumObj
}

enc1P689field2Line20ServiceValue OBJECT-TYPE
    SYNTAX     Enc1E9enumObj
    MAX-ACCESS read-only
    STATUS     current
    DESCRIPTION
    "Shows whether or not this line's service is present."
::= { enc1P689field2Line20ServiceEntry 1 }

enc1P690field2Line21ErrorTable OBJECT-TYPE
    SYNTAX SEQUENCE OF Enc1P690field2Line21ErrorEntry
    MAX-ACCESS not-accessible
    STATUS     current
    DESCRIPTION
    "
    Name      : Field 2 Line 21 Error
    Menu Path : /Data/VBI Status
    Units     : 
    Precision : 0
    Low Range : 0
    High Range: -1
    Details   : Shows the error count for this VBI line.

     NOTE: Precision/Units/Ranges represent the state of the
           parameter during the MIB generation, and does not
           neccessary reflect the current state of the parameter
    "
::= { enc1Params 690 }

enc1P690field2Line21ErrorEntry OBJECT-TYPE
    SYNTAX Enc1P690field2Line21ErrorEntry
    MAX-ACCESS not-accessible
    STATUS     current
    DESCRIPTION
    "Table Entry for Field 2 Line 21 Error"
    INDEX { slotId }
::= { enc1P690field2Line21ErrorTable 1 }

Enc1P690field2Line21ErrorEntry ::= SEQUENCE {
    enc1P690field2Line21ErrorValue    INTEGER
}

enc1P690field2Line21ErrorValue OBJECT-TYPE
    SYNTAX     INTEGER
    MAX-ACCESS read-only
    STATUS     current
    DESCRIPTION
    "Shows the error count for this VBI line."
::= { enc1P690field2Line21ErrorEntry 1 }

enc1P691field2Line21ServiceTable OBJECT-TYPE
    SYNTAX SEQUENCE OF Enc1P691field2Line21ServiceEntry
    MAX-ACCESS not-accessible
    STATUS     current
    DESCRIPTION
    "
    Name      : Field 2 Line 21 Service
    Menu Path : /Data/VBI Status
    Details   : Shows whether or not this line's service is present.
    "
::= { enc1Params 691 }

enc1P691field2Line21ServiceEntry OBJECT-TYPE
    SYNTAX Enc1P691field2Line21ServiceEntry
    MAX-ACCESS not-accessible
    STATUS     current
    DESCRIPTION
    "Table Entry for Field 2 Line 21 Service"
    INDEX { slotId }
::= { enc1P691field2Line21ServiceTable 1 }

Enc1P691field2Line21ServiceEntry ::= SEQUENCE {
    enc1P691field2Line21ServiceValue    Enc1E9enumObj
}

enc1P691field2Line21ServiceValue OBJECT-TYPE
    SYNTAX     Enc1E9enumObj
    MAX-ACCESS read-only
    STATUS     current
    DESCRIPTION
    "Shows whether or not this line's service is present."
::= { enc1P691field2Line21ServiceEntry 1 }

enc1P692field2Line22ErrorTable OBJECT-TYPE
    SYNTAX SEQUENCE OF Enc1P692field2Line22ErrorEntry
    MAX-ACCESS not-accessible
    STATUS     current
    DESCRIPTION
    "
    Name      : Field 2 Line 22 Error
    Menu Path : /Data/VBI Status
    Units     : 
    Precision : 0
    Low Range : 0
    High Range: -1
    Details   : Shows the error count for this VBI line.

     NOTE: Precision/Units/Ranges represent the state of the
           parameter during the MIB generation, and does not
           neccessary reflect the current state of the parameter
    "
::= { enc1Params 692 }

enc1P692field2Line22ErrorEntry OBJECT-TYPE
    SYNTAX Enc1P692field2Line22ErrorEntry
    MAX-ACCESS not-accessible
    STATUS     current
    DESCRIPTION
    "Table Entry for Field 2 Line 22 Error"
    INDEX { slotId }
::= { enc1P692field2Line22ErrorTable 1 }

Enc1P692field2Line22ErrorEntry ::= SEQUENCE {
    enc1P692field2Line22ErrorValue    INTEGER
}

enc1P692field2Line22ErrorValue OBJECT-TYPE
    SYNTAX     INTEGER
    MAX-ACCESS read-only
    STATUS     current
    DESCRIPTION
    "Shows the error count for this VBI line."
::= { enc1P692field2Line22ErrorEntry 1 }

enc1P693field2Line22ServiceTable OBJECT-TYPE
    SYNTAX SEQUENCE OF Enc1P693field2Line22ServiceEntry
    MAX-ACCESS not-accessible
    STATUS     current
    DESCRIPTION
    "
    Name      : Field 2 Line 22 Service
    Menu Path : /Data/VBI Status
    Details   : Shows whether or not this line's service is present.
    "
::= { enc1Params 693 }

enc1P693field2Line22ServiceEntry OBJECT-TYPE
    SYNTAX Enc1P693field2Line22ServiceEntry
    MAX-ACCESS not-accessible
    STATUS     current
    DESCRIPTION
    "Table Entry for Field 2 Line 22 Service"
    INDEX { slotId }
::= { enc1P693field2Line22ServiceTable 1 }

Enc1P693field2Line22ServiceEntry ::= SEQUENCE {
    enc1P693field2Line22ServiceValue    Enc1E9enumObj
}

enc1P693field2Line22ServiceValue OBJECT-TYPE
    SYNTAX     Enc1E9enumObj
    MAX-ACCESS read-only
    STATUS     current
    DESCRIPTION
    "Shows whether or not this line's service is present."
::= { enc1P693field2Line22ServiceEntry 1 }

enc1P694rateTable OBJECT-TYPE
    SYNTAX SEQUENCE OF Enc1P694rateEntry
    MAX-ACCESS not-accessible
    STATUS     current
    DESCRIPTION
    "
    Name      : Rate
    Menu Path : /Data/Ancillary
    Units     : Mbits/sec
    Precision : 6
    Low Range : 0
    High Range: 2000000
    Details   : Specifies maximum TS rate dedicated to VANC data. (Units: Mbits/sec)

     NOTE: Precision/Units/Ranges represent the state of the
           parameter during the MIB generation, and does not
           neccessary reflect the current state of the parameter
    "
::= { enc1Params 694 }

enc1P694rateEntry OBJECT-TYPE
    SYNTAX Enc1P694rateEntry
    MAX-ACCESS not-accessible
    STATUS     current
    DESCRIPTION
    "Table Entry for Rate"
    INDEX { slotId }
::= { enc1P694rateTable 1 }

Enc1P694rateEntry ::= SEQUENCE {
    enc1P694rateValue    INTEGER
}

enc1P694rateValue OBJECT-TYPE
    SYNTAX     INTEGER
    MAX-ACCESS read-write
    STATUS     current
    DESCRIPTION
    "Specifies maximum TS rate dedicated to VANC data. (Units: Mbits/sec)"
::= { enc1P694rateEntry 1 }

enc1P695filterTable OBJECT-TYPE
    SYNTAX SEQUENCE OF Enc1P695filterEntry
    MAX-ACCESS not-accessible
    STATUS     current
    DESCRIPTION
    "
    Name      : Filter
    Menu Path : /Data/Ancillary
    Details   : Enables/Disables DID/SDID based filtering of VANC data.
    "
::= { enc1Params 695 }

enc1P695filterEntry OBJECT-TYPE
    SYNTAX Enc1P695filterEntry
    MAX-ACCESS not-accessible
    STATUS     current
    DESCRIPTION
    "Table Entry for Filter"
    INDEX { slotId }
::= { enc1P695filterTable 1 }

Enc1P695filterEntry ::= SEQUENCE {
    enc1P695filterValue    Enc1E0enumObj
}

enc1P695filterValue OBJECT-TYPE
    SYNTAX     Enc1E0enumObj
    MAX-ACCESS read-write
    STATUS     current
    DESCRIPTION
    "Enables/Disables DID/SDID based filtering of VANC data."
::= { enc1P695filterEntry 1 }

enc1P696formatTable OBJECT-TYPE
    SYNTAX SEQUENCE OF Enc1P696formatEntry
    MAX-ACCESS not-accessible
    STATUS     current
    DESCRIPTION
    "
    Name      : Format
    Menu Path : /Data/Ancillary
    Details   : Specifies ANC data format (SMPTE2038 or RDD-11) in TS.
    "
::= { enc1Params 696 }

enc1P696formatEntry OBJECT-TYPE
    SYNTAX Enc1P696formatEntry
    MAX-ACCESS not-accessible
    STATUS     current
    DESCRIPTION
    "Table Entry for Format"
    INDEX { slotId }
::= { enc1P696formatTable 1 }

Enc1P696formatEntry ::= SEQUENCE {
    enc1P696formatValue    Enc1E124enumObj
}

enc1P696formatValue OBJECT-TYPE
    SYNTAX     Enc1E124enumObj
    MAX-ACCESS read-write
    STATUS     current
    DESCRIPTION
    "Specifies ANC data format (SMPTE2038 or RDD-11) in TS."
::= { enc1P696formatEntry 1 }

enc1P697vancservice1Table OBJECT-TYPE
    SYNTAX SEQUENCE OF Enc1P697vancservice1Entry
    MAX-ACCESS not-accessible
    STATUS     current
    DESCRIPTION
    "
    Name      : VANC Service 1
    Menu Path : /Data/Ancillary
    Details   : Specifies data type of service.
    "
::= { enc1Params 697 }

enc1P697vancservice1Entry OBJECT-TYPE
    SYNTAX Enc1P697vancservice1Entry
    MAX-ACCESS not-accessible
    STATUS     current
    DESCRIPTION
    "Table Entry for VANC Service 1"
    INDEX { slotId }
::= { enc1P697vancservice1Table 1 }

Enc1P697vancservice1Entry ::= SEQUENCE {
    enc1P697vancservice1Value    Enc1E125enumObj
}

enc1P697vancservice1Value OBJECT-TYPE
    SYNTAX     Enc1E125enumObj
    MAX-ACCESS read-write
    STATUS     current
    DESCRIPTION
    "Specifies data type of service."
::= { enc1P697vancservice1Entry 1 }

enc1P698vancservice2Table OBJECT-TYPE
    SYNTAX SEQUENCE OF Enc1P698vancservice2Entry
    MAX-ACCESS not-accessible
    STATUS     current
    DESCRIPTION
    "
    Name      : VANC Service 2
    Menu Path : /Data/Ancillary
    Details   : Specifies data type of service.
    "
::= { enc1Params 698 }

enc1P698vancservice2Entry OBJECT-TYPE
    SYNTAX Enc1P698vancservice2Entry
    MAX-ACCESS not-accessible
    STATUS     current
    DESCRIPTION
    "Table Entry for VANC Service 2"
    INDEX { slotId }
::= { enc1P698vancservice2Table 1 }

Enc1P698vancservice2Entry ::= SEQUENCE {
    enc1P698vancservice2Value    Enc1E125enumObj
}

enc1P698vancservice2Value OBJECT-TYPE
    SYNTAX     Enc1E125enumObj
    MAX-ACCESS read-write
    STATUS     current
    DESCRIPTION
    "Specifies data type of service."
::= { enc1P698vancservice2Entry 1 }

enc1P699vancservice3Table OBJECT-TYPE
    SYNTAX SEQUENCE OF Enc1P699vancservice3Entry
    MAX-ACCESS not-accessible
    STATUS     current
    DESCRIPTION
    "
    Name      : VANC Service 3
    Menu Path : /Data/Ancillary
    Details   : Specifies data type of service.
    "
::= { enc1Params 699 }

enc1P699vancservice3Entry OBJECT-TYPE
    SYNTAX Enc1P699vancservice3Entry
    MAX-ACCESS not-accessible
    STATUS     current
    DESCRIPTION
    "Table Entry for VANC Service 3"
    INDEX { slotId }
::= { enc1P699vancservice3Table 1 }

Enc1P699vancservice3Entry ::= SEQUENCE {
    enc1P699vancservice3Value    Enc1E125enumObj
}

enc1P699vancservice3Value OBJECT-TYPE
    SYNTAX     Enc1E125enumObj
    MAX-ACCESS read-write
    STATUS     current
    DESCRIPTION
    "Specifies data type of service."
::= { enc1P699vancservice3Entry 1 }

enc1P700vancservice4Table OBJECT-TYPE
    SYNTAX SEQUENCE OF Enc1P700vancservice4Entry
    MAX-ACCESS not-accessible
    STATUS     current
    DESCRIPTION
    "
    Name      : VANC Service 4
    Menu Path : /Data/Ancillary
    Details   : Specifies data type of service.
    "
::= { enc1Params 700 }

enc1P700vancservice4Entry OBJECT-TYPE
    SYNTAX Enc1P700vancservice4Entry
    MAX-ACCESS not-accessible
    STATUS     current
    DESCRIPTION
    "Table Entry for VANC Service 4"
    INDEX { slotId }
::= { enc1P700vancservice4Table 1 }

Enc1P700vancservice4Entry ::= SEQUENCE {
    enc1P700vancservice4Value    Enc1E125enumObj
}

enc1P700vancservice4Value OBJECT-TYPE
    SYNTAX     Enc1E125enumObj
    MAX-ACCESS read-write
    STATUS     current
    DESCRIPTION
    "Specifies data type of service."
::= { enc1P700vancservice4Entry 1 }

enc1P701vancservice5Table OBJECT-TYPE
    SYNTAX SEQUENCE OF Enc1P701vancservice5Entry
    MAX-ACCESS not-accessible
    STATUS     current
    DESCRIPTION
    "
    Name      : VANC Service 5
    Menu Path : /Data/Ancillary
    Details   : Specifies data type of service.
    "
::= { enc1Params 701 }

enc1P701vancservice5Entry OBJECT-TYPE
    SYNTAX Enc1P701vancservice5Entry
    MAX-ACCESS not-accessible
    STATUS     current
    DESCRIPTION
    "Table Entry for VANC Service 5"
    INDEX { slotId }
::= { enc1P701vancservice5Table 1 }

Enc1P701vancservice5Entry ::= SEQUENCE {
    enc1P701vancservice5Value    Enc1E125enumObj
}

enc1P701vancservice5Value OBJECT-TYPE
    SYNTAX     Enc1E125enumObj
    MAX-ACCESS read-write
    STATUS     current
    DESCRIPTION
    "Specifies data type of service."
::= { enc1P701vancservice5Entry 1 }

enc1P702vancservice6Table OBJECT-TYPE
    SYNTAX SEQUENCE OF Enc1P702vancservice6Entry
    MAX-ACCESS not-accessible
    STATUS     current
    DESCRIPTION
    "
    Name      : VANC Service 6
    Menu Path : /Data/Ancillary
    Details   : Specifies data type of service.
    "
::= { enc1Params 702 }

enc1P702vancservice6Entry OBJECT-TYPE
    SYNTAX Enc1P702vancservice6Entry
    MAX-ACCESS not-accessible
    STATUS     current
    DESCRIPTION
    "Table Entry for VANC Service 6"
    INDEX { slotId }
::= { enc1P702vancservice6Table 1 }

Enc1P702vancservice6Entry ::= SEQUENCE {
    enc1P702vancservice6Value    Enc1E125enumObj
}

enc1P702vancservice6Value OBJECT-TYPE
    SYNTAX     Enc1E125enumObj
    MAX-ACCESS read-write
    STATUS     current
    DESCRIPTION
    "Specifies data type of service."
::= { enc1P702vancservice6Entry 1 }

enc1P703vancservice7Table OBJECT-TYPE
    SYNTAX SEQUENCE OF Enc1P703vancservice7Entry
    MAX-ACCESS not-accessible
    STATUS     current
    DESCRIPTION
    "
    Name      : VANC Service 7
    Menu Path : /Data/Ancillary
    Details   : Specifies data type of service.
    "
::= { enc1Params 703 }

enc1P703vancservice7Entry OBJECT-TYPE
    SYNTAX Enc1P703vancservice7Entry
    MAX-ACCESS not-accessible
    STATUS     current
    DESCRIPTION
    "Table Entry for VANC Service 7"
    INDEX { slotId }
::= { enc1P703vancservice7Table 1 }

Enc1P703vancservice7Entry ::= SEQUENCE {
    enc1P703vancservice7Value    Enc1E125enumObj
}

enc1P703vancservice7Value OBJECT-TYPE
    SYNTAX     Enc1E125enumObj
    MAX-ACCESS read-write
    STATUS     current
    DESCRIPTION
    "Specifies data type of service."
::= { enc1P703vancservice7Entry 1 }

enc1P704vancservice8Table OBJECT-TYPE
    SYNTAX SEQUENCE OF Enc1P704vancservice8Entry
    MAX-ACCESS not-accessible
    STATUS     current
    DESCRIPTION
    "
    Name      : VANC Service 8
    Menu Path : /Data/Ancillary
    Details   : Specifies data type of service.
    "
::= { enc1Params 704 }

enc1P704vancservice8Entry OBJECT-TYPE
    SYNTAX Enc1P704vancservice8Entry
    MAX-ACCESS not-accessible
    STATUS     current
    DESCRIPTION
    "Table Entry for VANC Service 8"
    INDEX { slotId }
::= { enc1P704vancservice8Table 1 }

Enc1P704vancservice8Entry ::= SEQUENCE {
    enc1P704vancservice8Value    Enc1E125enumObj
}

enc1P704vancservice8Value OBJECT-TYPE
    SYNTAX     Enc1E125enumObj
    MAX-ACCESS read-write
    STATUS     current
    DESCRIPTION
    "Specifies data type of service."
::= { enc1P704vancservice8Entry 1 }

enc1P705vancservice9Table OBJECT-TYPE
    SYNTAX SEQUENCE OF Enc1P705vancservice9Entry
    MAX-ACCESS not-accessible
    STATUS     current
    DESCRIPTION
    "
    Name      : VANC Service 9
    Menu Path : /Data/Ancillary
    Details   : Specifies data type of service.
    "
::= { enc1Params 705 }

enc1P705vancservice9Entry OBJECT-TYPE
    SYNTAX Enc1P705vancservice9Entry
    MAX-ACCESS not-accessible
    STATUS     current
    DESCRIPTION
    "Table Entry for VANC Service 9"
    INDEX { slotId }
::= { enc1P705vancservice9Table 1 }

Enc1P705vancservice9Entry ::= SEQUENCE {
    enc1P705vancservice9Value    Enc1E125enumObj
}

enc1P705vancservice9Value OBJECT-TYPE
    SYNTAX     Enc1E125enumObj
    MAX-ACCESS read-write
    STATUS     current
    DESCRIPTION
    "Specifies data type of service."
::= { enc1P705vancservice9Entry 1 }

enc1P706vancservice10Table OBJECT-TYPE
    SYNTAX SEQUENCE OF Enc1P706vancservice10Entry
    MAX-ACCESS not-accessible
    STATUS     current
    DESCRIPTION
    "
    Name      : VANC Service 10
    Menu Path : /Data/Ancillary
    Details   : Specifies data type of service.
    "
::= { enc1Params 706 }

enc1P706vancservice10Entry OBJECT-TYPE
    SYNTAX Enc1P706vancservice10Entry
    MAX-ACCESS not-accessible
    STATUS     current
    DESCRIPTION
    "Table Entry for VANC Service 10"
    INDEX { slotId }
::= { enc1P706vancservice10Table 1 }

Enc1P706vancservice10Entry ::= SEQUENCE {
    enc1P706vancservice10Value    Enc1E125enumObj
}

enc1P706vancservice10Value OBJECT-TYPE
    SYNTAX     Enc1E125enumObj
    MAX-ACCESS read-write
    STATUS     current
    DESCRIPTION
    "Specifies data type of service."
::= { enc1P706vancservice10Entry 1 }

enc1P707vancservice11Table OBJECT-TYPE
    SYNTAX SEQUENCE OF Enc1P707vancservice11Entry
    MAX-ACCESS not-accessible
    STATUS     current
    DESCRIPTION
    "
    Name      : VANC Service 11
    Menu Path : /Data/Ancillary
    Details   : Specifies data type of service.
    "
::= { enc1Params 707 }

enc1P707vancservice11Entry OBJECT-TYPE
    SYNTAX Enc1P707vancservice11Entry
    MAX-ACCESS not-accessible
    STATUS     current
    DESCRIPTION
    "Table Entry for VANC Service 11"
    INDEX { slotId }
::= { enc1P707vancservice11Table 1 }

Enc1P707vancservice11Entry ::= SEQUENCE {
    enc1P707vancservice11Value    Enc1E125enumObj
}

enc1P707vancservice11Value OBJECT-TYPE
    SYNTAX     Enc1E125enumObj
    MAX-ACCESS read-write
    STATUS     current
    DESCRIPTION
    "Specifies data type of service."
::= { enc1P707vancservice11Entry 1 }

enc1P708vancservice12Table OBJECT-TYPE
    SYNTAX SEQUENCE OF Enc1P708vancservice12Entry
    MAX-ACCESS not-accessible
    STATUS     current
    DESCRIPTION
    "
    Name      : VANC Service 12
    Menu Path : /Data/Ancillary
    Details   : Specifies data type of service.
    "
::= { enc1Params 708 }

enc1P708vancservice12Entry OBJECT-TYPE
    SYNTAX Enc1P708vancservice12Entry
    MAX-ACCESS not-accessible
    STATUS     current
    DESCRIPTION
    "Table Entry for VANC Service 12"
    INDEX { slotId }
::= { enc1P708vancservice12Table 1 }

Enc1P708vancservice12Entry ::= SEQUENCE {
    enc1P708vancservice12Value    Enc1E125enumObj
}

enc1P708vancservice12Value OBJECT-TYPE
    SYNTAX     Enc1E125enumObj
    MAX-ACCESS read-write
    STATUS     current
    DESCRIPTION
    "Specifies data type of service."
::= { enc1P708vancservice12Entry 1 }

enc1P709vancservice13Table OBJECT-TYPE
    SYNTAX SEQUENCE OF Enc1P709vancservice13Entry
    MAX-ACCESS not-accessible
    STATUS     current
    DESCRIPTION
    "
    Name      : VANC Service 13
    Menu Path : /Data/Ancillary
    Details   : Specifies data type of service.
    "
::= { enc1Params 709 }

enc1P709vancservice13Entry OBJECT-TYPE
    SYNTAX Enc1P709vancservice13Entry
    MAX-ACCESS not-accessible
    STATUS     current
    DESCRIPTION
    "Table Entry for VANC Service 13"
    INDEX { slotId }
::= { enc1P709vancservice13Table 1 }

Enc1P709vancservice13Entry ::= SEQUENCE {
    enc1P709vancservice13Value    Enc1E125enumObj
}

enc1P709vancservice13Value OBJECT-TYPE
    SYNTAX     Enc1E125enumObj
    MAX-ACCESS read-write
    STATUS     current
    DESCRIPTION
    "Specifies data type of service."
::= { enc1P709vancservice13Entry 1 }

enc1P710vancservice14Table OBJECT-TYPE
    SYNTAX SEQUENCE OF Enc1P710vancservice14Entry
    MAX-ACCESS not-accessible
    STATUS     current
    DESCRIPTION
    "
    Name      : VANC Service 14
    Menu Path : /Data/Ancillary
    Details   : Specifies data type of service.
    "
::= { enc1Params 710 }

enc1P710vancservice14Entry OBJECT-TYPE
    SYNTAX Enc1P710vancservice14Entry
    MAX-ACCESS not-accessible
    STATUS     current
    DESCRIPTION
    "Table Entry for VANC Service 14"
    INDEX { slotId }
::= { enc1P710vancservice14Table 1 }

Enc1P710vancservice14Entry ::= SEQUENCE {
    enc1P710vancservice14Value    Enc1E125enumObj
}

enc1P710vancservice14Value OBJECT-TYPE
    SYNTAX     Enc1E125enumObj
    MAX-ACCESS read-write
    STATUS     current
    DESCRIPTION
    "Specifies data type of service."
::= { enc1P710vancservice14Entry 1 }

enc1P711vancservice15Table OBJECT-TYPE
    SYNTAX SEQUENCE OF Enc1P711vancservice15Entry
    MAX-ACCESS not-accessible
    STATUS     current
    DESCRIPTION
    "
    Name      : VANC Service 15
    Menu Path : /Data/Ancillary
    Details   : Specifies data type of service.
    "
::= { enc1Params 711 }

enc1P711vancservice15Entry OBJECT-TYPE
    SYNTAX Enc1P711vancservice15Entry
    MAX-ACCESS not-accessible
    STATUS     current
    DESCRIPTION
    "Table Entry for VANC Service 15"
    INDEX { slotId }
::= { enc1P711vancservice15Table 1 }

Enc1P711vancservice15Entry ::= SEQUENCE {
    enc1P711vancservice15Value    Enc1E125enumObj
}

enc1P711vancservice15Value OBJECT-TYPE
    SYNTAX     Enc1E125enumObj
    MAX-ACCESS read-write
    STATUS     current
    DESCRIPTION
    "Specifies data type of service."
::= { enc1P711vancservice15Entry 1 }

enc1P712vancservice16Table OBJECT-TYPE
    SYNTAX SEQUENCE OF Enc1P712vancservice16Entry
    MAX-ACCESS not-accessible
    STATUS     current
    DESCRIPTION
    "
    Name      : VANC Service 16
    Menu Path : /Data/Ancillary
    Details   : Specifies data type of service.
    "
::= { enc1Params 712 }

enc1P712vancservice16Entry OBJECT-TYPE
    SYNTAX Enc1P712vancservice16Entry
    MAX-ACCESS not-accessible
    STATUS     current
    DESCRIPTION
    "Table Entry for VANC Service 16"
    INDEX { slotId }
::= { enc1P712vancservice16Table 1 }

Enc1P712vancservice16Entry ::= SEQUENCE {
    enc1P712vancservice16Value    Enc1E125enumObj
}

enc1P712vancservice16Value OBJECT-TYPE
    SYNTAX     Enc1E125enumObj
    MAX-ACCESS read-write
    STATUS     current
    DESCRIPTION
    "Specifies data type of service."
::= { enc1P712vancservice16Entry 1 }

enc1P729dropTable OBJECT-TYPE
    SYNTAX SEQUENCE OF Enc1P729dropEntry
    MAX-ACCESS not-accessible
    STATUS     current
    DESCRIPTION
    "
    Name      : Drop
    Menu Path : /Data/Ancillary Status
    Units     : 
    Precision : 0
    Low Range : 0
    High Range: -1
    Details   : Shows the dropped ANC packet count.

     NOTE: Precision/Units/Ranges represent the state of the
           parameter during the MIB generation, and does not
           neccessary reflect the current state of the parameter
    "
::= { enc1Params 729 }

enc1P729dropEntry OBJECT-TYPE
    SYNTAX Enc1P729dropEntry
    MAX-ACCESS not-accessible
    STATUS     current
    DESCRIPTION
    "Table Entry for Drop"
    INDEX { slotId }
::= { enc1P729dropTable 1 }

Enc1P729dropEntry ::= SEQUENCE {
    enc1P729dropValue    INTEGER
}

enc1P729dropValue OBJECT-TYPE
    SYNTAX     INTEGER
    MAX-ACCESS read-only
    STATUS     current
    DESCRIPTION
    "Shows the dropped ANC packet count."
::= { enc1P729dropEntry 1 }

enc1P730rateTable OBJECT-TYPE
    SYNTAX SEQUENCE OF Enc1P730rateEntry
    MAX-ACCESS not-accessible
    STATUS     current
    DESCRIPTION
    "
    Name      : Rate
    Menu Path : /Data/Ancillary Status
    Units     : Mbits/sec
    Precision : 6
    Low Range : 0
    High Range: 5000000
    Details   : Shows the peak bitrate for VANC data.(Units: Mbits/sec)

     NOTE: Precision/Units/Ranges represent the state of the
           parameter during the MIB generation, and does not
           neccessary reflect the current state of the parameter
    "
::= { enc1Params 730 }

enc1P730rateEntry OBJECT-TYPE
    SYNTAX Enc1P730rateEntry
    MAX-ACCESS not-accessible
    STATUS     current
    DESCRIPTION
    "Table Entry for Rate"
    INDEX { slotId }
::= { enc1P730rateTable 1 }

Enc1P730rateEntry ::= SEQUENCE {
    enc1P730rateValue    INTEGER
}

enc1P730rateValue OBJECT-TYPE
    SYNTAX     INTEGER
    MAX-ACCESS read-only
    STATUS     current
    DESCRIPTION
    "Shows the peak bitrate for VANC data.(Units: Mbits/sec)"
::= { enc1P730rateEntry 1 }

enc1P731service1RateTable OBJECT-TYPE
    SYNTAX SEQUENCE OF Enc1P731service1RateEntry
    MAX-ACCESS not-accessible
    STATUS     current
    DESCRIPTION
    "
    Name      : Service 1 Rate
    Menu Path : /Data/Ancillary Status
    Units     : Mbits/sec
    Precision : 6
    Low Range : 0
    High Range: 5000000
    Details   : Shows the peak bitrate for this service. (Units: Mbits/sec)

     NOTE: Precision/Units/Ranges represent the state of the
           parameter during the MIB generation, and does not
           neccessary reflect the current state of the parameter
    "
::= { enc1Params 731 }

enc1P731service1RateEntry OBJECT-TYPE
    SYNTAX Enc1P731service1RateEntry
    MAX-ACCESS not-accessible
    STATUS     current
    DESCRIPTION
    "Table Entry for Service 1 Rate"
    INDEX { slotId }
::= { enc1P731service1RateTable 1 }

Enc1P731service1RateEntry ::= SEQUENCE {
    enc1P731service1RateValue    INTEGER
}

enc1P731service1RateValue OBJECT-TYPE
    SYNTAX     INTEGER
    MAX-ACCESS read-only
    STATUS     current
    DESCRIPTION
    "Shows the peak bitrate for this service. (Units: Mbits/sec)"
::= { enc1P731service1RateEntry 1 }

enc1P732service1PresentTable OBJECT-TYPE
    SYNTAX SEQUENCE OF Enc1P732service1PresentEntry
    MAX-ACCESS not-accessible
    STATUS     current
    DESCRIPTION
    "
    Name      : Service 1 Present
    Menu Path : /Data/Ancillary Status
    Details   : Shows whether or not this service is present.
    "
::= { enc1Params 732 }

enc1P732service1PresentEntry OBJECT-TYPE
    SYNTAX Enc1P732service1PresentEntry
    MAX-ACCESS not-accessible
    STATUS     current
    DESCRIPTION
    "Table Entry for Service 1 Present"
    INDEX { slotId }
::= { enc1P732service1PresentTable 1 }

Enc1P732service1PresentEntry ::= SEQUENCE {
    enc1P732service1PresentValue    Enc1E9enumObj
}

enc1P732service1PresentValue OBJECT-TYPE
    SYNTAX     Enc1E9enumObj
    MAX-ACCESS read-only
    STATUS     current
    DESCRIPTION
    "Shows whether or not this service is present."
::= { enc1P732service1PresentEntry 1 }

enc1P733service2RateTable OBJECT-TYPE
    SYNTAX SEQUENCE OF Enc1P733service2RateEntry
    MAX-ACCESS not-accessible
    STATUS     current
    DESCRIPTION
    "
    Name      : Service 2 Rate
    Menu Path : /Data/Ancillary Status
    Units     : Mbits/sec
    Precision : 6
    Low Range : 0
    High Range: 5000000
    Details   : Shows the peak bitrate for this service. (Units: Mbits/sec)

     NOTE: Precision/Units/Ranges represent the state of the
           parameter during the MIB generation, and does not
           neccessary reflect the current state of the parameter
    "
::= { enc1Params 733 }

enc1P733service2RateEntry OBJECT-TYPE
    SYNTAX Enc1P733service2RateEntry
    MAX-ACCESS not-accessible
    STATUS     current
    DESCRIPTION
    "Table Entry for Service 2 Rate"
    INDEX { slotId }
::= { enc1P733service2RateTable 1 }

Enc1P733service2RateEntry ::= SEQUENCE {
    enc1P733service2RateValue    INTEGER
}

enc1P733service2RateValue OBJECT-TYPE
    SYNTAX     INTEGER
    MAX-ACCESS read-only
    STATUS     current
    DESCRIPTION
    "Shows the peak bitrate for this service. (Units: Mbits/sec)"
::= { enc1P733service2RateEntry 1 }

enc1P734service2PresentTable OBJECT-TYPE
    SYNTAX SEQUENCE OF Enc1P734service2PresentEntry
    MAX-ACCESS not-accessible
    STATUS     current
    DESCRIPTION
    "
    Name      : Service 2 Present
    Menu Path : /Data/Ancillary Status
    Details   : Shows whether or not this service is present.
    "
::= { enc1Params 734 }

enc1P734service2PresentEntry OBJECT-TYPE
    SYNTAX Enc1P734service2PresentEntry
    MAX-ACCESS not-accessible
    STATUS     current
    DESCRIPTION
    "Table Entry for Service 2 Present"
    INDEX { slotId }
::= { enc1P734service2PresentTable 1 }

Enc1P734service2PresentEntry ::= SEQUENCE {
    enc1P734service2PresentValue    Enc1E9enumObj
}

enc1P734service2PresentValue OBJECT-TYPE
    SYNTAX     Enc1E9enumObj
    MAX-ACCESS read-only
    STATUS     current
    DESCRIPTION
    "Shows whether or not this service is present."
::= { enc1P734service2PresentEntry 1 }

enc1P735service3RateTable OBJECT-TYPE
    SYNTAX SEQUENCE OF Enc1P735service3RateEntry
    MAX-ACCESS not-accessible
    STATUS     current
    DESCRIPTION
    "
    Name      : Service 3 Rate
    Menu Path : /Data/Ancillary Status
    Units     : Mbits/sec
    Precision : 6
    Low Range : 0
    High Range: 5000000
    Details   : Shows the peak bitrate for this service. (Units: Mbits/sec)

     NOTE: Precision/Units/Ranges represent the state of the
           parameter during the MIB generation, and does not
           neccessary reflect the current state of the parameter
    "
::= { enc1Params 735 }

enc1P735service3RateEntry OBJECT-TYPE
    SYNTAX Enc1P735service3RateEntry
    MAX-ACCESS not-accessible
    STATUS     current
    DESCRIPTION
    "Table Entry for Service 3 Rate"
    INDEX { slotId }
::= { enc1P735service3RateTable 1 }

Enc1P735service3RateEntry ::= SEQUENCE {
    enc1P735service3RateValue    INTEGER
}

enc1P735service3RateValue OBJECT-TYPE
    SYNTAX     INTEGER
    MAX-ACCESS read-only
    STATUS     current
    DESCRIPTION
    "Shows the peak bitrate for this service. (Units: Mbits/sec)"
::= { enc1P735service3RateEntry 1 }

enc1P736service3PresentTable OBJECT-TYPE
    SYNTAX SEQUENCE OF Enc1P736service3PresentEntry
    MAX-ACCESS not-accessible
    STATUS     current
    DESCRIPTION
    "
    Name      : Service 3 Present
    Menu Path : /Data/Ancillary Status
    Details   : Shows whether or not this service is present.
    "
::= { enc1Params 736 }

enc1P736service3PresentEntry OBJECT-TYPE
    SYNTAX Enc1P736service3PresentEntry
    MAX-ACCESS not-accessible
    STATUS     current
    DESCRIPTION
    "Table Entry for Service 3 Present"
    INDEX { slotId }
::= { enc1P736service3PresentTable 1 }

Enc1P736service3PresentEntry ::= SEQUENCE {
    enc1P736service3PresentValue    Enc1E9enumObj
}

enc1P736service3PresentValue OBJECT-TYPE
    SYNTAX     Enc1E9enumObj
    MAX-ACCESS read-only
    STATUS     current
    DESCRIPTION
    "Shows whether or not this service is present."
::= { enc1P736service3PresentEntry 1 }

enc1P737service4RateTable OBJECT-TYPE
    SYNTAX SEQUENCE OF Enc1P737service4RateEntry
    MAX-ACCESS not-accessible
    STATUS     current
    DESCRIPTION
    "
    Name      : Service 4 Rate
    Menu Path : /Data/Ancillary Status
    Units     : Mbits/sec
    Precision : 6
    Low Range : 0
    High Range: 5000000
    Details   : Shows the peak bitrate for this service. (Units: Mbits/sec)

     NOTE: Precision/Units/Ranges represent the state of the
           parameter during the MIB generation, and does not
           neccessary reflect the current state of the parameter
    "
::= { enc1Params 737 }

enc1P737service4RateEntry OBJECT-TYPE
    SYNTAX Enc1P737service4RateEntry
    MAX-ACCESS not-accessible
    STATUS     current
    DESCRIPTION
    "Table Entry for Service 4 Rate"
    INDEX { slotId }
::= { enc1P737service4RateTable 1 }

Enc1P737service4RateEntry ::= SEQUENCE {
    enc1P737service4RateValue    INTEGER
}

enc1P737service4RateValue OBJECT-TYPE
    SYNTAX     INTEGER
    MAX-ACCESS read-only
    STATUS     current
    DESCRIPTION
    "Shows the peak bitrate for this service. (Units: Mbits/sec)"
::= { enc1P737service4RateEntry 1 }

enc1P738service4PresentTable OBJECT-TYPE
    SYNTAX SEQUENCE OF Enc1P738service4PresentEntry
    MAX-ACCESS not-accessible
    STATUS     current
    DESCRIPTION
    "
    Name      : Service 4 Present
    Menu Path : /Data/Ancillary Status
    Details   : Shows whether or not this service is present.
    "
::= { enc1Params 738 }

enc1P738service4PresentEntry OBJECT-TYPE
    SYNTAX Enc1P738service4PresentEntry
    MAX-ACCESS not-accessible
    STATUS     current
    DESCRIPTION
    "Table Entry for Service 4 Present"
    INDEX { slotId }
::= { enc1P738service4PresentTable 1 }

Enc1P738service4PresentEntry ::= SEQUENCE {
    enc1P738service4PresentValue    Enc1E9enumObj
}

enc1P738service4PresentValue OBJECT-TYPE
    SYNTAX     Enc1E9enumObj
    MAX-ACCESS read-only
    STATUS     current
    DESCRIPTION
    "Shows whether or not this service is present."
::= { enc1P738service4PresentEntry 1 }

enc1P739service5RateTable OBJECT-TYPE
    SYNTAX SEQUENCE OF Enc1P739service5RateEntry
    MAX-ACCESS not-accessible
    STATUS     current
    DESCRIPTION
    "
    Name      : Service 5 Rate
    Menu Path : /Data/Ancillary Status
    Units     : Mbits/sec
    Precision : 6
    Low Range : 0
    High Range: 5000000
    Details   : Shows the peak bitrate for this service. (Units: Mbits/sec)

     NOTE: Precision/Units/Ranges represent the state of the
           parameter during the MIB generation, and does not
           neccessary reflect the current state of the parameter
    "
::= { enc1Params 739 }

enc1P739service5RateEntry OBJECT-TYPE
    SYNTAX Enc1P739service5RateEntry
    MAX-ACCESS not-accessible
    STATUS     current
    DESCRIPTION
    "Table Entry for Service 5 Rate"
    INDEX { slotId }
::= { enc1P739service5RateTable 1 }

Enc1P739service5RateEntry ::= SEQUENCE {
    enc1P739service5RateValue    INTEGER
}

enc1P739service5RateValue OBJECT-TYPE
    SYNTAX     INTEGER
    MAX-ACCESS read-only
    STATUS     current
    DESCRIPTION
    "Shows the peak bitrate for this service. (Units: Mbits/sec)"
::= { enc1P739service5RateEntry 1 }

enc1P740service5PresentTable OBJECT-TYPE
    SYNTAX SEQUENCE OF Enc1P740service5PresentEntry
    MAX-ACCESS not-accessible
    STATUS     current
    DESCRIPTION
    "
    Name      : Service 5 Present
    Menu Path : /Data/Ancillary Status
    Details   : Shows whether or not this service is present.
    "
::= { enc1Params 740 }

enc1P740service5PresentEntry OBJECT-TYPE
    SYNTAX Enc1P740service5PresentEntry
    MAX-ACCESS not-accessible
    STATUS     current
    DESCRIPTION
    "Table Entry for Service 5 Present"
    INDEX { slotId }
::= { enc1P740service5PresentTable 1 }

Enc1P740service5PresentEntry ::= SEQUENCE {
    enc1P740service5PresentValue    Enc1E9enumObj
}

enc1P740service5PresentValue OBJECT-TYPE
    SYNTAX     Enc1E9enumObj
    MAX-ACCESS read-only
    STATUS     current
    DESCRIPTION
    "Shows whether or not this service is present."
::= { enc1P740service5PresentEntry 1 }

enc1P741service6RateTable OBJECT-TYPE
    SYNTAX SEQUENCE OF Enc1P741service6RateEntry
    MAX-ACCESS not-accessible
    STATUS     current
    DESCRIPTION
    "
    Name      : Service 6 Rate
    Menu Path : /Data/Ancillary Status
    Units     : Mbits/sec
    Precision : 6
    Low Range : 0
    High Range: 5000000
    Details   : Shows the peak bitrate for this service. (Units: Mbits/sec)

     NOTE: Precision/Units/Ranges represent the state of the
           parameter during the MIB generation, and does not
           neccessary reflect the current state of the parameter
    "
::= { enc1Params 741 }

enc1P741service6RateEntry OBJECT-TYPE
    SYNTAX Enc1P741service6RateEntry
    MAX-ACCESS not-accessible
    STATUS     current
    DESCRIPTION
    "Table Entry for Service 6 Rate"
    INDEX { slotId }
::= { enc1P741service6RateTable 1 }

Enc1P741service6RateEntry ::= SEQUENCE {
    enc1P741service6RateValue    INTEGER
}

enc1P741service6RateValue OBJECT-TYPE
    SYNTAX     INTEGER
    MAX-ACCESS read-only
    STATUS     current
    DESCRIPTION
    "Shows the peak bitrate for this service. (Units: Mbits/sec)"
::= { enc1P741service6RateEntry 1 }

enc1P742service6PresentTable OBJECT-TYPE
    SYNTAX SEQUENCE OF Enc1P742service6PresentEntry
    MAX-ACCESS not-accessible
    STATUS     current
    DESCRIPTION
    "
    Name      : Service 6 Present
    Menu Path : /Data/Ancillary Status
    Details   : Shows whether or not this service is present.
    "
::= { enc1Params 742 }

enc1P742service6PresentEntry OBJECT-TYPE
    SYNTAX Enc1P742service6PresentEntry
    MAX-ACCESS not-accessible
    STATUS     current
    DESCRIPTION
    "Table Entry for Service 6 Present"
    INDEX { slotId }
::= { enc1P742service6PresentTable 1 }

Enc1P742service6PresentEntry ::= SEQUENCE {
    enc1P742service6PresentValue    Enc1E9enumObj
}

enc1P742service6PresentValue OBJECT-TYPE
    SYNTAX     Enc1E9enumObj
    MAX-ACCESS read-only
    STATUS     current
    DESCRIPTION
    "Shows whether or not this service is present."
::= { enc1P742service6PresentEntry 1 }

enc1P743service7RateTable OBJECT-TYPE
    SYNTAX SEQUENCE OF Enc1P743service7RateEntry
    MAX-ACCESS not-accessible
    STATUS     current
    DESCRIPTION
    "
    Name      : Service 7 Rate
    Menu Path : /Data/Ancillary Status
    Units     : Mbits/sec
    Precision : 6
    Low Range : 0
    High Range: 5000000
    Details   : Shows the peak bitrate for this service. (Units: Mbits/sec)

     NOTE: Precision/Units/Ranges represent the state of the
           parameter during the MIB generation, and does not
           neccessary reflect the current state of the parameter
    "
::= { enc1Params 743 }

enc1P743service7RateEntry OBJECT-TYPE
    SYNTAX Enc1P743service7RateEntry
    MAX-ACCESS not-accessible
    STATUS     current
    DESCRIPTION
    "Table Entry for Service 7 Rate"
    INDEX { slotId }
::= { enc1P743service7RateTable 1 }

Enc1P743service7RateEntry ::= SEQUENCE {
    enc1P743service7RateValue    INTEGER
}

enc1P743service7RateValue OBJECT-TYPE
    SYNTAX     INTEGER
    MAX-ACCESS read-only
    STATUS     current
    DESCRIPTION
    "Shows the peak bitrate for this service. (Units: Mbits/sec)"
::= { enc1P743service7RateEntry 1 }

enc1P744service7PresentTable OBJECT-TYPE
    SYNTAX SEQUENCE OF Enc1P744service7PresentEntry
    MAX-ACCESS not-accessible
    STATUS     current
    DESCRIPTION
    "
    Name      : Service 7 Present
    Menu Path : /Data/Ancillary Status
    Details   : Shows whether or not this service is present.
    "
::= { enc1Params 744 }

enc1P744service7PresentEntry OBJECT-TYPE
    SYNTAX Enc1P744service7PresentEntry
    MAX-ACCESS not-accessible
    STATUS     current
    DESCRIPTION
    "Table Entry for Service 7 Present"
    INDEX { slotId }
::= { enc1P744service7PresentTable 1 }

Enc1P744service7PresentEntry ::= SEQUENCE {
    enc1P744service7PresentValue    Enc1E9enumObj
}

enc1P744service7PresentValue OBJECT-TYPE
    SYNTAX     Enc1E9enumObj
    MAX-ACCESS read-only
    STATUS     current
    DESCRIPTION
    "Shows whether or not this service is present."
::= { enc1P744service7PresentEntry 1 }

enc1P745service8RateTable OBJECT-TYPE
    SYNTAX SEQUENCE OF Enc1P745service8RateEntry
    MAX-ACCESS not-accessible
    STATUS     current
    DESCRIPTION
    "
    Name      : Service 8 Rate
    Menu Path : /Data/Ancillary Status
    Units     : Mbits/sec
    Precision : 6
    Low Range : 0
    High Range: 5000000
    Details   : Shows the peak bitrate for this service. (Units: Mbits/sec)

     NOTE: Precision/Units/Ranges represent the state of the
           parameter during the MIB generation, and does not
           neccessary reflect the current state of the parameter
    "
::= { enc1Params 745 }

enc1P745service8RateEntry OBJECT-TYPE
    SYNTAX Enc1P745service8RateEntry
    MAX-ACCESS not-accessible
    STATUS     current
    DESCRIPTION
    "Table Entry for Service 8 Rate"
    INDEX { slotId }
::= { enc1P745service8RateTable 1 }

Enc1P745service8RateEntry ::= SEQUENCE {
    enc1P745service8RateValue    INTEGER
}

enc1P745service8RateValue OBJECT-TYPE
    SYNTAX     INTEGER
    MAX-ACCESS read-only
    STATUS     current
    DESCRIPTION
    "Shows the peak bitrate for this service. (Units: Mbits/sec)"
::= { enc1P745service8RateEntry 1 }

enc1P746service8PresentTable OBJECT-TYPE
    SYNTAX SEQUENCE OF Enc1P746service8PresentEntry
    MAX-ACCESS not-accessible
    STATUS     current
    DESCRIPTION
    "
    Name      : Service 8 Present
    Menu Path : /Data/Ancillary Status
    Details   : Shows whether or not this service is present.
    "
::= { enc1Params 746 }

enc1P746service8PresentEntry OBJECT-TYPE
    SYNTAX Enc1P746service8PresentEntry
    MAX-ACCESS not-accessible
    STATUS     current
    DESCRIPTION
    "Table Entry for Service 8 Present"
    INDEX { slotId }
::= { enc1P746service8PresentTable 1 }

Enc1P746service8PresentEntry ::= SEQUENCE {
    enc1P746service8PresentValue    Enc1E9enumObj
}

enc1P746service8PresentValue OBJECT-TYPE
    SYNTAX     Enc1E9enumObj
    MAX-ACCESS read-only
    STATUS     current
    DESCRIPTION
    "Shows whether or not this service is present."
::= { enc1P746service8PresentEntry 1 }

enc1P747service9RateTable OBJECT-TYPE
    SYNTAX SEQUENCE OF Enc1P747service9RateEntry
    MAX-ACCESS not-accessible
    STATUS     current
    DESCRIPTION
    "
    Name      : Service 9 Rate
    Menu Path : /Data/Ancillary Status
    Units     : Mbits/sec
    Precision : 6
    Low Range : 0
    High Range: 5000000
    Details   : Shows the peak bitrate for this service. (Units: Mbits/sec)

     NOTE: Precision/Units/Ranges represent the state of the
           parameter during the MIB generation, and does not
           neccessary reflect the current state of the parameter
    "
::= { enc1Params 747 }

enc1P747service9RateEntry OBJECT-TYPE
    SYNTAX Enc1P747service9RateEntry
    MAX-ACCESS not-accessible
    STATUS     current
    DESCRIPTION
    "Table Entry for Service 9 Rate"
    INDEX { slotId }
::= { enc1P747service9RateTable 1 }

Enc1P747service9RateEntry ::= SEQUENCE {
    enc1P747service9RateValue    INTEGER
}

enc1P747service9RateValue OBJECT-TYPE
    SYNTAX     INTEGER
    MAX-ACCESS read-only
    STATUS     current
    DESCRIPTION
    "Shows the peak bitrate for this service. (Units: Mbits/sec)"
::= { enc1P747service9RateEntry 1 }

enc1P748service9PresentTable OBJECT-TYPE
    SYNTAX SEQUENCE OF Enc1P748service9PresentEntry
    MAX-ACCESS not-accessible
    STATUS     current
    DESCRIPTION
    "
    Name      : Service 9 Present
    Menu Path : /Data/Ancillary Status
    Details   : Shows whether or not this service is present.
    "
::= { enc1Params 748 }

enc1P748service9PresentEntry OBJECT-TYPE
    SYNTAX Enc1P748service9PresentEntry
    MAX-ACCESS not-accessible
    STATUS     current
    DESCRIPTION
    "Table Entry for Service 9 Present"
    INDEX { slotId }
::= { enc1P748service9PresentTable 1 }

Enc1P748service9PresentEntry ::= SEQUENCE {
    enc1P748service9PresentValue    Enc1E9enumObj
}

enc1P748service9PresentValue OBJECT-TYPE
    SYNTAX     Enc1E9enumObj
    MAX-ACCESS read-only
    STATUS     current
    DESCRIPTION
    "Shows whether or not this service is present."
::= { enc1P748service9PresentEntry 1 }

enc1P749service10RateTable OBJECT-TYPE
    SYNTAX SEQUENCE OF Enc1P749service10RateEntry
    MAX-ACCESS not-accessible
    STATUS     current
    DESCRIPTION
    "
    Name      : Service 10 Rate
    Menu Path : /Data/Ancillary Status
    Units     : Mbits/sec
    Precision : 6
    Low Range : 0
    High Range: 5000000
    Details   : Shows the peak bitrate for this service. (Units: Mbits/sec)

     NOTE: Precision/Units/Ranges represent the state of the
           parameter during the MIB generation, and does not
           neccessary reflect the current state of the parameter
    "
::= { enc1Params 749 }

enc1P749service10RateEntry OBJECT-TYPE
    SYNTAX Enc1P749service10RateEntry
    MAX-ACCESS not-accessible
    STATUS     current
    DESCRIPTION
    "Table Entry for Service 10 Rate"
    INDEX { slotId }
::= { enc1P749service10RateTable 1 }

Enc1P749service10RateEntry ::= SEQUENCE {
    enc1P749service10RateValue    INTEGER
}

enc1P749service10RateValue OBJECT-TYPE
    SYNTAX     INTEGER
    MAX-ACCESS read-only
    STATUS     current
    DESCRIPTION
    "Shows the peak bitrate for this service. (Units: Mbits/sec)"
::= { enc1P749service10RateEntry 1 }

enc1P750service10PresentTable OBJECT-TYPE
    SYNTAX SEQUENCE OF Enc1P750service10PresentEntry
    MAX-ACCESS not-accessible
    STATUS     current
    DESCRIPTION
    "
    Name      : Service 10 Present
    Menu Path : /Data/Ancillary Status
    Details   : Shows whether or not this service is present.
    "
::= { enc1Params 750 }

enc1P750service10PresentEntry OBJECT-TYPE
    SYNTAX Enc1P750service10PresentEntry
    MAX-ACCESS not-accessible
    STATUS     current
    DESCRIPTION
    "Table Entry for Service 10 Present"
    INDEX { slotId }
::= { enc1P750service10PresentTable 1 }

Enc1P750service10PresentEntry ::= SEQUENCE {
    enc1P750service10PresentValue    Enc1E9enumObj
}

enc1P750service10PresentValue OBJECT-TYPE
    SYNTAX     Enc1E9enumObj
    MAX-ACCESS read-only
    STATUS     current
    DESCRIPTION
    "Shows whether or not this service is present."
::= { enc1P750service10PresentEntry 1 }

enc1P751service11RateTable OBJECT-TYPE
    SYNTAX SEQUENCE OF Enc1P751service11RateEntry
    MAX-ACCESS not-accessible
    STATUS     current
    DESCRIPTION
    "
    Name      : Service 11 Rate
    Menu Path : /Data/Ancillary Status
    Units     : Mbits/sec
    Precision : 6
    Low Range : 0
    High Range: 5000000
    Details   : Shows the peak bitrate for this service. (Units: Mbits/sec)

     NOTE: Precision/Units/Ranges represent the state of the
           parameter during the MIB generation, and does not
           neccessary reflect the current state of the parameter
    "
::= { enc1Params 751 }

enc1P751service11RateEntry OBJECT-TYPE
    SYNTAX Enc1P751service11RateEntry
    MAX-ACCESS not-accessible
    STATUS     current
    DESCRIPTION
    "Table Entry for Service 11 Rate"
    INDEX { slotId }
::= { enc1P751service11RateTable 1 }

Enc1P751service11RateEntry ::= SEQUENCE {
    enc1P751service11RateValue    INTEGER
}

enc1P751service11RateValue OBJECT-TYPE
    SYNTAX     INTEGER
    MAX-ACCESS read-only
    STATUS     current
    DESCRIPTION
    "Shows the peak bitrate for this service. (Units: Mbits/sec)"
::= { enc1P751service11RateEntry 1 }

enc1P752service11PresentTable OBJECT-TYPE
    SYNTAX SEQUENCE OF Enc1P752service11PresentEntry
    MAX-ACCESS not-accessible
    STATUS     current
    DESCRIPTION
    "
    Name      : Service 11 Present
    Menu Path : /Data/Ancillary Status
    Details   : Shows whether or not this service is present.
    "
::= { enc1Params 752 }

enc1P752service11PresentEntry OBJECT-TYPE
    SYNTAX Enc1P752service11PresentEntry
    MAX-ACCESS not-accessible
    STATUS     current
    DESCRIPTION
    "Table Entry for Service 11 Present"
    INDEX { slotId }
::= { enc1P752service11PresentTable 1 }

Enc1P752service11PresentEntry ::= SEQUENCE {
    enc1P752service11PresentValue    Enc1E9enumObj
}

enc1P752service11PresentValue OBJECT-TYPE
    SYNTAX     Enc1E9enumObj
    MAX-ACCESS read-only
    STATUS     current
    DESCRIPTION
    "Shows whether or not this service is present."
::= { enc1P752service11PresentEntry 1 }

enc1P753service12RateTable OBJECT-TYPE
    SYNTAX SEQUENCE OF Enc1P753service12RateEntry
    MAX-ACCESS not-accessible
    STATUS     current
    DESCRIPTION
    "
    Name      : Service 12 Rate
    Menu Path : /Data/Ancillary Status
    Units     : Mbits/sec
    Precision : 6
    Low Range : 0
    High Range: 5000000
    Details   : Shows the peak bitrate for this service. (Units: Mbits/sec)

     NOTE: Precision/Units/Ranges represent the state of the
           parameter during the MIB generation, and does not
           neccessary reflect the current state of the parameter
    "
::= { enc1Params 753 }

enc1P753service12RateEntry OBJECT-TYPE
    SYNTAX Enc1P753service12RateEntry
    MAX-ACCESS not-accessible
    STATUS     current
    DESCRIPTION
    "Table Entry for Service 12 Rate"
    INDEX { slotId }
::= { enc1P753service12RateTable 1 }

Enc1P753service12RateEntry ::= SEQUENCE {
    enc1P753service12RateValue    INTEGER
}

enc1P753service12RateValue OBJECT-TYPE
    SYNTAX     INTEGER
    MAX-ACCESS read-only
    STATUS     current
    DESCRIPTION
    "Shows the peak bitrate for this service. (Units: Mbits/sec)"
::= { enc1P753service12RateEntry 1 }

enc1P754service12PresentTable OBJECT-TYPE
    SYNTAX SEQUENCE OF Enc1P754service12PresentEntry
    MAX-ACCESS not-accessible
    STATUS     current
    DESCRIPTION
    "
    Name      : Service 12 Present
    Menu Path : /Data/Ancillary Status
    Details   : Shows whether or not this service is present.
    "
::= { enc1Params 754 }

enc1P754service12PresentEntry OBJECT-TYPE
    SYNTAX Enc1P754service12PresentEntry
    MAX-ACCESS not-accessible
    STATUS     current
    DESCRIPTION
    "Table Entry for Service 12 Present"
    INDEX { slotId }
::= { enc1P754service12PresentTable 1 }

Enc1P754service12PresentEntry ::= SEQUENCE {
    enc1P754service12PresentValue    Enc1E9enumObj
}

enc1P754service12PresentValue OBJECT-TYPE
    SYNTAX     Enc1E9enumObj
    MAX-ACCESS read-only
    STATUS     current
    DESCRIPTION
    "Shows whether or not this service is present."
::= { enc1P754service12PresentEntry 1 }

enc1P755service13RateTable OBJECT-TYPE
    SYNTAX SEQUENCE OF Enc1P755service13RateEntry
    MAX-ACCESS not-accessible
    STATUS     current
    DESCRIPTION
    "
    Name      : Service 13 Rate
    Menu Path : /Data/Ancillary Status
    Units     : Mbits/sec
    Precision : 6
    Low Range : 0
    High Range: 5000000
    Details   : Shows the peak bitrate for this service. (Units: Mbits/sec)

     NOTE: Precision/Units/Ranges represent the state of the
           parameter during the MIB generation, and does not
           neccessary reflect the current state of the parameter
    "
::= { enc1Params 755 }

enc1P755service13RateEntry OBJECT-TYPE
    SYNTAX Enc1P755service13RateEntry
    MAX-ACCESS not-accessible
    STATUS     current
    DESCRIPTION
    "Table Entry for Service 13 Rate"
    INDEX { slotId }
::= { enc1P755service13RateTable 1 }

Enc1P755service13RateEntry ::= SEQUENCE {
    enc1P755service13RateValue    INTEGER
}

enc1P755service13RateValue OBJECT-TYPE
    SYNTAX     INTEGER
    MAX-ACCESS read-only
    STATUS     current
    DESCRIPTION
    "Shows the peak bitrate for this service. (Units: Mbits/sec)"
::= { enc1P755service13RateEntry 1 }

enc1P756service13PresentTable OBJECT-TYPE
    SYNTAX SEQUENCE OF Enc1P756service13PresentEntry
    MAX-ACCESS not-accessible
    STATUS     current
    DESCRIPTION
    "
    Name      : Service 13 Present
    Menu Path : /Data/Ancillary Status
    Details   : Shows whether or not this service is present.
    "
::= { enc1Params 756 }

enc1P756service13PresentEntry OBJECT-TYPE
    SYNTAX Enc1P756service13PresentEntry
    MAX-ACCESS not-accessible
    STATUS     current
    DESCRIPTION
    "Table Entry for Service 13 Present"
    INDEX { slotId }
::= { enc1P756service13PresentTable 1 }

Enc1P756service13PresentEntry ::= SEQUENCE {
    enc1P756service13PresentValue    Enc1E9enumObj
}

enc1P756service13PresentValue OBJECT-TYPE
    SYNTAX     Enc1E9enumObj
    MAX-ACCESS read-only
    STATUS     current
    DESCRIPTION
    "Shows whether or not this service is present."
::= { enc1P756service13PresentEntry 1 }

enc1P757service14RateTable OBJECT-TYPE
    SYNTAX SEQUENCE OF Enc1P757service14RateEntry
    MAX-ACCESS not-accessible
    STATUS     current
    DESCRIPTION
    "
    Name      : Service 14 Rate
    Menu Path : /Data/Ancillary Status
    Units     : Mbits/sec
    Precision : 6
    Low Range : 0
    High Range: 5000000
    Details   : Shows the peak bitrate for this service. (Units: Mbits/sec)

     NOTE: Precision/Units/Ranges represent the state of the
           parameter during the MIB generation, and does not
           neccessary reflect the current state of the parameter
    "
::= { enc1Params 757 }

enc1P757service14RateEntry OBJECT-TYPE
    SYNTAX Enc1P757service14RateEntry
    MAX-ACCESS not-accessible
    STATUS     current
    DESCRIPTION
    "Table Entry for Service 14 Rate"
    INDEX { slotId }
::= { enc1P757service14RateTable 1 }

Enc1P757service14RateEntry ::= SEQUENCE {
    enc1P757service14RateValue    INTEGER
}

enc1P757service14RateValue OBJECT-TYPE
    SYNTAX     INTEGER
    MAX-ACCESS read-only
    STATUS     current
    DESCRIPTION
    "Shows the peak bitrate for this service. (Units: Mbits/sec)"
::= { enc1P757service14RateEntry 1 }

enc1P758service14PresentTable OBJECT-TYPE
    SYNTAX SEQUENCE OF Enc1P758service14PresentEntry
    MAX-ACCESS not-accessible
    STATUS     current
    DESCRIPTION
    "
    Name      : Service 14 Present
    Menu Path : /Data/Ancillary Status
    Details   : Shows whether or not this service is present.
    "
::= { enc1Params 758 }

enc1P758service14PresentEntry OBJECT-TYPE
    SYNTAX Enc1P758service14PresentEntry
    MAX-ACCESS not-accessible
    STATUS     current
    DESCRIPTION
    "Table Entry for Service 14 Present"
    INDEX { slotId }
::= { enc1P758service14PresentTable 1 }

Enc1P758service14PresentEntry ::= SEQUENCE {
    enc1P758service14PresentValue    Enc1E9enumObj
}

enc1P758service14PresentValue OBJECT-TYPE
    SYNTAX     Enc1E9enumObj
    MAX-ACCESS read-only
    STATUS     current
    DESCRIPTION
    "Shows whether or not this service is present."
::= { enc1P758service14PresentEntry 1 }

enc1P759service15RateTable OBJECT-TYPE
    SYNTAX SEQUENCE OF Enc1P759service15RateEntry
    MAX-ACCESS not-accessible
    STATUS     current
    DESCRIPTION
    "
    Name      : Service 15 Rate
    Menu Path : /Data/Ancillary Status
    Units     : Mbits/sec
    Precision : 6
    Low Range : 0
    High Range: 5000000
    Details   : Shows the peak bitrate for this service. (Units: Mbits/sec)

     NOTE: Precision/Units/Ranges represent the state of the
           parameter during the MIB generation, and does not
           neccessary reflect the current state of the parameter
    "
::= { enc1Params 759 }

enc1P759service15RateEntry OBJECT-TYPE
    SYNTAX Enc1P759service15RateEntry
    MAX-ACCESS not-accessible
    STATUS     current
    DESCRIPTION
    "Table Entry for Service 15 Rate"
    INDEX { slotId }
::= { enc1P759service15RateTable 1 }

Enc1P759service15RateEntry ::= SEQUENCE {
    enc1P759service15RateValue    INTEGER
}

enc1P759service15RateValue OBJECT-TYPE
    SYNTAX     INTEGER
    MAX-ACCESS read-only
    STATUS     current
    DESCRIPTION
    "Shows the peak bitrate for this service. (Units: Mbits/sec)"
::= { enc1P759service15RateEntry 1 }

enc1P760service15PresentTable OBJECT-TYPE
    SYNTAX SEQUENCE OF Enc1P760service15PresentEntry
    MAX-ACCESS not-accessible
    STATUS     current
    DESCRIPTION
    "
    Name      : Service 15 Present
    Menu Path : /Data/Ancillary Status
    Details   : Shows whether or not this service is present.
    "
::= { enc1Params 760 }

enc1P760service15PresentEntry OBJECT-TYPE
    SYNTAX Enc1P760service15PresentEntry
    MAX-ACCESS not-accessible
    STATUS     current
    DESCRIPTION
    "Table Entry for Service 15 Present"
    INDEX { slotId }
::= { enc1P760service15PresentTable 1 }

Enc1P760service15PresentEntry ::= SEQUENCE {
    enc1P760service15PresentValue    Enc1E9enumObj
}

enc1P760service15PresentValue OBJECT-TYPE
    SYNTAX     Enc1E9enumObj
    MAX-ACCESS read-only
    STATUS     current
    DESCRIPTION
    "Shows whether or not this service is present."
::= { enc1P760service15PresentEntry 1 }

enc1P761service16RateTable OBJECT-TYPE
    SYNTAX SEQUENCE OF Enc1P761service16RateEntry
    MAX-ACCESS not-accessible
    STATUS     current
    DESCRIPTION
    "
    Name      : Service 16 Rate
    Menu Path : /Data/Ancillary Status
    Units     : Mbits/sec
    Precision : 6
    Low Range : 0
    High Range: 5000000
    Details   : Shows the peak bitrate for this service. (Units: Mbits/sec)

     NOTE: Precision/Units/Ranges represent the state of the
           parameter during the MIB generation, and does not
           neccessary reflect the current state of the parameter
    "
::= { enc1Params 761 }

enc1P761service16RateEntry OBJECT-TYPE
    SYNTAX Enc1P761service16RateEntry
    MAX-ACCESS not-accessible
    STATUS     current
    DESCRIPTION
    "Table Entry for Service 16 Rate"
    INDEX { slotId }
::= { enc1P761service16RateTable 1 }

Enc1P761service16RateEntry ::= SEQUENCE {
    enc1P761service16RateValue    INTEGER
}

enc1P761service16RateValue OBJECT-TYPE
    SYNTAX     INTEGER
    MAX-ACCESS read-only
    STATUS     current
    DESCRIPTION
    "Shows the peak bitrate for this service. (Units: Mbits/sec)"
::= { enc1P761service16RateEntry 1 }

enc1P762service16PresentTable OBJECT-TYPE
    SYNTAX SEQUENCE OF Enc1P762service16PresentEntry
    MAX-ACCESS not-accessible
    STATUS     current
    DESCRIPTION
    "
    Name      : Service 16 Present
    Menu Path : /Data/Ancillary Status
    Details   : Shows whether or not this service is present.
    "
::= { enc1Params 762 }

enc1P762service16PresentEntry OBJECT-TYPE
    SYNTAX Enc1P762service16PresentEntry
    MAX-ACCESS not-accessible
    STATUS     current
    DESCRIPTION
    "Table Entry for Service 16 Present"
    INDEX { slotId }
::= { enc1P762service16PresentTable 1 }

Enc1P762service16PresentEntry ::= SEQUENCE {
    enc1P762service16PresentValue    Enc1E9enumObj
}

enc1P762service16PresentValue OBJECT-TYPE
    SYNTAX     Enc1E9enumObj
    MAX-ACCESS read-only
    STATUS     current
    DESCRIPTION
    "Shows whether or not this service is present."
::= { enc1P762service16PresentEntry 1 }

enc1P763sourceTable OBJECT-TYPE
    SYNTAX SEQUENCE OF Enc1P763sourceEntry
    MAX-ACCESS not-accessible
    STATUS     current
    DESCRIPTION
    "
    Name      : Source
    Menu Path : /Data/Closed Caption
    Details   : Specifies the closed caption source for this program.
    "
::= { enc1Params 763 }

enc1P763sourceEntry OBJECT-TYPE
    SYNTAX Enc1P763sourceEntry
    MAX-ACCESS not-accessible
    STATUS     current
    DESCRIPTION
    "Table Entry for Source"
    INDEX { slotId }
::= { enc1P763sourceTable 1 }

Enc1P763sourceEntry ::= SEQUENCE {
    enc1P763sourceValue    Enc1E115enumObj
}

enc1P763sourceValue OBJECT-TYPE
    SYNTAX     Enc1E115enumObj
    MAX-ACCESS read-write
    STATUS     current
    DESCRIPTION
    "Specifies the closed caption source for this program."
::= { enc1P763sourceEntry 1 }

enc1P764transTable OBJECT-TYPE
    SYNTAX SEQUENCE OF Enc1P764transEntry
    MAX-ACCESS not-accessible
    STATUS     current
    DESCRIPTION
    "
    Name      : Trans
    Menu Path : /Data/Closed Caption
    Details   : Specifies the closed caption translation behavior.
    "
::= { enc1Params 764 }

enc1P764transEntry OBJECT-TYPE
    SYNTAX Enc1P764transEntry
    MAX-ACCESS not-accessible
    STATUS     current
    DESCRIPTION
    "Table Entry for Trans"
    INDEX { slotId }
::= { enc1P764transTable 1 }

Enc1P764transEntry ::= SEQUENCE {
    enc1P764transValue    Enc1E118enumObj
}

enc1P764transValue OBJECT-TYPE
    SYNTAX     Enc1E118enumObj
    MAX-ACCESS read-write
    STATUS     current
    DESCRIPTION
    "Specifies the closed caption translation behavior."
::= { enc1P764transEntry 1 }

enc1P765afddefaultTable OBJECT-TYPE
    SYNTAX SEQUENCE OF Enc1P765afddefaultEntry
    MAX-ACCESS not-accessible
    STATUS     current
    DESCRIPTION
    "
    Name      : AFD Default
    Menu Path : /Data/AFD
    Details   : Specifies the default active format description.
    "
::= { enc1Params 765 }

enc1P765afddefaultEntry OBJECT-TYPE
    SYNTAX Enc1P765afddefaultEntry
    MAX-ACCESS not-accessible
    STATUS     current
    DESCRIPTION
    "Table Entry for AFD Default"
    INDEX { slotId }
::= { enc1P765afddefaultTable 1 }

Enc1P765afddefaultEntry ::= SEQUENCE {
    enc1P765afddefaultValue    Enc1E114enumObj
}

enc1P765afddefaultValue OBJECT-TYPE
    SYNTAX     Enc1E114enumObj
    MAX-ACCESS read-write
    STATUS     current
    DESCRIPTION
    "Specifies the default active format description."
::= { enc1P765afddefaultEntry 1 }

enc1P766klvrateTable OBJECT-TYPE
    SYNTAX SEQUENCE OF Enc1P766klvrateEntry
    MAX-ACCESS not-accessible
    STATUS     current
    DESCRIPTION
    "
    Name      : KLV Rate
    Menu Path : /Data/KLV
    Units     : Mbits/sec
    Precision : 6
    Low Range : 0
    High Range: 2000000
    Details   : Specifies maximum TS rate dedicated to KLV data. (Units: Mbits/sec)

     NOTE: Precision/Units/Ranges represent the state of the
           parameter during the MIB generation, and does not
           neccessary reflect the current state of the parameter
    "
::= { enc1Params 766 }

enc1P766klvrateEntry OBJECT-TYPE
    SYNTAX Enc1P766klvrateEntry
    MAX-ACCESS not-accessible
    STATUS     current
    DESCRIPTION
    "Table Entry for KLV Rate"
    INDEX { slotId }
::= { enc1P766klvrateTable 1 }

Enc1P766klvrateEntry ::= SEQUENCE {
    enc1P766klvrateValue    INTEGER
}

enc1P766klvrateValue OBJECT-TYPE
    SYNTAX     INTEGER
    MAX-ACCESS read-write
    STATUS     current
    DESCRIPTION
    "Specifies maximum TS rate dedicated to KLV data. (Units: Mbits/sec)"
::= { enc1P766klvrateEntry 1 }

enc1P767teletextModeTable OBJECT-TYPE
    SYNTAX SEQUENCE OF Enc1P767teletextModeEntry
    MAX-ACCESS not-accessible
    STATUS     current
    DESCRIPTION
    "
    Name      : Teletext Mode
    Menu Path : /Data/VBI over VANC
    Details   : Specifies encoding for teletext data.
    "
::= { enc1Params 767 }

enc1P767teletextModeEntry OBJECT-TYPE
    SYNTAX Enc1P767teletextModeEntry
    MAX-ACCESS not-accessible
    STATUS     current
    DESCRIPTION
    "Table Entry for Teletext Mode"
    INDEX { slotId }
::= { enc1P767teletextModeTable 1 }

Enc1P767teletextModeEntry ::= SEQUENCE {
    enc1P767teletextModeValue    Enc1E110enumObj
}

enc1P767teletextModeValue OBJECT-TYPE
    SYNTAX     Enc1E110enumObj
    MAX-ACCESS read-write
    STATUS     current
    DESCRIPTION
    "Specifies encoding for teletext data."
::= { enc1P767teletextModeEntry 1 }

enc1P768op47LinesTable OBJECT-TYPE
    SYNTAX SEQUENCE OF Enc1P768op47LinesEntry
    MAX-ACCESS not-accessible
    STATUS     current
    DESCRIPTION
    "
    Name      : OP 47 Lines
    Menu Path : /Data/VBI over VANC
    Units     : 
    Precision : 0
    Low Range : 0
    High Range: 34
    Details   : Specifies maximum number of OP47 teletext lines per frame. A value of zero does no teletext processing.

     NOTE: Precision/Units/Ranges represent the state of the
           parameter during the MIB generation, and does not
           neccessary reflect the current state of the parameter
    "
::= { enc1Params 768 }

enc1P768op47LinesEntry OBJECT-TYPE
    SYNTAX Enc1P768op47LinesEntry
    MAX-ACCESS not-accessible
    STATUS     current
    DESCRIPTION
    "Table Entry for OP 47 Lines"
    INDEX { slotId }
::= { enc1P768op47LinesTable 1 }

Enc1P768op47LinesEntry ::= SEQUENCE {
    enc1P768op47LinesValue    INTEGER
}

enc1P768op47LinesValue OBJECT-TYPE
    SYNTAX     INTEGER
    MAX-ACCESS read-write
    STATUS     current
    DESCRIPTION
    "Specifies maximum number of OP47 teletext lines per frame. A value of zero does no teletext processing."
::= { enc1P768op47LinesEntry 1 }

enc1P769prerollTable OBJECT-TYPE
    SYNTAX SEQUENCE OF Enc1P769prerollEntry
    MAX-ACCESS not-accessible
    STATUS     current
    DESCRIPTION
    "
    Name      : Preroll
    Menu Path : /Data/Splice
    Units     : msec
    Precision : 0
    Low Range : 0
    High Range: 10000
    Details   : Specifies preroll time for splice events. (Units: Msec)

     NOTE: Precision/Units/Ranges represent the state of the
           parameter during the MIB generation, and does not
           neccessary reflect the current state of the parameter
    "
::= { enc1Params 769 }

enc1P769prerollEntry OBJECT-TYPE
    SYNTAX Enc1P769prerollEntry
    MAX-ACCESS not-accessible
    STATUS     current
    DESCRIPTION
    "Table Entry for Preroll"
    INDEX { slotId }
::= { enc1P769prerollTable 1 }

Enc1P769prerollEntry ::= SEQUENCE {
    enc1P769prerollValue    INTEGER
}

enc1P769prerollValue OBJECT-TYPE
    SYNTAX     INTEGER
    MAX-ACCESS read-write
    STATUS     current
    DESCRIPTION
    "Specifies preroll time for splice events. (Units: Msec)"
::= { enc1P769prerollEntry 1 }

enc1P770gpimodeTable OBJECT-TYPE
    SYNTAX SEQUENCE OF Enc1P770gpimodeEntry
    MAX-ACCESS not-accessible
    STATUS     current
    DESCRIPTION
    "
    Name      : GPI Mode
    Menu Path : /Data/Splice
    Details   : Specifies GPI mode for splice events.
    "
::= { enc1Params 770 }

enc1P770gpimodeEntry OBJECT-TYPE
    SYNTAX Enc1P770gpimodeEntry
    MAX-ACCESS not-accessible
    STATUS     current
    DESCRIPTION
    "Table Entry for GPI Mode"
    INDEX { slotId }
::= { enc1P770gpimodeTable 1 }

Enc1P770gpimodeEntry ::= SEQUENCE {
    enc1P770gpimodeValue    Enc1E107enumObj
}

enc1P770gpimodeValue OBJECT-TYPE
    SYNTAX     Enc1E107enumObj
    MAX-ACCESS read-write
    STATUS     current
    DESCRIPTION
    "Specifies GPI mode for splice events."
::= { enc1P770gpimodeEntry 1 }

enc1P771spliceTriggerTable OBJECT-TYPE
    SYNTAX SEQUENCE OF Enc1P771spliceTriggerEntry
    MAX-ACCESS not-accessible
    STATUS     current
    DESCRIPTION
    "
    Name      : Splice Trigger
    Menu Path : /Data/Splice
    Details   : Specifies splice event trigger. Should be one of the GPIs, IP, or VANC).
    "
::= { enc1Params 771 }

enc1P771spliceTriggerEntry OBJECT-TYPE
    SYNTAX Enc1P771spliceTriggerEntry
    MAX-ACCESS not-accessible
    STATUS     current
    DESCRIPTION
    "Table Entry for Splice Trigger"
    INDEX { slotId }
::= { enc1P771spliceTriggerTable 1 }

Enc1P771spliceTriggerEntry ::= SEQUENCE {
    enc1P771spliceTriggerValue    Enc1E108enumObj
}

enc1P771spliceTriggerValue OBJECT-TYPE
    SYNTAX     Enc1E108enumObj
    MAX-ACCESS read-write
    STATUS     current
    DESCRIPTION
    "Specifies splice event trigger. Should be one of the GPIs, IP, or VANC)."
::= { enc1P771spliceTriggerEntry 1 }

enc1P772spliceEventTrapTable OBJECT-TYPE
    SYNTAX SEQUENCE OF Enc1P772spliceEventTrapEntry
    MAX-ACCESS not-accessible
    STATUS     current
    DESCRIPTION
    "
    Name      : Splice Event Trap
    Menu Path : /Data/Splice
    Details   : Enables/disables an event trap on reception of splice triggers.
    "
::= { enc1Params 772 }

enc1P772spliceEventTrapEntry OBJECT-TYPE
    SYNTAX Enc1P772spliceEventTrapEntry
    MAX-ACCESS not-accessible
    STATUS     current
    DESCRIPTION
    "Table Entry for Splice Event Trap"
    INDEX { slotId }
::= { enc1P772spliceEventTrapTable 1 }

Enc1P772spliceEventTrapEntry ::= SEQUENCE {
    enc1P772spliceEventTrapValue    Enc1E0enumObj
}

enc1P772spliceEventTrapValue OBJECT-TYPE
    SYNTAX     Enc1E0enumObj
    MAX-ACCESS read-write
    STATUS     current
    DESCRIPTION
    "Enables/disables an event trap on reception of splice triggers."
::= { enc1P772spliceEventTrapEntry 1 }

enc1P773sourceTable OBJECT-TYPE
    SYNTAX SEQUENCE OF Enc1P773sourceEntry
    MAX-ACCESS not-accessible
    STATUS     current
    DESCRIPTION
    "
    Name      : Source
    Menu Path : Not Applicable
    Details   : Specifies source for timecode info.
    "
::= { enc1Params 773 }

enc1P773sourceEntry OBJECT-TYPE
    SYNTAX Enc1P773sourceEntry
    MAX-ACCESS not-accessible
    STATUS     current
    DESCRIPTION
    "Table Entry for Source"
    INDEX { slotId }
::= { enc1P773sourceTable 1 }

Enc1P773sourceEntry ::= SEQUENCE {
    enc1P773sourceValue    Enc1E126enumObj
}

enc1P773sourceValue OBJECT-TYPE
    SYNTAX     Enc1E126enumObj
    MAX-ACCESS read-write
    STATUS     current
    DESCRIPTION
    "Specifies source for timecode info."
::= { enc1P773sourceEntry 1 }

enc1P774sourceFormatTable OBJECT-TYPE
    SYNTAX SEQUENCE OF Enc1P774sourceFormatEntry
    MAX-ACCESS not-accessible
    STATUS     current
    DESCRIPTION
    "
    Name      : Source Format
    Menu Path : Not Applicable
    Details   : Specifies format for timecode insertion.
    "
::= { enc1Params 774 }

enc1P774sourceFormatEntry OBJECT-TYPE
    SYNTAX Enc1P774sourceFormatEntry
    MAX-ACCESS not-accessible
    STATUS     current
    DESCRIPTION
    "Table Entry for Source Format"
    INDEX { slotId }
::= { enc1P774sourceFormatTable 1 }

Enc1P774sourceFormatEntry ::= SEQUENCE {
    enc1P774sourceFormatValue    Enc1E127enumObj
}

enc1P774sourceFormatValue OBJECT-TYPE
    SYNTAX     Enc1E127enumObj
    MAX-ACCESS read-write
    STATUS     current
    DESCRIPTION
    "Specifies format for timecode insertion."
::= { enc1P774sourceFormatEntry 1 }

enc1P775extDataCharsTable OBJECT-TYPE
    SYNTAX SEQUENCE OF Enc1P775extDataCharsEntry
    MAX-ACCESS not-accessible
    STATUS     current
    DESCRIPTION
    "
    Name      : Ext Data Chars
    Menu Path : /Data/Status
    Units     : 
    Precision : 0
    Low Range : 0
    High Range: -1
    Details   : Shows the received byte count for program data.

     NOTE: Precision/Units/Ranges represent the state of the
           parameter during the MIB generation, and does not
           neccessary reflect the current state of the parameter
    "
::= { enc1Params 775 }

enc1P775extDataCharsEntry OBJECT-TYPE
    SYNTAX Enc1P775extDataCharsEntry
    MAX-ACCESS not-accessible
    STATUS     current
    DESCRIPTION
    "Table Entry for Ext Data Chars"
    INDEX { slotId }
::= { enc1P775extDataCharsTable 1 }

Enc1P775extDataCharsEntry ::= SEQUENCE {
    enc1P775extDataCharsValue    INTEGER
}

enc1P775extDataCharsValue OBJECT-TYPE
    SYNTAX     INTEGER
    MAX-ACCESS read-only
    STATUS     current
    DESCRIPTION
    "Shows the received byte count for program data."
::= { enc1P775extDataCharsEntry 1 }

enc1P776extDataDropTable OBJECT-TYPE
    SYNTAX SEQUENCE OF Enc1P776extDataDropEntry
    MAX-ACCESS not-accessible
    STATUS     current
    DESCRIPTION
    "
    Name      : Ext Data Drop
    Menu Path : /Data/Status
    Units     : 
    Precision : 0
    Low Range : 0
    High Range: -1
    Details   : Shows the dropped byte count for program data.

     NOTE: Precision/Units/Ranges represent the state of the
           parameter during the MIB generation, and does not
           neccessary reflect the current state of the parameter
    "
::= { enc1Params 776 }

enc1P776extDataDropEntry OBJECT-TYPE
    SYNTAX Enc1P776extDataDropEntry
    MAX-ACCESS not-accessible
    STATUS     current
    DESCRIPTION
    "Table Entry for Ext Data Drop"
    INDEX { slotId }
::= { enc1P776extDataDropTable 1 }

Enc1P776extDataDropEntry ::= SEQUENCE {
    enc1P776extDataDropValue    INTEGER
}

enc1P776extDataDropValue OBJECT-TYPE
    SYNTAX     INTEGER
    MAX-ACCESS read-only
    STATUS     current
    DESCRIPTION
    "Shows the dropped byte count for program data."
::= { enc1P776extDataDropEntry 1 }

enc1P777cccountTable OBJECT-TYPE
    SYNTAX SEQUENCE OF Enc1P777cccountEntry
    MAX-ACCESS not-accessible
    STATUS     current
    DESCRIPTION
    "
    Name      : CC Count
    Menu Path : /Data/Status
    Units     : 
    Precision : 0
    Low Range : 0
    High Range: -1
    Details   : Shows the count of closed caption characters.

     NOTE: Precision/Units/Ranges represent the state of the
           parameter during the MIB generation, and does not
           neccessary reflect the current state of the parameter
    "
::= { enc1Params 777 }

enc1P777cccountEntry OBJECT-TYPE
    SYNTAX Enc1P777cccountEntry
    MAX-ACCESS not-accessible
    STATUS     current
    DESCRIPTION
    "Table Entry for CC Count"
    INDEX { slotId }
::= { enc1P777cccountTable 1 }

Enc1P777cccountEntry ::= SEQUENCE {
    enc1P777cccountValue    INTEGER
}

enc1P777cccountValue OBJECT-TYPE
    SYNTAX     INTEGER
    MAX-ACCESS read-only
    STATUS     current
    DESCRIPTION
    "Shows the count of closed caption characters."
::= { enc1P777cccountEntry 1 }

enc1P778klvrateTable OBJECT-TYPE
    SYNTAX SEQUENCE OF Enc1P778klvrateEntry
    MAX-ACCESS not-accessible
    STATUS     current
    DESCRIPTION
    "
    Name      : KLV Rate
    Menu Path : /Data/Status
    Units     : Mbits/sec
    Precision : 6
    Low Range : 0
    High Range: 5000000
    Details   : Shows the peak bitrate for KLV-encoded metadata. (Units: Mbits/sec)

     NOTE: Precision/Units/Ranges represent the state of the
           parameter during the MIB generation, and does not
           neccessary reflect the current state of the parameter
    "
::= { enc1Params 778 }

enc1P778klvrateEntry OBJECT-TYPE
    SYNTAX Enc1P778klvrateEntry
    MAX-ACCESS not-accessible
    STATUS     current
    DESCRIPTION
    "Table Entry for KLV Rate"
    INDEX { slotId }
::= { enc1P778klvrateTable 1 }

Enc1P778klvrateEntry ::= SEQUENCE {
    enc1P778klvrateValue    INTEGER
}

enc1P778klvrateValue OBJECT-TYPE
    SYNTAX     INTEGER
    MAX-ACCESS read-only
    STATUS     current
    DESCRIPTION
    "Shows the peak bitrate for KLV-encoded metadata. (Units: Mbits/sec)"
::= { enc1P778klvrateEntry 1 }

enc1P779klvdropTable OBJECT-TYPE
    SYNTAX SEQUENCE OF Enc1P779klvdropEntry
    MAX-ACCESS not-accessible
    STATUS     current
    DESCRIPTION
    "
    Name      : KLV Drop
    Menu Path : /Data/Status
    Units     : 
    Precision : 0
    Low Range : 0
    High Range: -1
    Details   : Shows the number of dropped KLV packets

     NOTE: Precision/Units/Ranges represent the state of the
           parameter during the MIB generation, and does not
           neccessary reflect the current state of the parameter
    "
::= { enc1Params 779 }

enc1P779klvdropEntry OBJECT-TYPE
    SYNTAX Enc1P779klvdropEntry
    MAX-ACCESS not-accessible
    STATUS     current
    DESCRIPTION
    "Table Entry for KLV Drop"
    INDEX { slotId }
::= { enc1P779klvdropTable 1 }

Enc1P779klvdropEntry ::= SEQUENCE {
    enc1P779klvdropValue    INTEGER
}

enc1P779klvdropValue OBJECT-TYPE
    SYNTAX     INTEGER
    MAX-ACCESS read-only
    STATUS     current
    DESCRIPTION
    "Shows the number of dropped KLV packets"
::= { enc1P779klvdropEntry 1 }

enc1P780op47dropTable OBJECT-TYPE
    SYNTAX SEQUENCE OF Enc1P780op47dropEntry
    MAX-ACCESS not-accessible
    STATUS     current
    DESCRIPTION
    "
    Name      : OP47 drop
    Menu Path : /Data/Status
    Units     : 
    Precision : 0
    Low Range : 0
    High Range: -1
    Details   : Shows the dropped line count for OP-47 subtitling.

     NOTE: Precision/Units/Ranges represent the state of the
           parameter during the MIB generation, and does not
           neccessary reflect the current state of the parameter
    "
::= { enc1Params 780 }

enc1P780op47dropEntry OBJECT-TYPE
    SYNTAX Enc1P780op47dropEntry
    MAX-ACCESS not-accessible
    STATUS     current
    DESCRIPTION
    "Table Entry for OP47 drop"
    INDEX { slotId }
::= { enc1P780op47dropTable 1 }

Enc1P780op47dropEntry ::= SEQUENCE {
    enc1P780op47dropValue    INTEGER
}

enc1P780op47dropValue OBJECT-TYPE
    SYNTAX     INTEGER
    MAX-ACCESS read-only
    STATUS     current
    DESCRIPTION
    "Shows the dropped line count for OP-47 subtitling."
::= { enc1P780op47dropEntry 1 }

enc1P781op47LinesTable OBJECT-TYPE
    SYNTAX SEQUENCE OF Enc1P781op47LinesEntry
    MAX-ACCESS not-accessible
    STATUS     current
    DESCRIPTION
    "
    Name      : OP47 Lines
    Menu Path : /Data/Status
    Units     : 
    Precision : 0
    Low Range : 0
    High Range: -1
    Details   : Shows the peak OP-47 teletext lines/frame in the last few seconds.

     NOTE: Precision/Units/Ranges represent the state of the
           parameter during the MIB generation, and does not
           neccessary reflect the current state of the parameter
    "
::= { enc1Params 781 }

enc1P781op47LinesEntry OBJECT-TYPE
    SYNTAX Enc1P781op47LinesEntry
    MAX-ACCESS not-accessible
    STATUS     current
    DESCRIPTION
    "Table Entry for OP47 Lines"
    INDEX { slotId }
::= { enc1P781op47LinesTable 1 }

Enc1P781op47LinesEntry ::= SEQUENCE {
    enc1P781op47LinesValue    INTEGER
}

enc1P781op47LinesValue OBJECT-TYPE
    SYNTAX     INTEGER
    MAX-ACCESS read-only
    STATUS     current
    DESCRIPTION
    "Shows the peak OP-47 teletext lines/frame in the last few seconds."
::= { enc1P781op47LinesEntry 1 }

enc1P782programTable OBJECT-TYPE
    SYNTAX SEQUENCE OF Enc1P782programEntry
    MAX-ACCESS not-accessible
    STATUS     current
    DESCRIPTION
    "
    Name      : Program
    Menu Path : /TS Mux/ASI Output
    Details   : Specifies which program is routed to the ASI output.
    "
::= { enc1Params 782 }

enc1P782programEntry OBJECT-TYPE
    SYNTAX Enc1P782programEntry
    MAX-ACCESS not-accessible
    STATUS     current
    DESCRIPTION
    "Table Entry for Program"
    INDEX { slotId }
::= { enc1P782programTable 1 }

Enc1P782programEntry ::= SEQUENCE {
    enc1P782programValue    Enc1E131enumObj
}

enc1P782programValue OBJECT-TYPE
    SYNTAX     Enc1E131enumObj
    MAX-ACCESS read-write
    STATUS     current
    DESCRIPTION
    "Specifies which program is routed to the ASI output."
::= { enc1P782programEntry 1 }

enc1P783primaryIPAddressTable OBJECT-TYPE
    SYNTAX SEQUENCE OF Enc1P783primaryIPAddressEntry
    MAX-ACCESS not-accessible
    STATUS     current
    DESCRIPTION
    "
    Name      : Primary IP Address
    Menu Path : /IP Encapsulation/Main Program IP
    Details   : Specifies the IP address for this external destination. If zero, data will not be transmitted.
    "
::= { enc1Params 783 }

enc1P783primaryIPAddressEntry OBJECT-TYPE
    SYNTAX Enc1P783primaryIPAddressEntry
    MAX-ACCESS not-accessible
    STATUS     current
    DESCRIPTION
    "Table Entry for Primary IP Address"
    INDEX { slotId }
::= { enc1P783primaryIPAddressTable 1 }

Enc1P783primaryIPAddressEntry ::= SEQUENCE {
    enc1P783primaryIPAddressValue    DisplayString
}

enc1P783primaryIPAddressValue OBJECT-TYPE
    SYNTAX     DisplayString
    MAX-ACCESS read-write
    STATUS     current
    DESCRIPTION
    "Specifies the IP address for this external destination. If zero, data will not be transmitted."
::= { enc1P783primaryIPAddressEntry 1 }

enc1P784primaryPortTable OBJECT-TYPE
    SYNTAX SEQUENCE OF Enc1P784primaryPortEntry
    MAX-ACCESS not-accessible
    STATUS     current
    DESCRIPTION
    "
    Name      : Primary Port
    Menu Path : /IP Encapsulation/Main Program IP
    Units     : 
    Precision : 0
    Low Range : 0
    High Range: 65535
    Details   : Specifies the UDP port for this destination. If zero, data will not be transmitted.

     NOTE: Precision/Units/Ranges represent the state of the
           parameter during the MIB generation, and does not
           neccessary reflect the current state of the parameter
    "
::= { enc1Params 784 }

enc1P784primaryPortEntry OBJECT-TYPE
    SYNTAX Enc1P784primaryPortEntry
    MAX-ACCESS not-accessible
    STATUS     current
    DESCRIPTION
    "Table Entry for Primary Port"
    INDEX { slotId }
::= { enc1P784primaryPortTable 1 }

Enc1P784primaryPortEntry ::= SEQUENCE {
    enc1P784primaryPortValue    INTEGER
}

enc1P784primaryPortValue OBJECT-TYPE
    SYNTAX     INTEGER
    MAX-ACCESS read-write
    STATUS     current
    DESCRIPTION
    "Specifies the UDP port for this destination. If zero, data will not be transmitted."
::= { enc1P784primaryPortEntry 1 }

enc1P785secondaryIPAddressTable OBJECT-TYPE
    SYNTAX SEQUENCE OF Enc1P785secondaryIPAddressEntry
    MAX-ACCESS not-accessible
    STATUS     current
    DESCRIPTION
    "
    Name      : Secondary IP Address
    Menu Path : /IP Encapsulation/Main Program IP
    Details   : Specifies the IP address for this external destination. If zero, data will not be transmitted.
    "
::= { enc1Params 785 }

enc1P785secondaryIPAddressEntry OBJECT-TYPE
    SYNTAX Enc1P785secondaryIPAddressEntry
    MAX-ACCESS not-accessible
    STATUS     current
    DESCRIPTION
    "Table Entry for Secondary IP Address"
    INDEX { slotId }
::= { enc1P785secondaryIPAddressTable 1 }

Enc1P785secondaryIPAddressEntry ::= SEQUENCE {
    enc1P785secondaryIPAddressValue    DisplayString
}

enc1P785secondaryIPAddressValue OBJECT-TYPE
    SYNTAX     DisplayString
    MAX-ACCESS read-write
    STATUS     current
    DESCRIPTION
    "Specifies the IP address for this external destination. If zero, data will not be transmitted."
::= { enc1P785secondaryIPAddressEntry 1 }

enc1P786secondaryPortTable OBJECT-TYPE
    SYNTAX SEQUENCE OF Enc1P786secondaryPortEntry
    MAX-ACCESS not-accessible
    STATUS     current
    DESCRIPTION
    "
    Name      : Secondary Port
    Menu Path : /IP Encapsulation/Main Program IP
    Units     : 
    Precision : 0
    Low Range : 0
    High Range: 65535
    Details   : Specifies the UDP port for this destination. If zero, data will not be transmitted.

     NOTE: Precision/Units/Ranges represent the state of the
           parameter during the MIB generation, and does not
           neccessary reflect the current state of the parameter
    "
::= { enc1Params 786 }

enc1P786secondaryPortEntry OBJECT-TYPE
    SYNTAX Enc1P786secondaryPortEntry
    MAX-ACCESS not-accessible
    STATUS     current
    DESCRIPTION
    "Table Entry for Secondary Port"
    INDEX { slotId }
::= { enc1P786secondaryPortTable 1 }

Enc1P786secondaryPortEntry ::= SEQUENCE {
    enc1P786secondaryPortValue    INTEGER
}

enc1P786secondaryPortValue OBJECT-TYPE
    SYNTAX     INTEGER
    MAX-ACCESS read-write
    STATUS     current
    DESCRIPTION
    "Specifies the UDP port for this destination. If zero, data will not be transmitted."
::= { enc1P786secondaryPortEntry 1 }

enc1P787ipencapsulationTable OBJECT-TYPE
    SYNTAX SEQUENCE OF Enc1P787ipencapsulationEntry
    MAX-ACCESS not-accessible
    STATUS     current
    DESCRIPTION
    "
    Name      : IP Encapsulation
    Menu Path : /IP Encapsulation/Main Program IP
    Details   : Specifies the ip encapsulation for this program.
    "
::= { enc1Params 787 }

enc1P787ipencapsulationEntry OBJECT-TYPE
    SYNTAX Enc1P787ipencapsulationEntry
    MAX-ACCESS not-accessible
    STATUS     current
    DESCRIPTION
    "Table Entry for IP Encapsulation"
    INDEX { slotId }
::= { enc1P787ipencapsulationTable 1 }

Enc1P787ipencapsulationEntry ::= SEQUENCE {
    enc1P787ipencapsulationValue    Enc1E137enumObj
}

enc1P787ipencapsulationValue OBJECT-TYPE
    SYNTAX     Enc1E137enumObj
    MAX-ACCESS read-write
    STATUS     current
    DESCRIPTION
    "Specifies the ip encapsulation for this program."
::= { enc1P787ipencapsulationEntry 1 }

enc1P788fecTable OBJECT-TYPE
    SYNTAX SEQUENCE OF Enc1P788fecEntry
    MAX-ACCESS not-accessible
    STATUS     current
    DESCRIPTION
    "
    Name      : FEC
    Menu Path : /IP Encapsulation/Main Program IP
    Details   : Specifies FEC settings for this program.
    "
::= { enc1Params 788 }

enc1P788fecEntry OBJECT-TYPE
    SYNTAX Enc1P788fecEntry
    MAX-ACCESS not-accessible
    STATUS     current
    DESCRIPTION
    "Table Entry for FEC"
    INDEX { slotId }
::= { enc1P788fecTable 1 }

Enc1P788fecEntry ::= SEQUENCE {
    enc1P788fecValue    Enc1E138enumObj
}

enc1P788fecValue OBJECT-TYPE
    SYNTAX     Enc1E138enumObj
    MAX-ACCESS read-write
    STATUS     current
    DESCRIPTION
    "Specifies FEC settings for this program."
::= { enc1P788fecEntry 1 }

enc1P789rowFECTable OBJECT-TYPE
    SYNTAX SEQUENCE OF Enc1P789rowFECEntry
    MAX-ACCESS not-accessible
    STATUS     current
    DESCRIPTION
    "
    Name      : Row FEC
    Menu Path : /IP Encapsulation/Main Program IP
    Details   : Specifies whether or not ROW FEC is enabled.
    "
::= { enc1Params 789 }

enc1P789rowFECEntry OBJECT-TYPE
    SYNTAX Enc1P789rowFECEntry
    MAX-ACCESS not-accessible
    STATUS     current
    DESCRIPTION
    "Table Entry for Row FEC"
    INDEX { slotId }
::= { enc1P789rowFECTable 1 }

Enc1P789rowFECEntry ::= SEQUENCE {
    enc1P789rowFECValue    Enc1E0enumObj
}

enc1P789rowFECValue OBJECT-TYPE
    SYNTAX     Enc1E0enumObj
    MAX-ACCESS read-write
    STATUS     current
    DESCRIPTION
    "Specifies whether or not ROW FEC is enabled."
::= { enc1P789rowFECEntry 1 }

enc1P790fecorderTable OBJECT-TYPE
    SYNTAX SEQUENCE OF Enc1P790fecorderEntry
    MAX-ACCESS not-accessible
    STATUS     current
    DESCRIPTION
    "
    Name      : FEC Order
    Menu Path : /IP Encapsulation/Main Program IP
    Units     : 
    Precision : 0
    Low Range : 4
    High Range: 20
    Details   : Specifies the FEC order for this program.

     NOTE: Precision/Units/Ranges represent the state of the
           parameter during the MIB generation, and does not
           neccessary reflect the current state of the parameter
    "
::= { enc1Params 790 }

enc1P790fecorderEntry OBJECT-TYPE
    SYNTAX Enc1P790fecorderEntry
    MAX-ACCESS not-accessible
    STATUS     current
    DESCRIPTION
    "Table Entry for FEC Order"
    INDEX { slotId }
::= { enc1P790fecorderTable 1 }

Enc1P790fecorderEntry ::= SEQUENCE {
    enc1P790fecorderValue    INTEGER
}

enc1P790fecorderValue OBJECT-TYPE
    SYNTAX     INTEGER
    MAX-ACCESS read-write
    STATUS     current
    DESCRIPTION
    "Specifies the FEC order for this program."
::= { enc1P790fecorderEntry 1 }

enc1P791fecperiodTable OBJECT-TYPE
    SYNTAX SEQUENCE OF Enc1P791fecperiodEntry
    MAX-ACCESS not-accessible
    STATUS     current
    DESCRIPTION
    "
    Name      : FEC Period
    Menu Path : /IP Encapsulation/Main Program IP
    Units     : 
    Precision : 0
    Low Range : 1
    High Range: 20
    Details   : Specifies the FEC period for this program.

     NOTE: Precision/Units/Ranges represent the state of the
           parameter during the MIB generation, and does not
           neccessary reflect the current state of the parameter
    "
::= { enc1Params 791 }

enc1P791fecperiodEntry OBJECT-TYPE
    SYNTAX Enc1P791fecperiodEntry
    MAX-ACCESS not-accessible
    STATUS     current
    DESCRIPTION
    "Table Entry for FEC Period"
    INDEX { slotId }
::= { enc1P791fecperiodTable 1 }

Enc1P791fecperiodEntry ::= SEQUENCE {
    enc1P791fecperiodValue    INTEGER
}

enc1P791fecperiodValue OBJECT-TYPE
    SYNTAX     INTEGER
    MAX-ACCESS read-write
    STATUS     current
    DESCRIPTION
    "Specifies the FEC period for this program."
::= { enc1P791fecperiodEntry 1 }

enc1P792tspacketsperIPTable OBJECT-TYPE
    SYNTAX SEQUENCE OF Enc1P792tspacketsperIPEntry
    MAX-ACCESS not-accessible
    STATUS     current
    DESCRIPTION
    "
    Name      : TS Packets per IP
    Menu Path : /IP Encapsulation/Main Program IP
    Units     : 
    Precision : 0
    Low Range : 1
    High Range: 7
    Details   : Specifies number of TS packets per IP packet.

     NOTE: Precision/Units/Ranges represent the state of the
           parameter during the MIB generation, and does not
           neccessary reflect the current state of the parameter
    "
::= { enc1Params 792 }

enc1P792tspacketsperIPEntry OBJECT-TYPE
    SYNTAX Enc1P792tspacketsperIPEntry
    MAX-ACCESS not-accessible
    STATUS     current
    DESCRIPTION
    "Table Entry for TS Packets per IP"
    INDEX { slotId }
::= { enc1P792tspacketsperIPTable 1 }

Enc1P792tspacketsperIPEntry ::= SEQUENCE {
    enc1P792tspacketsperIPValue    INTEGER
}

enc1P792tspacketsperIPValue OBJECT-TYPE
    SYNTAX     INTEGER
    MAX-ACCESS read-write
    STATUS     current
    DESCRIPTION
    "Specifies number of TS packets per IP packet."
::= { enc1P792tspacketsperIPEntry 1 }

enc1P793typeofServiceTable OBJECT-TYPE
    SYNTAX SEQUENCE OF Enc1P793typeofServiceEntry
    MAX-ACCESS not-accessible
    STATUS     current
    DESCRIPTION
    "
    Name      : Type of Service
    Menu Path : /IP Encapsulation/Main Program IP
    Units     : 
    Precision : 0
    Low Range : 0
    High Range: 255
    Details   : Specifies type of service for program.

     NOTE: Precision/Units/Ranges represent the state of the
           parameter during the MIB generation, and does not
           neccessary reflect the current state of the parameter
    "
::= { enc1Params 793 }

enc1P793typeofServiceEntry OBJECT-TYPE
    SYNTAX Enc1P793typeofServiceEntry
    MAX-ACCESS not-accessible
    STATUS     current
    DESCRIPTION
    "Table Entry for Type of Service"
    INDEX { slotId }
::= { enc1P793typeofServiceTable 1 }

Enc1P793typeofServiceEntry ::= SEQUENCE {
    enc1P793typeofServiceValue    INTEGER
}

enc1P793typeofServiceValue OBJECT-TYPE
    SYNTAX     INTEGER
    MAX-ACCESS read-write
    STATUS     current
    DESCRIPTION
    "Specifies type of service for program."
::= { enc1P793typeofServiceEntry 1 }

enc1P794primaryIPAddressTable OBJECT-TYPE
    SYNTAX SEQUENCE OF Enc1P794primaryIPAddressEntry
    MAX-ACCESS not-accessible
    STATUS     current
    DESCRIPTION
    "
    Name      : Primary IP Address
    Menu Path : /IP Encapsulation/Pip Program IP
    Details   : Specifies the IP address for this external destination.
    "
::= { enc1Params 794 }

enc1P794primaryIPAddressEntry OBJECT-TYPE
    SYNTAX Enc1P794primaryIPAddressEntry
    MAX-ACCESS not-accessible
    STATUS     current
    DESCRIPTION
    "Table Entry for Primary IP Address"
    INDEX { slotId }
::= { enc1P794primaryIPAddressTable 1 }

Enc1P794primaryIPAddressEntry ::= SEQUENCE {
    enc1P794primaryIPAddressValue    DisplayString
}

enc1P794primaryIPAddressValue OBJECT-TYPE
    SYNTAX     DisplayString
    MAX-ACCESS read-write
    STATUS     current
    DESCRIPTION
    "Specifies the IP address for this external destination."
::= { enc1P794primaryIPAddressEntry 1 }

enc1P795primaryPortTable OBJECT-TYPE
    SYNTAX SEQUENCE OF Enc1P795primaryPortEntry
    MAX-ACCESS not-accessible
    STATUS     current
    DESCRIPTION
    "
    Name      : Primary Port
    Menu Path : /IP Encapsulation/Pip Program IP
    Units     : 
    Precision : 0
    Low Range : 0
    High Range: 65535
    Details   : Specifies the UDP port for this destination.

     NOTE: Precision/Units/Ranges represent the state of the
           parameter during the MIB generation, and does not
           neccessary reflect the current state of the parameter
    "
::= { enc1Params 795 }

enc1P795primaryPortEntry OBJECT-TYPE
    SYNTAX Enc1P795primaryPortEntry
    MAX-ACCESS not-accessible
    STATUS     current
    DESCRIPTION
    "Table Entry for Primary Port"
    INDEX { slotId }
::= { enc1P795primaryPortTable 1 }

Enc1P795primaryPortEntry ::= SEQUENCE {
    enc1P795primaryPortValue    INTEGER
}

enc1P795primaryPortValue OBJECT-TYPE
    SYNTAX     INTEGER
    MAX-ACCESS read-write
    STATUS     current
    DESCRIPTION
    "Specifies the UDP port for this destination."
::= { enc1P795primaryPortEntry 1 }

enc1P796secondaryIPAddressTable OBJECT-TYPE
    SYNTAX SEQUENCE OF Enc1P796secondaryIPAddressEntry
    MAX-ACCESS not-accessible
    STATUS     current
    DESCRIPTION
    "
    Name      : Secondary IP Address
    Menu Path : /IP Encapsulation/Pip Program IP
    Details   : Specifies the IP address for this external destination.
    "
::= { enc1Params 796 }

enc1P796secondaryIPAddressEntry OBJECT-TYPE
    SYNTAX Enc1P796secondaryIPAddressEntry
    MAX-ACCESS not-accessible
    STATUS     current
    DESCRIPTION
    "Table Entry for Secondary IP Address"
    INDEX { slotId }
::= { enc1P796secondaryIPAddressTable 1 }

Enc1P796secondaryIPAddressEntry ::= SEQUENCE {
    enc1P796secondaryIPAddressValue    DisplayString
}

enc1P796secondaryIPAddressValue OBJECT-TYPE
    SYNTAX     DisplayString
    MAX-ACCESS read-write
    STATUS     current
    DESCRIPTION
    "Specifies the IP address for this external destination."
::= { enc1P796secondaryIPAddressEntry 1 }

enc1P797secondaryPortTable OBJECT-TYPE
    SYNTAX SEQUENCE OF Enc1P797secondaryPortEntry
    MAX-ACCESS not-accessible
    STATUS     current
    DESCRIPTION
    "
    Name      : Secondary Port
    Menu Path : /IP Encapsulation/Pip Program IP
    Units     : 
    Precision : 0
    Low Range : 0
    High Range: 65535
    Details   : Specifies the UDP port for this destination.

     NOTE: Precision/Units/Ranges represent the state of the
           parameter during the MIB generation, and does not
           neccessary reflect the current state of the parameter
    "
::= { enc1Params 797 }

enc1P797secondaryPortEntry OBJECT-TYPE
    SYNTAX Enc1P797secondaryPortEntry
    MAX-ACCESS not-accessible
    STATUS     current
    DESCRIPTION
    "Table Entry for Secondary Port"
    INDEX { slotId }
::= { enc1P797secondaryPortTable 1 }

Enc1P797secondaryPortEntry ::= SEQUENCE {
    enc1P797secondaryPortValue    INTEGER
}

enc1P797secondaryPortValue OBJECT-TYPE
    SYNTAX     INTEGER
    MAX-ACCESS read-write
    STATUS     current
    DESCRIPTION
    "Specifies the UDP port for this destination."
::= { enc1P797secondaryPortEntry 1 }

enc1P798ipencapsulationTable OBJECT-TYPE
    SYNTAX SEQUENCE OF Enc1P798ipencapsulationEntry
    MAX-ACCESS not-accessible
    STATUS     current
    DESCRIPTION
    "
    Name      : IP Encapsulation
    Menu Path : /IP Encapsulation/Pip Program IP
    Details   : Specifies the ip encapsulation mode (TS on UDP, TS on RTP, or RTP-RTCP) for this program.
    "
::= { enc1Params 798 }

enc1P798ipencapsulationEntry OBJECT-TYPE
    SYNTAX Enc1P798ipencapsulationEntry
    MAX-ACCESS not-accessible
    STATUS     current
    DESCRIPTION
    "Table Entry for IP Encapsulation"
    INDEX { slotId }
::= { enc1P798ipencapsulationTable 1 }

Enc1P798ipencapsulationEntry ::= SEQUENCE {
    enc1P798ipencapsulationValue    Enc1E137enumObj
}

enc1P798ipencapsulationValue OBJECT-TYPE
    SYNTAX     Enc1E137enumObj
    MAX-ACCESS read-write
    STATUS     current
    DESCRIPTION
    "Specifies the ip encapsulation mode (TS on UDP, TS on RTP, or RTP-RTCP) for this program."
::= { enc1P798ipencapsulationEntry 1 }

enc1P799fecTable OBJECT-TYPE
    SYNTAX SEQUENCE OF Enc1P799fecEntry
    MAX-ACCESS not-accessible
    STATUS     current
    DESCRIPTION
    "
    Name      : FEC
    Menu Path : /IP Encapsulation/Pip Program IP
    Details   : Specifies ROW FEC settings.
    "
::= { enc1Params 799 }

enc1P799fecEntry OBJECT-TYPE
    SYNTAX Enc1P799fecEntry
    MAX-ACCESS not-accessible
    STATUS     current
    DESCRIPTION
    "Table Entry for FEC"
    INDEX { slotId }
::= { enc1P799fecTable 1 }

Enc1P799fecEntry ::= SEQUENCE {
    enc1P799fecValue    Enc1E138enumObj
}

enc1P799fecValue OBJECT-TYPE
    SYNTAX     Enc1E138enumObj
    MAX-ACCESS read-write
    STATUS     current
    DESCRIPTION
    "Specifies ROW FEC settings."
::= { enc1P799fecEntry 1 }

enc1P800rowFECTable OBJECT-TYPE
    SYNTAX SEQUENCE OF Enc1P800rowFECEntry
    MAX-ACCESS not-accessible
    STATUS     current
    DESCRIPTION
    "
    Name      : Row FEC
    Menu Path : /IP Encapsulation/Pip Program IP
    Details   : Specifies whether or not ROW FEC is enabled.
    "
::= { enc1Params 800 }

enc1P800rowFECEntry OBJECT-TYPE
    SYNTAX Enc1P800rowFECEntry
    MAX-ACCESS not-accessible
    STATUS     current
    DESCRIPTION
    "Table Entry for Row FEC"
    INDEX { slotId }
::= { enc1P800rowFECTable 1 }

Enc1P800rowFECEntry ::= SEQUENCE {
    enc1P800rowFECValue    Enc1E0enumObj
}

enc1P800rowFECValue OBJECT-TYPE
    SYNTAX     Enc1E0enumObj
    MAX-ACCESS read-write
    STATUS     current
    DESCRIPTION
    "Specifies whether or not ROW FEC is enabled."
::= { enc1P800rowFECEntry 1 }

enc1P801fecorderTable OBJECT-TYPE
    SYNTAX SEQUENCE OF Enc1P801fecorderEntry
    MAX-ACCESS not-accessible
    STATUS     current
    DESCRIPTION
    "
    Name      : FEC Order
    Menu Path : /IP Encapsulation/Pip Program IP
    Units     : 
    Precision : 0
    Low Range : 4
    High Range: 20
    Details   : Specifies the FEC order for this program.

     NOTE: Precision/Units/Ranges represent the state of the
           parameter during the MIB generation, and does not
           neccessary reflect the current state of the parameter
    "
::= { enc1Params 801 }

enc1P801fecorderEntry OBJECT-TYPE
    SYNTAX Enc1P801fecorderEntry
    MAX-ACCESS not-accessible
    STATUS     current
    DESCRIPTION
    "Table Entry for FEC Order"
    INDEX { slotId }
::= { enc1P801fecorderTable 1 }

Enc1P801fecorderEntry ::= SEQUENCE {
    enc1P801fecorderValue    INTEGER
}

enc1P801fecorderValue OBJECT-TYPE
    SYNTAX     INTEGER
    MAX-ACCESS read-write
    STATUS     current
    DESCRIPTION
    "Specifies the FEC order for this program."
::= { enc1P801fecorderEntry 1 }

enc1P802fecperiodTable OBJECT-TYPE
    SYNTAX SEQUENCE OF Enc1P802fecperiodEntry
    MAX-ACCESS not-accessible
    STATUS     current
    DESCRIPTION
    "
    Name      : FEC Period
    Menu Path : /IP Encapsulation/Pip Program IP
    Units     : 
    Precision : 0
    Low Range : 1
    High Range: 20
    Details   : Specifies the FEC period for this program.

     NOTE: Precision/Units/Ranges represent the state of the
           parameter during the MIB generation, and does not
           neccessary reflect the current state of the parameter
    "
::= { enc1Params 802 }

enc1P802fecperiodEntry OBJECT-TYPE
    SYNTAX Enc1P802fecperiodEntry
    MAX-ACCESS not-accessible
    STATUS     current
    DESCRIPTION
    "Table Entry for FEC Period"
    INDEX { slotId }
::= { enc1P802fecperiodTable 1 }

Enc1P802fecperiodEntry ::= SEQUENCE {
    enc1P802fecperiodValue    INTEGER
}

enc1P802fecperiodValue OBJECT-TYPE
    SYNTAX     INTEGER
    MAX-ACCESS read-write
    STATUS     current
    DESCRIPTION
    "Specifies the FEC period for this program."
::= { enc1P802fecperiodEntry 1 }

enc1P803tspacketsperIPTable OBJECT-TYPE
    SYNTAX SEQUENCE OF Enc1P803tspacketsperIPEntry
    MAX-ACCESS not-accessible
    STATUS     current
    DESCRIPTION
    "
    Name      : TS Packets per IP
    Menu Path : /IP Encapsulation/Pip Program IP
    Units     : 
    Precision : 0
    Low Range : 1
    High Range: 7
    Details   : Specifies number of TS packets per IP packet.

     NOTE: Precision/Units/Ranges represent the state of the
           parameter during the MIB generation, and does not
           neccessary reflect the current state of the parameter
    "
::= { enc1Params 803 }

enc1P803tspacketsperIPEntry OBJECT-TYPE
    SYNTAX Enc1P803tspacketsperIPEntry
    MAX-ACCESS not-accessible
    STATUS     current
    DESCRIPTION
    "Table Entry for TS Packets per IP"
    INDEX { slotId }
::= { enc1P803tspacketsperIPTable 1 }

Enc1P803tspacketsperIPEntry ::= SEQUENCE {
    enc1P803tspacketsperIPValue    INTEGER
}

enc1P803tspacketsperIPValue OBJECT-TYPE
    SYNTAX     INTEGER
    MAX-ACCESS read-write
    STATUS     current
    DESCRIPTION
    "Specifies number of TS packets per IP packet."
::= { enc1P803tspacketsperIPEntry 1 }

enc1P804typeofServiceTable OBJECT-TYPE
    SYNTAX SEQUENCE OF Enc1P804typeofServiceEntry
    MAX-ACCESS not-accessible
    STATUS     current
    DESCRIPTION
    "
    Name      : Type of Service
    Menu Path : /IP Encapsulation/Pip Program IP
    Units     : 
    Precision : 0
    Low Range : 0
    High Range: 255
    Details   : Specifies type of service for this program.

     NOTE: Precision/Units/Ranges represent the state of the
           parameter during the MIB generation, and does not
           neccessary reflect the current state of the parameter
    "
::= { enc1Params 804 }

enc1P804typeofServiceEntry OBJECT-TYPE
    SYNTAX Enc1P804typeofServiceEntry
    MAX-ACCESS not-accessible
    STATUS     current
    DESCRIPTION
    "Table Entry for Type of Service"
    INDEX { slotId }
::= { enc1P804typeofServiceTable 1 }

Enc1P804typeofServiceEntry ::= SEQUENCE {
    enc1P804typeofServiceValue    INTEGER
}

enc1P804typeofServiceValue OBJECT-TYPE
    SYNTAX     INTEGER
    MAX-ACCESS read-write
    STATUS     current
    DESCRIPTION
    "Specifies type of service for this program."
::= { enc1P804typeofServiceEntry 1 }

enc1P805rateTable OBJECT-TYPE
    SYNTAX SEQUENCE OF Enc1P805rateEntry
    MAX-ACCESS not-accessible
    STATUS     current
    DESCRIPTION
    "
    Name      : Rate
    Menu Path : /TS Mux/ASI Status
    Units     : Mbits/sec
    Precision : 6
    Low Range : 0
    High Range: 150000000
    Details   : Output ASI rate. (Units: Mbits/sec)

     NOTE: Precision/Units/Ranges represent the state of the
           parameter during the MIB generation, and does not
           neccessary reflect the current state of the parameter
    "
::= { enc1Params 805 }

enc1P805rateEntry OBJECT-TYPE
    SYNTAX Enc1P805rateEntry
    MAX-ACCESS not-accessible
    STATUS     current
    DESCRIPTION
    "Table Entry for Rate"
    INDEX { slotId }
::= { enc1P805rateTable 1 }

Enc1P805rateEntry ::= SEQUENCE {
    enc1P805rateValue    INTEGER
}

enc1P805rateValue OBJECT-TYPE
    SYNTAX     INTEGER
    MAX-ACCESS read-only
    STATUS     current
    DESCRIPTION
    "Output ASI rate. (Units: Mbits/sec)"
::= { enc1P805rateEntry 1 }

enc1P806videoTSRateTable OBJECT-TYPE
    SYNTAX SEQUENCE OF Enc1P806videoTSRateEntry
    MAX-ACCESS not-accessible
    STATUS     current
    DESCRIPTION
    "
    Name      : Video TS Rate
    Menu Path : /TS Mux/ASI Status
    Units     : Mbits/sec
    Precision : 6
    Low Range : 0
    High Range: 120000000
    Details   : Output video TS rate. (Units: Mbits/sec)

     NOTE: Precision/Units/Ranges represent the state of the
           parameter during the MIB generation, and does not
           neccessary reflect the current state of the parameter
    "
::= { enc1Params 806 }

enc1P806videoTSRateEntry OBJECT-TYPE
    SYNTAX Enc1P806videoTSRateEntry
    MAX-ACCESS not-accessible
    STATUS     current
    DESCRIPTION
    "Table Entry for Video TS Rate"
    INDEX { slotId }
::= { enc1P806videoTSRateTable 1 }

Enc1P806videoTSRateEntry ::= SEQUENCE {
    enc1P806videoTSRateValue    INTEGER
}

enc1P806videoTSRateValue OBJECT-TYPE
    SYNTAX     INTEGER
    MAX-ACCESS read-only
    STATUS     current
    DESCRIPTION
    "Output video TS rate. (Units: Mbits/sec)"
::= { enc1P806videoTSRateEntry 1 }

enc1P807audioTSRateTable OBJECT-TYPE
    SYNTAX SEQUENCE OF Enc1P807audioTSRateEntry
    MAX-ACCESS not-accessible
    STATUS     current
    DESCRIPTION
    "
    Name      : Audio TS Rate
    Menu Path : /TS Mux/ASI Status
    Units     : Mbits/sec
    Precision : 6
    Low Range : 0
    High Range: 20000000
    Details   : Output audio TS rate. (Units: Mbits/sec)

     NOTE: Precision/Units/Ranges represent the state of the
           parameter during the MIB generation, and does not
           neccessary reflect the current state of the parameter
    "
::= { enc1Params 807 }

enc1P807audioTSRateEntry OBJECT-TYPE
    SYNTAX Enc1P807audioTSRateEntry
    MAX-ACCESS not-accessible
    STATUS     current
    DESCRIPTION
    "Table Entry for Audio TS Rate"
    INDEX { slotId }
::= { enc1P807audioTSRateTable 1 }

Enc1P807audioTSRateEntry ::= SEQUENCE {
    enc1P807audioTSRateValue    INTEGER
}

enc1P807audioTSRateValue OBJECT-TYPE
    SYNTAX     INTEGER
    MAX-ACCESS read-only
    STATUS     current
    DESCRIPTION
    "Output audio TS rate. (Units: Mbits/sec)"
::= { enc1P807audioTSRateEntry 1 }

enc1P808tspacketsTable OBJECT-TYPE
    SYNTAX SEQUENCE OF Enc1P808tspacketsEntry
    MAX-ACCESS not-accessible
    STATUS     current
    DESCRIPTION
    "
    Name      : TS Packets
    Menu Path : /TS Mux/ASI Status
    Units     : 
    Precision : 0
    Low Range : 0
    High Range: -1
    Details   : Count of TS packets on the interface.

     NOTE: Precision/Units/Ranges represent the state of the
           parameter during the MIB generation, and does not
           neccessary reflect the current state of the parameter
    "
::= { enc1Params 808 }

enc1P808tspacketsEntry OBJECT-TYPE
    SYNTAX Enc1P808tspacketsEntry
    MAX-ACCESS not-accessible
    STATUS     current
    DESCRIPTION
    "Table Entry for TS Packets"
    INDEX { slotId }
::= { enc1P808tspacketsTable 1 }

Enc1P808tspacketsEntry ::= SEQUENCE {
    enc1P808tspacketsValue    INTEGER
}

enc1P808tspacketsValue OBJECT-TYPE
    SYNTAX     INTEGER
    MAX-ACCESS read-only
    STATUS     current
    DESCRIPTION
    "Count of TS packets on the interface."
::= { enc1P808tspacketsEntry 1 }

enc1P809videoTSPacketsTable OBJECT-TYPE
    SYNTAX SEQUENCE OF Enc1P809videoTSPacketsEntry
    MAX-ACCESS not-accessible
    STATUS     current
    DESCRIPTION
    "
    Name      : Video TS Packets
    Menu Path : /TS Mux/ASI Status
    Units     : 
    Precision : 0
    Low Range : 0
    High Range: -1
    Details   : Count of video and PCR TS packets on the interface.

     NOTE: Precision/Units/Ranges represent the state of the
           parameter during the MIB generation, and does not
           neccessary reflect the current state of the parameter
    "
::= { enc1Params 809 }

enc1P809videoTSPacketsEntry OBJECT-TYPE
    SYNTAX Enc1P809videoTSPacketsEntry
    MAX-ACCESS not-accessible
    STATUS     current
    DESCRIPTION
    "Table Entry for Video TS Packets"
    INDEX { slotId }
::= { enc1P809videoTSPacketsTable 1 }

Enc1P809videoTSPacketsEntry ::= SEQUENCE {
    enc1P809videoTSPacketsValue    INTEGER
}

enc1P809videoTSPacketsValue OBJECT-TYPE
    SYNTAX     INTEGER
    MAX-ACCESS read-only
    STATUS     current
    DESCRIPTION
    "Count of video and PCR TS packets on the interface."
::= { enc1P809videoTSPacketsEntry 1 }

enc1P810audioTSPacketsTable OBJECT-TYPE
    SYNTAX SEQUENCE OF Enc1P810audioTSPacketsEntry
    MAX-ACCESS not-accessible
    STATUS     current
    DESCRIPTION
    "
    Name      : Audio TS Packets
    Menu Path : /TS Mux/ASI Status
    Units     : 
    Precision : 0
    Low Range : 0
    High Range: -1
    Details   : Count of audio TS packets on the interface.

     NOTE: Precision/Units/Ranges represent the state of the
           parameter during the MIB generation, and does not
           neccessary reflect the current state of the parameter
    "
::= { enc1Params 810 }

enc1P810audioTSPacketsEntry OBJECT-TYPE
    SYNTAX Enc1P810audioTSPacketsEntry
    MAX-ACCESS not-accessible
    STATUS     current
    DESCRIPTION
    "Table Entry for Audio TS Packets"
    INDEX { slotId }
::= { enc1P810audioTSPacketsTable 1 }

Enc1P810audioTSPacketsEntry ::= SEQUENCE {
    enc1P810audioTSPacketsValue    INTEGER
}

enc1P810audioTSPacketsValue OBJECT-TYPE
    SYNTAX     INTEGER
    MAX-ACCESS read-only
    STATUS     current
    DESCRIPTION
    "Count of audio TS packets on the interface."
::= { enc1P810audioTSPacketsEntry 1 }

enc1P811videoFIFOOverflowTable OBJECT-TYPE
    SYNTAX SEQUENCE OF Enc1P811videoFIFOOverflowEntry
    MAX-ACCESS not-accessible
    STATUS     current
    DESCRIPTION
    "
    Name      : Video FIFO Overflow
    Menu Path : /TS Mux/ASI Status
    Units     : 
    Precision : 0
    Low Range : 0
    High Range: -1
    Details   : Count of video fifo overflows.

     NOTE: Precision/Units/Ranges represent the state of the
           parameter during the MIB generation, and does not
           neccessary reflect the current state of the parameter
    "
::= { enc1Params 811 }

enc1P811videoFIFOOverflowEntry OBJECT-TYPE
    SYNTAX Enc1P811videoFIFOOverflowEntry
    MAX-ACCESS not-accessible
    STATUS     current
    DESCRIPTION
    "Table Entry for Video FIFO Overflow"
    INDEX { slotId }
::= { enc1P811videoFIFOOverflowTable 1 }

Enc1P811videoFIFOOverflowEntry ::= SEQUENCE {
    enc1P811videoFIFOOverflowValue    INTEGER
}

enc1P811videoFIFOOverflowValue OBJECT-TYPE
    SYNTAX     INTEGER
    MAX-ACCESS read-only
    STATUS     current
    DESCRIPTION
    "Count of video fifo overflows."
::= { enc1P811videoFIFOOverflowEntry 1 }

enc1P812audioFIFOOverflowTable OBJECT-TYPE
    SYNTAX SEQUENCE OF Enc1P812audioFIFOOverflowEntry
    MAX-ACCESS not-accessible
    STATUS     current
    DESCRIPTION
    "
    Name      : Audio FIFO Overflow
    Menu Path : /TS Mux/ASI Status
    Units     : 
    Precision : 0
    Low Range : 0
    High Range: -1
    Details   : Count of audio fifo overflows.

     NOTE: Precision/Units/Ranges represent the state of the
           parameter during the MIB generation, and does not
           neccessary reflect the current state of the parameter
    "
::= { enc1Params 812 }

enc1P812audioFIFOOverflowEntry OBJECT-TYPE
    SYNTAX Enc1P812audioFIFOOverflowEntry
    MAX-ACCESS not-accessible
    STATUS     current
    DESCRIPTION
    "Table Entry for Audio FIFO Overflow"
    INDEX { slotId }
::= { enc1P812audioFIFOOverflowTable 1 }

Enc1P812audioFIFOOverflowEntry ::= SEQUENCE {
    enc1P812audioFIFOOverflowValue    INTEGER
}

enc1P812audioFIFOOverflowValue OBJECT-TYPE
    SYNTAX     INTEGER
    MAX-ACCESS read-only
    STATUS     current
    DESCRIPTION
    "Count of audio fifo overflows."
::= { enc1P812audioFIFOOverflowEntry 1 }

enc1P813tspacketsTable OBJECT-TYPE
    SYNTAX SEQUENCE OF Enc1P813tspacketsEntry
    MAX-ACCESS not-accessible
    STATUS     current
    DESCRIPTION
    "
    Name      : TS Packets
    Menu Path : /IP Encapsulation/Main Program IP Status
    Units     : 
    Precision : 0
    Low Range : 0
    High Range: -1
    Details   : Indicates the count of transmitted transport stream packets on this program.

     NOTE: Precision/Units/Ranges represent the state of the
           parameter during the MIB generation, and does not
           neccessary reflect the current state of the parameter
    "
::= { enc1Params 813 }

enc1P813tspacketsEntry OBJECT-TYPE
    SYNTAX Enc1P813tspacketsEntry
    MAX-ACCESS not-accessible
    STATUS     current
    DESCRIPTION
    "Table Entry for TS Packets"
    INDEX { slotId }
::= { enc1P813tspacketsTable 1 }

Enc1P813tspacketsEntry ::= SEQUENCE {
    enc1P813tspacketsValue    INTEGER
}

enc1P813tspacketsValue OBJECT-TYPE
    SYNTAX     INTEGER
    MAX-ACCESS read-only
    STATUS     current
    DESCRIPTION
    "Indicates the count of transmitted transport stream packets on this program."
::= { enc1P813tspacketsEntry 1 }

enc1P814primaryIPFailureTable OBJECT-TYPE
    SYNTAX SEQUENCE OF Enc1P814primaryIPFailureEntry
    MAX-ACCESS not-accessible
    STATUS     current
    DESCRIPTION
    "
    Name      : Primary IP Failure
    Menu Path : /IP Encapsulation/Main Program IP Status
    Details   : Indicates transmission failure on this program.
    "
::= { enc1Params 814 }

enc1P814primaryIPFailureEntry OBJECT-TYPE
    SYNTAX Enc1P814primaryIPFailureEntry
    MAX-ACCESS not-accessible
    STATUS     current
    DESCRIPTION
    "Table Entry for Primary IP Failure"
    INDEX { slotId }
::= { enc1P814primaryIPFailureTable 1 }

Enc1P814primaryIPFailureEntry ::= SEQUENCE {
    enc1P814primaryIPFailureValue    Enc1E6enumObj
}

enc1P814primaryIPFailureValue OBJECT-TYPE
    SYNTAX     Enc1E6enumObj
    MAX-ACCESS read-only
    STATUS     current
    DESCRIPTION
    "Indicates transmission failure on this program."
::= { enc1P814primaryIPFailureEntry 1 }

enc1P815primaryIPPacketsTable OBJECT-TYPE
    SYNTAX SEQUENCE OF Enc1P815primaryIPPacketsEntry
    MAX-ACCESS not-accessible
    STATUS     current
    DESCRIPTION
    "
    Name      : Primary IP Packets
    Menu Path : /IP Encapsulation/Main Program IP Status
    Units     : 
    Precision : 0
    Low Range : 0
    High Range: -1
    Details   : Shows the count of transmitted IP packets on this program.

     NOTE: Precision/Units/Ranges represent the state of the
           parameter during the MIB generation, and does not
           neccessary reflect the current state of the parameter
    "
::= { enc1Params 815 }

enc1P815primaryIPPacketsEntry OBJECT-TYPE
    SYNTAX Enc1P815primaryIPPacketsEntry
    MAX-ACCESS not-accessible
    STATUS     current
    DESCRIPTION
    "Table Entry for Primary IP Packets"
    INDEX { slotId }
::= { enc1P815primaryIPPacketsTable 1 }

Enc1P815primaryIPPacketsEntry ::= SEQUENCE {
    enc1P815primaryIPPacketsValue    INTEGER
}

enc1P815primaryIPPacketsValue OBJECT-TYPE
    SYNTAX     INTEGER
    MAX-ACCESS read-only
    STATUS     current
    DESCRIPTION
    "Shows the count of transmitted IP packets on this program."
::= { enc1P815primaryIPPacketsEntry 1 }

enc1P816primaryIPTXRateTable OBJECT-TYPE
    SYNTAX SEQUENCE OF Enc1P816primaryIPTXRateEntry
    MAX-ACCESS not-accessible
    STATUS     current
    DESCRIPTION
    "
    Name      : Primary IP TX Rate
    Menu Path : /IP Encapsulation/Main Program IP Status
    Units     : Mbits/sec
    Precision : 6
    Low Range : 0
    High Range: 200000000
    Details   : Shows the computed transmitted bitrate for this program. (Units: Mbits/sec)

     NOTE: Precision/Units/Ranges represent the state of the
           parameter during the MIB generation, and does not
           neccessary reflect the current state of the parameter
    "
::= { enc1Params 816 }

enc1P816primaryIPTXRateEntry OBJECT-TYPE
    SYNTAX Enc1P816primaryIPTXRateEntry
    MAX-ACCESS not-accessible
    STATUS     current
    DESCRIPTION
    "Table Entry for Primary IP TX Rate"
    INDEX { slotId }
::= { enc1P816primaryIPTXRateTable 1 }

Enc1P816primaryIPTXRateEntry ::= SEQUENCE {
    enc1P816primaryIPTXRateValue    INTEGER
}

enc1P816primaryIPTXRateValue OBJECT-TYPE
    SYNTAX     INTEGER
    MAX-ACCESS read-only
    STATUS     current
    DESCRIPTION
    "Shows the computed transmitted bitrate for this program. (Units: Mbits/sec)"
::= { enc1P816primaryIPTXRateEntry 1 }

enc1P817secondaryIPFailureTable OBJECT-TYPE
    SYNTAX SEQUENCE OF Enc1P817secondaryIPFailureEntry
    MAX-ACCESS not-accessible
    STATUS     current
    DESCRIPTION
    "
    Name      : Secondary IP Failure
    Menu Path : /IP Encapsulation/Main Program IP Status
    Details   : Indicates transmission failure on this program.
    "
::= { enc1Params 817 }

enc1P817secondaryIPFailureEntry OBJECT-TYPE
    SYNTAX Enc1P817secondaryIPFailureEntry
    MAX-ACCESS not-accessible
    STATUS     current
    DESCRIPTION
    "Table Entry for Secondary IP Failure"
    INDEX { slotId }
::= { enc1P817secondaryIPFailureTable 1 }

Enc1P817secondaryIPFailureEntry ::= SEQUENCE {
    enc1P817secondaryIPFailureValue    Enc1E6enumObj
}

enc1P817secondaryIPFailureValue OBJECT-TYPE
    SYNTAX     Enc1E6enumObj
    MAX-ACCESS read-only
    STATUS     current
    DESCRIPTION
    "Indicates transmission failure on this program."
::= { enc1P817secondaryIPFailureEntry 1 }

enc1P818secondaryIPPacketsTable OBJECT-TYPE
    SYNTAX SEQUENCE OF Enc1P818secondaryIPPacketsEntry
    MAX-ACCESS not-accessible
    STATUS     current
    DESCRIPTION
    "
    Name      : Secondary IP Packets
    Menu Path : /IP Encapsulation/Main Program IP Status
    Units     : 
    Precision : 0
    Low Range : 0
    High Range: -1
    Details   : Shows the count of transmitted IP packets on this program.

     NOTE: Precision/Units/Ranges represent the state of the
           parameter during the MIB generation, and does not
           neccessary reflect the current state of the parameter
    "
::= { enc1Params 818 }

enc1P818secondaryIPPacketsEntry OBJECT-TYPE
    SYNTAX Enc1P818secondaryIPPacketsEntry
    MAX-ACCESS not-accessible
    STATUS     current
    DESCRIPTION
    "Table Entry for Secondary IP Packets"
    INDEX { slotId }
::= { enc1P818secondaryIPPacketsTable 1 }

Enc1P818secondaryIPPacketsEntry ::= SEQUENCE {
    enc1P818secondaryIPPacketsValue    INTEGER
}

enc1P818secondaryIPPacketsValue OBJECT-TYPE
    SYNTAX     INTEGER
    MAX-ACCESS read-only
    STATUS     current
    DESCRIPTION
    "Shows the count of transmitted IP packets on this program."
::= { enc1P818secondaryIPPacketsEntry 1 }

enc1P819secondaryIPTXRateTable OBJECT-TYPE
    SYNTAX SEQUENCE OF Enc1P819secondaryIPTXRateEntry
    MAX-ACCESS not-accessible
    STATUS     current
    DESCRIPTION
    "
    Name      : Secondary IP TX Rate
    Menu Path : /IP Encapsulation/Main Program IP Status
    Units     : Mbits/sec
    Precision : 6
    Low Range : 0
    High Range: 200000000
    Details   : Shows the computed transmitted bitrate for this program. (Units: Mbits/sec)

     NOTE: Precision/Units/Ranges represent the state of the
           parameter during the MIB generation, and does not
           neccessary reflect the current state of the parameter
    "
::= { enc1Params 819 }

enc1P819secondaryIPTXRateEntry OBJECT-TYPE
    SYNTAX Enc1P819secondaryIPTXRateEntry
    MAX-ACCESS not-accessible
    STATUS     current
    DESCRIPTION
    "Table Entry for Secondary IP TX Rate"
    INDEX { slotId }
::= { enc1P819secondaryIPTXRateTable 1 }

Enc1P819secondaryIPTXRateEntry ::= SEQUENCE {
    enc1P819secondaryIPTXRateValue    INTEGER
}

enc1P819secondaryIPTXRateValue OBJECT-TYPE
    SYNTAX     INTEGER
    MAX-ACCESS read-only
    STATUS     current
    DESCRIPTION
    "Shows the computed transmitted bitrate for this program. (Units: Mbits/sec)"
::= { enc1P819secondaryIPTXRateEntry 1 }

enc1P820tspacketsTable OBJECT-TYPE
    SYNTAX SEQUENCE OF Enc1P820tspacketsEntry
    MAX-ACCESS not-accessible
    STATUS     current
    DESCRIPTION
    "
    Name      : TS Packets
    Menu Path : /IP Encapsulation/Pip Program IP Status
    Units     : 
    Precision : 0
    Low Range : 0
    High Range: -1
    Details   : Shows the count of transmitted transport stream packets on this program.

     NOTE: Precision/Units/Ranges represent the state of the
           parameter during the MIB generation, and does not
           neccessary reflect the current state of the parameter
    "
::= { enc1Params 820 }

enc1P820tspacketsEntry OBJECT-TYPE
    SYNTAX Enc1P820tspacketsEntry
    MAX-ACCESS not-accessible
    STATUS     current
    DESCRIPTION
    "Table Entry for TS Packets"
    INDEX { slotId }
::= { enc1P820tspacketsTable 1 }

Enc1P820tspacketsEntry ::= SEQUENCE {
    enc1P820tspacketsValue    INTEGER
}

enc1P820tspacketsValue OBJECT-TYPE
    SYNTAX     INTEGER
    MAX-ACCESS read-only
    STATUS     current
    DESCRIPTION
    "Shows the count of transmitted transport stream packets on this program."
::= { enc1P820tspacketsEntry 1 }

enc1P821primaryIPFailureTable OBJECT-TYPE
    SYNTAX SEQUENCE OF Enc1P821primaryIPFailureEntry
    MAX-ACCESS not-accessible
    STATUS     current
    DESCRIPTION
    "
    Name      : Primary IP Failure
    Menu Path : /IP Encapsulation/Pip Program IP Status
    Details   : Indicates transmission failure on this program.
    "
::= { enc1Params 821 }

enc1P821primaryIPFailureEntry OBJECT-TYPE
    SYNTAX Enc1P821primaryIPFailureEntry
    MAX-ACCESS not-accessible
    STATUS     current
    DESCRIPTION
    "Table Entry for Primary IP Failure"
    INDEX { slotId }
::= { enc1P821primaryIPFailureTable 1 }

Enc1P821primaryIPFailureEntry ::= SEQUENCE {
    enc1P821primaryIPFailureValue    Enc1E6enumObj
}

enc1P821primaryIPFailureValue OBJECT-TYPE
    SYNTAX     Enc1E6enumObj
    MAX-ACCESS read-only
    STATUS     current
    DESCRIPTION
    "Indicates transmission failure on this program."
::= { enc1P821primaryIPFailureEntry 1 }

enc1P822primaryIPPacketsTable OBJECT-TYPE
    SYNTAX SEQUENCE OF Enc1P822primaryIPPacketsEntry
    MAX-ACCESS not-accessible
    STATUS     current
    DESCRIPTION
    "
    Name      : Primary IP Packets
    Menu Path : /IP Encapsulation/Pip Program IP Status
    Units     : 
    Precision : 0
    Low Range : 0
    High Range: -1
    Details   : Shows the count of transmitted IP packets on this program.

     NOTE: Precision/Units/Ranges represent the state of the
           parameter during the MIB generation, and does not
           neccessary reflect the current state of the parameter
    "
::= { enc1Params 822 }

enc1P822primaryIPPacketsEntry OBJECT-TYPE
    SYNTAX Enc1P822primaryIPPacketsEntry
    MAX-ACCESS not-accessible
    STATUS     current
    DESCRIPTION
    "Table Entry for Primary IP Packets"
    INDEX { slotId }
::= { enc1P822primaryIPPacketsTable 1 }

Enc1P822primaryIPPacketsEntry ::= SEQUENCE {
    enc1P822primaryIPPacketsValue    INTEGER
}

enc1P822primaryIPPacketsValue OBJECT-TYPE
    SYNTAX     INTEGER
    MAX-ACCESS read-only
    STATUS     current
    DESCRIPTION
    "Shows the count of transmitted IP packets on this program."
::= { enc1P822primaryIPPacketsEntry 1 }

enc1P823primaryIPTXRateTable OBJECT-TYPE
    SYNTAX SEQUENCE OF Enc1P823primaryIPTXRateEntry
    MAX-ACCESS not-accessible
    STATUS     current
    DESCRIPTION
    "
    Name      : Primary IP TX Rate
    Menu Path : /IP Encapsulation/Pip Program IP Status
    Units     : Mbits/sec
    Precision : 6
    Low Range : 0
    High Range: 100000000
    Details   : Shows the computed transmitted bitrate for this program. (Units: Mbits/sec)

     NOTE: Precision/Units/Ranges represent the state of the
           parameter during the MIB generation, and does not
           neccessary reflect the current state of the parameter
    "
::= { enc1Params 823 }

enc1P823primaryIPTXRateEntry OBJECT-TYPE
    SYNTAX Enc1P823primaryIPTXRateEntry
    MAX-ACCESS not-accessible
    STATUS     current
    DESCRIPTION
    "Table Entry for Primary IP TX Rate"
    INDEX { slotId }
::= { enc1P823primaryIPTXRateTable 1 }

Enc1P823primaryIPTXRateEntry ::= SEQUENCE {
    enc1P823primaryIPTXRateValue    INTEGER
}

enc1P823primaryIPTXRateValue OBJECT-TYPE
    SYNTAX     INTEGER
    MAX-ACCESS read-only
    STATUS     current
    DESCRIPTION
    "Shows the computed transmitted bitrate for this program. (Units: Mbits/sec)"
::= { enc1P823primaryIPTXRateEntry 1 }

enc1P824secondaryIPFailureTable OBJECT-TYPE
    SYNTAX SEQUENCE OF Enc1P824secondaryIPFailureEntry
    MAX-ACCESS not-accessible
    STATUS     current
    DESCRIPTION
    "
    Name      : Secondary IP Failure
    Menu Path : /IP Encapsulation/Pip Program IP Status
    Details   : Indicates transmission failure on this program.
    "
::= { enc1Params 824 }

enc1P824secondaryIPFailureEntry OBJECT-TYPE
    SYNTAX Enc1P824secondaryIPFailureEntry
    MAX-ACCESS not-accessible
    STATUS     current
    DESCRIPTION
    "Table Entry for Secondary IP Failure"
    INDEX { slotId }
::= { enc1P824secondaryIPFailureTable 1 }

Enc1P824secondaryIPFailureEntry ::= SEQUENCE {
    enc1P824secondaryIPFailureValue    Enc1E6enumObj
}

enc1P824secondaryIPFailureValue OBJECT-TYPE
    SYNTAX     Enc1E6enumObj
    MAX-ACCESS read-only
    STATUS     current
    DESCRIPTION
    "Indicates transmission failure on this program."
::= { enc1P824secondaryIPFailureEntry 1 }

enc1P825secondaryIPPacketsTable OBJECT-TYPE
    SYNTAX SEQUENCE OF Enc1P825secondaryIPPacketsEntry
    MAX-ACCESS not-accessible
    STATUS     current
    DESCRIPTION
    "
    Name      : Secondary IP Packets
    Menu Path : /IP Encapsulation/Pip Program IP Status
    Units     : 
    Precision : 0
    Low Range : 0
    High Range: -1
    Details   : Shows the count of transmitted IP packets on this program.

     NOTE: Precision/Units/Ranges represent the state of the
           parameter during the MIB generation, and does not
           neccessary reflect the current state of the parameter
    "
::= { enc1Params 825 }

enc1P825secondaryIPPacketsEntry OBJECT-TYPE
    SYNTAX Enc1P825secondaryIPPacketsEntry
    MAX-ACCESS not-accessible
    STATUS     current
    DESCRIPTION
    "Table Entry for Secondary IP Packets"
    INDEX { slotId }
::= { enc1P825secondaryIPPacketsTable 1 }

Enc1P825secondaryIPPacketsEntry ::= SEQUENCE {
    enc1P825secondaryIPPacketsValue    INTEGER
}

enc1P825secondaryIPPacketsValue OBJECT-TYPE
    SYNTAX     INTEGER
    MAX-ACCESS read-only
    STATUS     current
    DESCRIPTION
    "Shows the count of transmitted IP packets on this program."
::= { enc1P825secondaryIPPacketsEntry 1 }

enc1P826secondaryIPTXRateTable OBJECT-TYPE
    SYNTAX SEQUENCE OF Enc1P826secondaryIPTXRateEntry
    MAX-ACCESS not-accessible
    STATUS     current
    DESCRIPTION
    "
    Name      : Secondary IP TX Rate
    Menu Path : /IP Encapsulation/Pip Program IP Status
    Units     : Mbits/sec
    Precision : 6
    Low Range : 0
    High Range: 100000000
    Details   : Shows the computed transmitted bitrate for this program. (Units: Mbits/sec)

     NOTE: Precision/Units/Ranges represent the state of the
           parameter during the MIB generation, and does not
           neccessary reflect the current state of the parameter
    "
::= { enc1Params 826 }

enc1P826secondaryIPTXRateEntry OBJECT-TYPE
    SYNTAX Enc1P826secondaryIPTXRateEntry
    MAX-ACCESS not-accessible
    STATUS     current
    DESCRIPTION
    "Table Entry for Secondary IP TX Rate"
    INDEX { slotId }
::= { enc1P826secondaryIPTXRateTable 1 }

Enc1P826secondaryIPTXRateEntry ::= SEQUENCE {
    enc1P826secondaryIPTXRateValue    INTEGER
}

enc1P826secondaryIPTXRateValue OBJECT-TYPE
    SYNTAX     INTEGER
    MAX-ACCESS read-only
    STATUS     current
    DESCRIPTION
    "Shows the computed transmitted bitrate for this program. (Units: Mbits/sec)"
::= { enc1P826secondaryIPTXRateEntry 1 }

enc1P834aspectRatioTable OBJECT-TYPE
    SYNTAX SEQUENCE OF Enc1P834aspectRatioEntry
    MAX-ACCESS not-accessible
    STATUS     current
    DESCRIPTION
    "
    Name      : Aspect Ratio
    Menu Path : /Video/Compression/Status
    Details   : Shows current video aspect ratio
    "
::= { enc1Params 834 }

enc1P834aspectRatioEntry OBJECT-TYPE
    SYNTAX Enc1P834aspectRatioEntry
    MAX-ACCESS not-accessible
    STATUS     current
    DESCRIPTION
    "Table Entry for Aspect Ratio"
    INDEX { slotId }
::= { enc1P834aspectRatioTable 1 }

Enc1P834aspectRatioEntry ::= SEQUENCE {
    enc1P834aspectRatioValue    Enc1E53enumObj
}

enc1P834aspectRatioValue OBJECT-TYPE
    SYNTAX     Enc1E53enumObj
    MAX-ACCESS read-only
    STATUS     current
    DESCRIPTION
    "Shows current video aspect ratio"
::= { enc1P834aspectRatioEntry 1 }

enc1P835vipresentTable OBJECT-TYPE
    SYNTAX SEQUENCE OF Enc1P835vipresentEntry
    MAX-ACCESS not-accessible
    STATUS     current
    DESCRIPTION
    "
    Name      : VI Present
    Menu Path : /Data/VBI Status
    Details   : Shows whether or not Video Index Information is present
    "
::= { enc1Params 835 }

enc1P835vipresentEntry OBJECT-TYPE
    SYNTAX Enc1P835vipresentEntry
    MAX-ACCESS not-accessible
    STATUS     current
    DESCRIPTION
    "Table Entry for VI Present"
    INDEX { slotId }
::= { enc1P835vipresentTable 1 }

Enc1P835vipresentEntry ::= SEQUENCE {
    enc1P835vipresentValue    Enc1E9enumObj
}

enc1P835vipresentValue OBJECT-TYPE
    SYNTAX     Enc1E9enumObj
    MAX-ACCESS read-only
    STATUS     current
    DESCRIPTION
    "Shows whether or not Video Index Information is present"
::= { enc1P835vipresentEntry 1 }

enc1P836crcerrorTable OBJECT-TYPE
    SYNTAX SEQUENCE OF Enc1P836crcerrorEntry
    MAX-ACCESS not-accessible
    STATUS     current
    DESCRIPTION
    "
    Name      : CRC Error
    Menu Path : /Video/Input/Status
    Units     : 
    Precision : 0
    Low Range : 0
    High Range: -1
    Details   : Indicates the CRC error count (HD)

     NOTE: Precision/Units/Ranges represent the state of the
           parameter during the MIB generation, and does not
           neccessary reflect the current state of the parameter
    "
::= { enc1Params 836 }

enc1P836crcerrorEntry OBJECT-TYPE
    SYNTAX Enc1P836crcerrorEntry
    MAX-ACCESS not-accessible
    STATUS     current
    DESCRIPTION
    "Table Entry for CRC Error"
    INDEX { slotId }
::= { enc1P836crcerrorTable 1 }

Enc1P836crcerrorEntry ::= SEQUENCE {
    enc1P836crcerrorValue    INTEGER
}

enc1P836crcerrorValue OBJECT-TYPE
    SYNTAX     INTEGER
    MAX-ACCESS read-only
    STATUS     current
    DESCRIPTION
    "Indicates the CRC error count (HD)"
::= { enc1P836crcerrorEntry 1 }

enc1P837nameTable OBJECT-TYPE
    SYNTAX SEQUENCE OF Enc1P837nameEntry
    MAX-ACCESS not-accessible
    STATUS     current
    DESCRIPTION
    "
    Name      : Name
    Menu Path : /Misc
    Details   : User defined name for module.
    "
::= { enc1Params 837 }

enc1P837nameEntry OBJECT-TYPE
    SYNTAX Enc1P837nameEntry
    MAX-ACCESS not-accessible
    STATUS     current
    DESCRIPTION
    "Table Entry for Name"
    INDEX { slotId }
::= { enc1P837nameTable 1 }

Enc1P837nameEntry ::= SEQUENCE {
    enc1P837nameValue    DisplayString
}

enc1P837nameValue OBJECT-TYPE
    SYNTAX     DisplayString
    MAX-ACCESS read-write
    STATUS     current
    DESCRIPTION
    "User defined name for module."
::= { enc1P837nameEntry 1 }

enc1P838timetoLiveTable OBJECT-TYPE
    SYNTAX SEQUENCE OF Enc1P838timetoLiveEntry
    MAX-ACCESS not-accessible
    STATUS     current
    DESCRIPTION
    "
    Name      : Time to Live
    Menu Path : /Control/IP LANs
    Units     : 
    Precision : 0
    Low Range : 1
    High Range: 255
    Details   : Time to Live for IP packets.

     NOTE: Precision/Units/Ranges represent the state of the
           parameter during the MIB generation, and does not
           neccessary reflect the current state of the parameter
    "
::= { enc1Params 838 }

enc1P838timetoLiveEntry OBJECT-TYPE
    SYNTAX Enc1P838timetoLiveEntry
    MAX-ACCESS not-accessible
    STATUS     current
    DESCRIPTION
    "Table Entry for Time to Live"
    INDEX { slotId }
::= { enc1P838timetoLiveTable 1 }

Enc1P838timetoLiveEntry ::= SEQUENCE {
    enc1P838timetoLiveValue    INTEGER
}

enc1P838timetoLiveValue OBJECT-TYPE
    SYNTAX     INTEGER
    MAX-ACCESS read-write
    STATUS     current
    DESCRIPTION
    "Time to Live for IP packets."
::= { enc1P838timetoLiveEntry 1 }

enc1P839macaddressTable OBJECT-TYPE
    SYNTAX SEQUENCE OF Enc1P839macaddressEntry
    MAX-ACCESS not-accessible
    STATUS     current
    DESCRIPTION
    "
    Name      : MAC Address
    Menu Path : /Control/IP LANs/Primary Data IP LAN
    Details   : MAC address for primary data ethernet.
    "
::= { enc1Params 839 }

enc1P839macaddressEntry OBJECT-TYPE
    SYNTAX Enc1P839macaddressEntry
    MAX-ACCESS not-accessible
    STATUS     current
    DESCRIPTION
    "Table Entry for MAC Address"
    INDEX { slotId }
::= { enc1P839macaddressTable 1 }

Enc1P839macaddressEntry ::= SEQUENCE {
    enc1P839macaddressValue    DisplayString
}

enc1P839macaddressValue OBJECT-TYPE
    SYNTAX     DisplayString
    MAX-ACCESS read-only
    STATUS     current
    DESCRIPTION
    "MAC address for primary data ethernet."
::= { enc1P839macaddressEntry 1 }

enc1P840macaddressTable OBJECT-TYPE
    SYNTAX SEQUENCE OF Enc1P840macaddressEntry
    MAX-ACCESS not-accessible
    STATUS     current
    DESCRIPTION
    "
    Name      : MAC Address
    Menu Path : /Control/IP LANs/Secondary Data IP LAN
    Details   : MAC address for secondary data ethernet.
    "
::= { enc1Params 840 }

enc1P840macaddressEntry OBJECT-TYPE
    SYNTAX Enc1P840macaddressEntry
    MAX-ACCESS not-accessible
    STATUS     current
    DESCRIPTION
    "Table Entry for MAC Address"
    INDEX { slotId }
::= { enc1P840macaddressTable 1 }

Enc1P840macaddressEntry ::= SEQUENCE {
    enc1P840macaddressValue    DisplayString
}

enc1P840macaddressValue OBJECT-TYPE
    SYNTAX     DisplayString
    MAX-ACCESS read-only
    STATUS     current
    DESCRIPTION
    "MAC address for secondary data ethernet."
::= { enc1P840macaddressEntry 1 }

enc1P841edherrorTable OBJECT-TYPE
    SYNTAX SEQUENCE OF Enc1P841edherrorEntry
    MAX-ACCESS not-accessible
    STATUS     current
    DESCRIPTION
    "
    Name      : EDH Error
    Menu Path : /Video/Input/Status
    Units     : 
    Precision : 0
    Low Range : 0
    High Range: -1
    Details   : Indicates the EDH error count.

     NOTE: Precision/Units/Ranges represent the state of the
           parameter during the MIB generation, and does not
           neccessary reflect the current state of the parameter
    "
::= { enc1Params 841 }

enc1P841edherrorEntry OBJECT-TYPE
    SYNTAX Enc1P841edherrorEntry
    MAX-ACCESS not-accessible
    STATUS     current
    DESCRIPTION
    "Table Entry for EDH Error"
    INDEX { slotId }
::= { enc1P841edherrorTable 1 }

Enc1P841edherrorEntry ::= SEQUENCE {
    enc1P841edherrorValue    INTEGER
}

enc1P841edherrorValue OBJECT-TYPE
    SYNTAX     INTEGER
    MAX-ACCESS read-only
    STATUS     current
    DESCRIPTION
    "Indicates the EDH error count."
::= { enc1P841edherrorEntry 1 }

enc1P842languageTable OBJECT-TYPE
    SYNTAX SEQUENCE OF Enc1P842languageEntry
    MAX-ACCESS not-accessible
    STATUS     current
    DESCRIPTION
    "
    Name      : Language
    Menu Path : /TS Mux/SI Parameters
    Details   : Specifies default language code for names and captions. The value is used in descriptors in SI tables.
    "
::= { enc1Params 842 }

enc1P842languageEntry OBJECT-TYPE
    SYNTAX Enc1P842languageEntry
    MAX-ACCESS not-accessible
    STATUS     current
    DESCRIPTION
    "Table Entry for Language"
    INDEX { slotId }
::= { enc1P842languageTable 1 }

Enc1P842languageEntry ::= SEQUENCE {
    enc1P842languageValue    DisplayString
}

enc1P842languageValue OBJECT-TYPE
    SYNTAX     DisplayString
    MAX-ACCESS read-write
    STATUS     current
    DESCRIPTION
    "Specifies default language code for names and captions. The value is used in descriptors in SI tables."
::= { enc1P842languageEntry 1 }

enc1P859ipsecEncryptionTable OBJECT-TYPE
    SYNTAX SEQUENCE OF Enc1P859ipsecEncryptionEntry
    MAX-ACCESS not-accessible
    STATUS     current
    DESCRIPTION
    "
    Name      : IPSec Encryption
    Menu Path : /IP Encapsulation/ATSC MH IP
    Details   : Specifies IPSec encryption mode. Only applies when in MH mode.
    "
::= { enc1Params 859 }

enc1P859ipsecEncryptionEntry OBJECT-TYPE
    SYNTAX Enc1P859ipsecEncryptionEntry
    MAX-ACCESS not-accessible
    STATUS     current
    DESCRIPTION
    "Table Entry for IPSec Encryption"
    INDEX { slotId }
::= { enc1P859ipsecEncryptionTable 1 }

Enc1P859ipsecEncryptionEntry ::= SEQUENCE {
    enc1P859ipsecEncryptionValue    Enc1E140enumObj
}

enc1P859ipsecEncryptionValue OBJECT-TYPE
    SYNTAX     Enc1E140enumObj
    MAX-ACCESS read-write
    STATUS     current
    DESCRIPTION
    "Specifies IPSec encryption mode. Only applies when in MH mode."
::= { enc1P859ipsecEncryptionEntry 1 }

enc1P860fixedKeyTable OBJECT-TYPE
    SYNTAX SEQUENCE OF Enc1P860fixedKeyEntry
    MAX-ACCESS not-accessible
    STATUS     current
    DESCRIPTION
    "
    Name      : Fixed Key
    Menu Path : /IP Encapsulation/ATSC MH IP
    Details   : Specifies 128 bit fixed key for encryption (32 hex characters).
    "
::= { enc1Params 860 }

enc1P860fixedKeyEntry OBJECT-TYPE
    SYNTAX Enc1P860fixedKeyEntry
    MAX-ACCESS not-accessible
    STATUS     current
    DESCRIPTION
    "Table Entry for Fixed Key"
    INDEX { slotId }
::= { enc1P860fixedKeyTable 1 }

Enc1P860fixedKeyEntry ::= SEQUENCE {
    enc1P860fixedKeyValue    DisplayString
}

enc1P860fixedKeyValue OBJECT-TYPE
    SYNTAX     DisplayString
    MAX-ACCESS read-write
    STATUS     current
    DESCRIPTION
    "Specifies 128 bit fixed key for encryption (32 hex characters)."
::= { enc1P860fixedKeyEntry 1 }

enc1P861fixedSPITable OBJECT-TYPE
    SYNTAX SEQUENCE OF Enc1P861fixedSPIEntry
    MAX-ACCESS not-accessible
    STATUS     current
    DESCRIPTION
    "
    Name      : Fixed SPI
    Menu Path : /IP Encapsulation/ATSC MH IP
    Details   : Specifies 32 bit SPI (8 hex characters).
    "
::= { enc1Params 861 }

enc1P861fixedSPIEntry OBJECT-TYPE
    SYNTAX Enc1P861fixedSPIEntry
    MAX-ACCESS not-accessible
    STATUS     current
    DESCRIPTION
    "Table Entry for Fixed SPI"
    INDEX { slotId }
::= { enc1P861fixedSPITable 1 }

Enc1P861fixedSPIEntry ::= SEQUENCE {
    enc1P861fixedSPIValue    DisplayString
}

enc1P861fixedSPIValue OBJECT-TYPE
    SYNTAX     DisplayString
    MAX-ACCESS read-write
    STATUS     current
    DESCRIPTION
    "Specifies 32 bit SPI (8 hex characters)."
::= { enc1P861fixedSPIEntry 1 }

enc1P862primaryECMServerIPAddressTable OBJECT-TYPE
    SYNTAX SEQUENCE OF Enc1P862primaryECMServerIPAddressEntry
    MAX-ACCESS not-accessible
    STATUS     current
    DESCRIPTION
    "
    Name      : Primary ECM Server IP Address
    Menu Path : /IP Encapsulation/ATSC MH IP
    Details   : Specifies the IP address used to communicate with the primary Simulcrypt conditional access ECM generator.
    "
::= { enc1Params 862 }

enc1P862primaryECMServerIPAddressEntry OBJECT-TYPE
    SYNTAX Enc1P862primaryECMServerIPAddressEntry
    MAX-ACCESS not-accessible
    STATUS     current
    DESCRIPTION
    "Table Entry for Primary ECM Server IP Address"
    INDEX { slotId }
::= { enc1P862primaryECMServerIPAddressTable 1 }

Enc1P862primaryECMServerIPAddressEntry ::= SEQUENCE {
    enc1P862primaryECMServerIPAddressValue    DisplayString
}

enc1P862primaryECMServerIPAddressValue OBJECT-TYPE
    SYNTAX     DisplayString
    MAX-ACCESS read-write
    STATUS     current
    DESCRIPTION
    "Specifies the IP address used to communicate with the primary Simulcrypt conditional access ECM generator."
::= { enc1P862primaryECMServerIPAddressEntry 1 }

enc1P863primaryECMServerPortTable OBJECT-TYPE
    SYNTAX SEQUENCE OF Enc1P863primaryECMServerPortEntry
    MAX-ACCESS not-accessible
    STATUS     current
    DESCRIPTION
    "
    Name      : Primary ECM Server Port
    Menu Path : /IP Encapsulation/ATSC MH IP
    Units     : 
    Precision : 0
    Low Range : 0
    High Range: 65535
    Details   : Specifies the port used to communicate with the primary conditional access ECM generator.

     NOTE: Precision/Units/Ranges represent the state of the
           parameter during the MIB generation, and does not
           neccessary reflect the current state of the parameter
    "
::= { enc1Params 863 }

enc1P863primaryECMServerPortEntry OBJECT-TYPE
    SYNTAX Enc1P863primaryECMServerPortEntry
    MAX-ACCESS not-accessible
    STATUS     current
    DESCRIPTION
    "Table Entry for Primary ECM Server Port"
    INDEX { slotId }
::= { enc1P863primaryECMServerPortTable 1 }

Enc1P863primaryECMServerPortEntry ::= SEQUENCE {
    enc1P863primaryECMServerPortValue    INTEGER
}

enc1P863primaryECMServerPortValue OBJECT-TYPE
    SYNTAX     INTEGER
    MAX-ACCESS read-write
    STATUS     current
    DESCRIPTION
    "Specifies the port used to communicate with the primary conditional access ECM generator."
::= { enc1P863primaryECMServerPortEntry 1 }

enc1P864secondaryECMServerIPAddressTable OBJECT-TYPE
    SYNTAX SEQUENCE OF Enc1P864secondaryECMServerIPAddressEntry
    MAX-ACCESS not-accessible
    STATUS     current
    DESCRIPTION
    "
    Name      : Secondary ECM Server IP Address
    Menu Path : /IP Encapsulation/ATSC MH IP
    Details   : Specifies the IP address used to communicate with the secondary Simulcrypt conditional access ECM generator.
    "
::= { enc1Params 864 }

enc1P864secondaryECMServerIPAddressEntry OBJECT-TYPE
    SYNTAX Enc1P864secondaryECMServerIPAddressEntry
    MAX-ACCESS not-accessible
    STATUS     current
    DESCRIPTION
    "Table Entry for Secondary ECM Server IP Address"
    INDEX { slotId }
::= { enc1P864secondaryECMServerIPAddressTable 1 }

Enc1P864secondaryECMServerIPAddressEntry ::= SEQUENCE {
    enc1P864secondaryECMServerIPAddressValue    DisplayString
}

enc1P864secondaryECMServerIPAddressValue OBJECT-TYPE
    SYNTAX     DisplayString
    MAX-ACCESS read-write
    STATUS     current
    DESCRIPTION
    "Specifies the IP address used to communicate with the secondary Simulcrypt conditional access ECM generator."
::= { enc1P864secondaryECMServerIPAddressEntry 1 }

enc1P865secondaryECMServerPortTable OBJECT-TYPE
    SYNTAX SEQUENCE OF Enc1P865secondaryECMServerPortEntry
    MAX-ACCESS not-accessible
    STATUS     current
    DESCRIPTION
    "
    Name      : Secondary ECM Server Port
    Menu Path : /IP Encapsulation/ATSC MH IP
    Units     : 
    Precision : 0
    Low Range : 0
    High Range: 65535
    Details   : Specifies the port used to communicate with the secondary conditional access ECM generator.

     NOTE: Precision/Units/Ranges represent the state of the
           parameter during the MIB generation, and does not
           neccessary reflect the current state of the parameter
    "
::= { enc1Params 865 }

enc1P865secondaryECMServerPortEntry OBJECT-TYPE
    SYNTAX Enc1P865secondaryECMServerPortEntry
    MAX-ACCESS not-accessible
    STATUS     current
    DESCRIPTION
    "Table Entry for Secondary ECM Server Port"
    INDEX { slotId }
::= { enc1P865secondaryECMServerPortTable 1 }

Enc1P865secondaryECMServerPortEntry ::= SEQUENCE {
    enc1P865secondaryECMServerPortValue    INTEGER
}

enc1P865secondaryECMServerPortValue OBJECT-TYPE
    SYNTAX     INTEGER
    MAX-ACCESS read-write
    STATUS     current
    DESCRIPTION
    "Specifies the port used to communicate with the secondary conditional access ECM generator."
::= { enc1P865secondaryECMServerPortEntry 1 }

enc1P866vendorTable OBJECT-TYPE
    SYNTAX SEQUENCE OF Enc1P866vendorEntry
    MAX-ACCESS not-accessible
    STATUS     current
    DESCRIPTION
    "
    Name      : Vendor
    Menu Path : /IP Encapsulation/ATSC MH IP
    Details   : Specifies the vendor of the external conditional access system.
    "
::= { enc1Params 866 }

enc1P866vendorEntry OBJECT-TYPE
    SYNTAX Enc1P866vendorEntry
    MAX-ACCESS not-accessible
    STATUS     current
    DESCRIPTION
    "Table Entry for Vendor"
    INDEX { slotId }
::= { enc1P866vendorTable 1 }

Enc1P866vendorEntry ::= SEQUENCE {
    enc1P866vendorValue    Enc1E139enumObj
}

enc1P866vendorValue OBJECT-TYPE
    SYNTAX     Enc1E139enumObj
    MAX-ACCESS read-write
    STATUS     current
    DESCRIPTION
    "Specifies the vendor of the external conditional access system."
::= { enc1P866vendorEntry 1 }

enc1P867casystemIDTable OBJECT-TYPE
    SYNTAX SEQUENCE OF Enc1P867casystemIDEntry
    MAX-ACCESS not-accessible
    STATUS     current
    DESCRIPTION
    "
    Name      : CA System ID
    Menu Path : /IP Encapsulation/ATSC MH IP
    Units     : 
    Precision : 0
    Low Range : 0
    High Range: 65535
    Details   : Specifies the CA System ID assigned by the CA vendor.

     NOTE: Precision/Units/Ranges represent the state of the
           parameter during the MIB generation, and does not
           neccessary reflect the current state of the parameter
    "
::= { enc1Params 867 }

enc1P867casystemIDEntry OBJECT-TYPE
    SYNTAX Enc1P867casystemIDEntry
    MAX-ACCESS not-accessible
    STATUS     current
    DESCRIPTION
    "Table Entry for CA System ID"
    INDEX { slotId }
::= { enc1P867casystemIDTable 1 }

Enc1P867casystemIDEntry ::= SEQUENCE {
    enc1P867casystemIDValue    INTEGER
}

enc1P867casystemIDValue OBJECT-TYPE
    SYNTAX     INTEGER
    MAX-ACCESS read-write
    STATUS     current
    DESCRIPTION
    "Specifies the CA System ID assigned by the CA vendor."
::= { enc1P867casystemIDEntry 1 }

enc1P868subCasIDTable OBJECT-TYPE
    SYNTAX SEQUENCE OF Enc1P868subCasIDEntry
    MAX-ACCESS not-accessible
    STATUS     current
    DESCRIPTION
    "
    Name      : Sub Cas ID
    Menu Path : /IP Encapsulation/ATSC MH IP
    Units     : 
    Precision : 0
    Low Range : 0
    High Range: 65535
    Details   : Specifies the sub CA system ID for this conditional access ECM generator.

     NOTE: Precision/Units/Ranges represent the state of the
           parameter during the MIB generation, and does not
           neccessary reflect the current state of the parameter
    "
::= { enc1Params 868 }

enc1P868subCasIDEntry OBJECT-TYPE
    SYNTAX Enc1P868subCasIDEntry
    MAX-ACCESS not-accessible
    STATUS     current
    DESCRIPTION
    "Table Entry for Sub Cas ID"
    INDEX { slotId }
::= { enc1P868subCasIDTable 1 }

Enc1P868subCasIDEntry ::= SEQUENCE {
    enc1P868subCasIDValue    INTEGER
}

enc1P868subCasIDValue OBJECT-TYPE
    SYNTAX     INTEGER
    MAX-ACCESS read-write
    STATUS     current
    DESCRIPTION
    "Specifies the sub CA system ID for this conditional access ECM generator."
::= { enc1P868subCasIDEntry 1 }

enc1P869cryptoPeriodTable OBJECT-TYPE
    SYNTAX SEQUENCE OF Enc1P869cryptoPeriodEntry
    MAX-ACCESS not-accessible
    STATUS     current
    DESCRIPTION
    "
    Name      : Crypto Period
    Menu Path : /IP Encapsulation/ATSC MH IP
    Units     : 
    Precision : 0
    Low Range : 0
    High Range: 65535
    Details   : Specifies the crypto period for the MH service.

     NOTE: Precision/Units/Ranges represent the state of the
           parameter during the MIB generation, and does not
           neccessary reflect the current state of the parameter
    "
::= { enc1Params 869 }

enc1P869cryptoPeriodEntry OBJECT-TYPE
    SYNTAX Enc1P869cryptoPeriodEntry
    MAX-ACCESS not-accessible
    STATUS     current
    DESCRIPTION
    "Table Entry for Crypto Period"
    INDEX { slotId }
::= { enc1P869cryptoPeriodTable 1 }

Enc1P869cryptoPeriodEntry ::= SEQUENCE {
    enc1P869cryptoPeriodValue    INTEGER
}

enc1P869cryptoPeriodValue OBJECT-TYPE
    SYNTAX     INTEGER
    MAX-ACCESS read-write
    STATUS     current
    DESCRIPTION
    "Specifies the crypto period for the MH service."
::= { enc1P869cryptoPeriodEntry 1 }

enc1P870accessCriteriaValueTable OBJECT-TYPE
    SYNTAX SEQUENCE OF Enc1P870accessCriteriaValueEntry
    MAX-ACCESS not-accessible
    STATUS     current
    DESCRIPTION
    "
    Name      : Access Criteria Value
    Menu Path : /IP Encapsulation/ATSC MH IP
    Details   : Specifies the value string of this Access Criteria. Format is hex coded bytes. Ex. 010103010203 Maximum length is 80 characters supporting AC length of 40 bytes.
    "
::= { enc1Params 870 }

enc1P870accessCriteriaValueEntry OBJECT-TYPE
    SYNTAX Enc1P870accessCriteriaValueEntry
    MAX-ACCESS not-accessible
    STATUS     current
    DESCRIPTION
    "Table Entry for Access Criteria Value"
    INDEX { slotId }
::= { enc1P870accessCriteriaValueTable 1 }

Enc1P870accessCriteriaValueEntry ::= SEQUENCE {
    enc1P870accessCriteriaValueValue    DisplayString
}

enc1P870accessCriteriaValueValue OBJECT-TYPE
    SYNTAX     DisplayString
    MAX-ACCESS read-write
    STATUS     current
    DESCRIPTION
    "Specifies the value string of this Access Criteria. Format is hex coded bytes. Ex. 010103010203 Maximum length is 80 characters supporting AC length of 40 bytes."
::= { enc1P870accessCriteriaValueEntry 1 }

enc1P871sdpfileTable OBJECT-TYPE
    SYNTAX SEQUENCE OF Enc1P871sdpfileEntry
    MAX-ACCESS not-accessible
    STATUS     current
    DESCRIPTION
    "
    Name      : SDP file
    Menu Path : /IP Encapsulation/ATSC MH IP
    Details   : URL for SDP file.
    "
::= { enc1Params 871 }

enc1P871sdpfileEntry OBJECT-TYPE
    SYNTAX Enc1P871sdpfileEntry
    MAX-ACCESS not-accessible
    STATUS     current
    DESCRIPTION
    "Table Entry for SDP file"
    INDEX { slotId }
::= { enc1P871sdpfileTable 1 }

Enc1P871sdpfileEntry ::= SEQUENCE {
    enc1P871sdpfileValue    DisplayString
}

enc1P871sdpfileValue OBJECT-TYPE
    SYNTAX     DisplayString
    MAX-ACCESS read-only
    STATUS     current
    DESCRIPTION
    "URL for SDP file."
::= { enc1P871sdpfileEntry 1 }

enc1P872primaryECMServerStateTable OBJECT-TYPE
    SYNTAX SEQUENCE OF Enc1P872primaryECMServerStateEntry
    MAX-ACCESS not-accessible
    STATUS     current
    DESCRIPTION
    "
    Name      : Primary ECM Server State
    Menu Path : /IP Encapsulation/ATSC MH IP
    Details   : Specifies whether or not a connection exists to the primary ECM server.
    "
::= { enc1Params 872 }

enc1P872primaryECMServerStateEntry OBJECT-TYPE
    SYNTAX Enc1P872primaryECMServerStateEntry
    MAX-ACCESS not-accessible
    STATUS     current
    DESCRIPTION
    "Table Entry for Primary ECM Server State"
    INDEX { slotId }
::= { enc1P872primaryECMServerStateTable 1 }

Enc1P872primaryECMServerStateEntry ::= SEQUENCE {
    enc1P872primaryECMServerStateValue    DisplayString
}

enc1P872primaryECMServerStateValue OBJECT-TYPE
    SYNTAX     DisplayString
    MAX-ACCESS read-only
    STATUS     current
    DESCRIPTION
    "Specifies whether or not a connection exists to the primary ECM server."
::= { enc1P872primaryECMServerStateEntry 1 }

enc1P873secondaryECMServerStateTable OBJECT-TYPE
    SYNTAX SEQUENCE OF Enc1P873secondaryECMServerStateEntry
    MAX-ACCESS not-accessible
    STATUS     current
    DESCRIPTION
    "
    Name      : Secondary ECM Server State
    Menu Path : /IP Encapsulation/ATSC MH IP
    Details   : Specifies whether or not a connection exists to the secondary ECM server.
    "
::= { enc1Params 873 }

enc1P873secondaryECMServerStateEntry OBJECT-TYPE
    SYNTAX Enc1P873secondaryECMServerStateEntry
    MAX-ACCESS not-accessible
    STATUS     current
    DESCRIPTION
    "Table Entry for Secondary ECM Server State"
    INDEX { slotId }
::= { enc1P873secondaryECMServerStateTable 1 }

Enc1P873secondaryECMServerStateEntry ::= SEQUENCE {
    enc1P873secondaryECMServerStateValue    DisplayString
}

enc1P873secondaryECMServerStateValue OBJECT-TYPE
    SYNTAX     DisplayString
    MAX-ACCESS read-only
    STATUS     current
    DESCRIPTION
    "Specifies whether or not a connection exists to the secondary ECM server."
::= { enc1P873secondaryECMServerStateEntry 1 }

enc1P874ecmcountTable OBJECT-TYPE
    SYNTAX SEQUENCE OF Enc1P874ecmcountEntry
    MAX-ACCESS not-accessible
    STATUS     current
    DESCRIPTION
    "
    Name      : ECM Count
    Menu Path : /IP Encapsulation/ATSC MH IP
    Units     : 
    Precision : 0
    Low Range : 0
    High Range: -1
    Details   : Number of ECM messages exchanged with the server.

     NOTE: Precision/Units/Ranges represent the state of the
           parameter during the MIB generation, and does not
           neccessary reflect the current state of the parameter
    "
::= { enc1Params 874 }

enc1P874ecmcountEntry OBJECT-TYPE
    SYNTAX Enc1P874ecmcountEntry
    MAX-ACCESS not-accessible
    STATUS     current
    DESCRIPTION
    "Table Entry for ECM Count"
    INDEX { slotId }
::= { enc1P874ecmcountTable 1 }

Enc1P874ecmcountEntry ::= SEQUENCE {
    enc1P874ecmcountValue    INTEGER
}

enc1P874ecmcountValue OBJECT-TYPE
    SYNTAX     INTEGER
    MAX-ACCESS read-only
    STATUS     current
    DESCRIPTION
    "Number of ECM messages exchanged with the server."
::= { enc1P874ecmcountEntry 1 }

enc1P875systemDelayTable OBJECT-TYPE
    SYNTAX SEQUENCE OF Enc1P875systemDelayEntry
    MAX-ACCESS not-accessible
    STATUS     current
    DESCRIPTION
    "
    Name      : System Delay
    Menu Path : /Video/Compression
    Units     : msec
    Precision : 0
    Low Range : 0
    High Range: 3200
    Details   : Specifies end to end delay. (Units: msec)

     NOTE: Precision/Units/Ranges represent the state of the
           parameter during the MIB generation, and does not
           neccessary reflect the current state of the parameter
    "
::= { enc1Params 875 }

enc1P875systemDelayEntry OBJECT-TYPE
    SYNTAX Enc1P875systemDelayEntry
    MAX-ACCESS not-accessible
    STATUS     current
    DESCRIPTION
    "Table Entry for System Delay"
    INDEX { slotId }
::= { enc1P875systemDelayTable 1 }

Enc1P875systemDelayEntry ::= SEQUENCE {
    enc1P875systemDelayValue    INTEGER
}

enc1P875systemDelayValue OBJECT-TYPE
    SYNTAX     INTEGER
    MAX-ACCESS read-write
    STATUS     current
    DESCRIPTION
    "Specifies end to end delay. (Units: msec)"
::= { enc1P875systemDelayEntry 1 }

enc1P876sceneChangeDetectionTable OBJECT-TYPE
    SYNTAX SEQUENCE OF Enc1P876sceneChangeDetectionEntry
    MAX-ACCESS not-accessible
    STATUS     current
    DESCRIPTION
    "
    Name      : Scene Change Detection
    Menu Path : /Video/Compression/Advanced Parameters
    Details   : Enable/Disable scene change detection.
    "
::= { enc1Params 876 }

enc1P876sceneChangeDetectionEntry OBJECT-TYPE
    SYNTAX Enc1P876sceneChangeDetectionEntry
    MAX-ACCESS not-accessible
    STATUS     current
    DESCRIPTION
    "Table Entry for Scene Change Detection"
    INDEX { slotId }
::= { enc1P876sceneChangeDetectionTable 1 }

Enc1P876sceneChangeDetectionEntry ::= SEQUENCE {
    enc1P876sceneChangeDetectionValue    Enc1E0enumObj
}

enc1P876sceneChangeDetectionValue OBJECT-TYPE
    SYNTAX     Enc1E0enumObj
    MAX-ACCESS read-write
    STATUS     current
    DESCRIPTION
    "Enable/Disable scene change detection."
::= { enc1P876sceneChangeDetectionEntry 1 }

enc1P877fadeDetectionTable OBJECT-TYPE
    SYNTAX SEQUENCE OF Enc1P877fadeDetectionEntry
    MAX-ACCESS not-accessible
    STATUS     current
    DESCRIPTION
    "
    Name      : Fade Detection
    Menu Path : /Video/Compression/Advanced Parameters
    Details   : Enable/Disable fade detection.
    "
::= { enc1Params 877 }

enc1P877fadeDetectionEntry OBJECT-TYPE
    SYNTAX Enc1P877fadeDetectionEntry
    MAX-ACCESS not-accessible
    STATUS     current
    DESCRIPTION
    "Table Entry for Fade Detection"
    INDEX { slotId }
::= { enc1P877fadeDetectionTable 1 }

Enc1P877fadeDetectionEntry ::= SEQUENCE {
    enc1P877fadeDetectionValue    Enc1E0enumObj
}

enc1P877fadeDetectionValue OBJECT-TYPE
    SYNTAX     Enc1E0enumObj
    MAX-ACCESS read-write
    STATUS     current
    DESCRIPTION
    "Enable/Disable fade detection."
::= { enc1P877fadeDetectionEntry 1 }

enc1P878pre-DeblockingStrengthTable OBJECT-TYPE
    SYNTAX SEQUENCE OF Enc1P878pre-DeblockingStrengthEntry
    MAX-ACCESS not-accessible
    STATUS     current
    DESCRIPTION
    "
    Name      : Pre-Deblocking Strength
    Menu Path : /Video/Compression/Advanced Parameters
    Units     : 
    Precision : 0
    Low Range : 0
    High Range: 3
    Details   : Deblocking filter strength.

     NOTE: Precision/Units/Ranges represent the state of the
           parameter during the MIB generation, and does not
           neccessary reflect the current state of the parameter
    "
::= { enc1Params 878 }

enc1P878pre-DeblockingStrengthEntry OBJECT-TYPE
    SYNTAX Enc1P878pre-DeblockingStrengthEntry
    MAX-ACCESS not-accessible
    STATUS     current
    DESCRIPTION
    "Table Entry for Pre-Deblocking Strength"
    INDEX { slotId }
::= { enc1P878pre-DeblockingStrengthTable 1 }

Enc1P878pre-DeblockingStrengthEntry ::= SEQUENCE {
    enc1P878pre-DeblockingStrengthValue    INTEGER
}

enc1P878pre-DeblockingStrengthValue OBJECT-TYPE
    SYNTAX     INTEGER
    MAX-ACCESS read-write
    STATUS     current
    DESCRIPTION
    "Deblocking filter strength."
::= { enc1P878pre-DeblockingStrengthEntry 1 }

enc1P879mctfstrengthTable OBJECT-TYPE
    SYNTAX SEQUENCE OF Enc1P879mctfstrengthEntry
    MAX-ACCESS not-accessible
    STATUS     current
    DESCRIPTION
    "
    Name      : MCTF Strength
    Menu Path : /Video/Compression/Advanced Parameters
    Units     : 
    Precision : 0
    Low Range : 0
    High Range: 7
    Details   : Motion-compensated temporal filter strength.

     NOTE: Precision/Units/Ranges represent the state of the
           parameter during the MIB generation, and does not
           neccessary reflect the current state of the parameter
    "
::= { enc1Params 879 }

enc1P879mctfstrengthEntry OBJECT-TYPE
    SYNTAX Enc1P879mctfstrengthEntry
    MAX-ACCESS not-accessible
    STATUS     current
    DESCRIPTION
    "Table Entry for MCTF Strength"
    INDEX { slotId }
::= { enc1P879mctfstrengthTable 1 }

Enc1P879mctfstrengthEntry ::= SEQUENCE {
    enc1P879mctfstrengthValue    INTEGER
}

enc1P879mctfstrengthValue OBJECT-TYPE
    SYNTAX     INTEGER
    MAX-ACCESS read-write
    STATUS     current
    DESCRIPTION
    "Motion-compensated temporal filter strength."
::= { enc1P879mctfstrengthEntry 1 }

enc1P880skinToneDetectionTable OBJECT-TYPE
    SYNTAX SEQUENCE OF Enc1P880skinToneDetectionEntry
    MAX-ACCESS not-accessible
    STATUS     current
    DESCRIPTION
    "
    Name      : Skin Tone Detection
    Menu Path : /Video/Compression/Advanced Parameters
    Details   : Enable/Disable skin tone detection.
    "
::= { enc1Params 880 }

enc1P880skinToneDetectionEntry OBJECT-TYPE
    SYNTAX Enc1P880skinToneDetectionEntry
    MAX-ACCESS not-accessible
    STATUS     current
    DESCRIPTION
    "Table Entry for Skin Tone Detection"
    INDEX { slotId }
::= { enc1P880skinToneDetectionTable 1 }

Enc1P880skinToneDetectionEntry ::= SEQUENCE {
    enc1P880skinToneDetectionValue    Enc1E0enumObj
}

enc1P880skinToneDetectionValue OBJECT-TYPE
    SYNTAX     Enc1E0enumObj
    MAX-ACCESS read-write
    STATUS     current
    DESCRIPTION
    "Enable/Disable skin tone detection."
::= { enc1P880skinToneDetectionEntry 1 }

enc1P881skinToneDetectionStrengthTable OBJECT-TYPE
    SYNTAX SEQUENCE OF Enc1P881skinToneDetectionStrengthEntry
    MAX-ACCESS not-accessible
    STATUS     current
    DESCRIPTION
    "
    Name      : Skin Tone Detection Strength
    Menu Path : /Video/Compression/Advanced Parameters
    Units     : 
    Precision : 0
    Low Range : 0
    High Range: 7
    Details   : Skin tone detection filter strength.

     NOTE: Precision/Units/Ranges represent the state of the
           parameter during the MIB generation, and does not
           neccessary reflect the current state of the parameter
    "
::= { enc1Params 881 }

enc1P881skinToneDetectionStrengthEntry OBJECT-TYPE
    SYNTAX Enc1P881skinToneDetectionStrengthEntry
    MAX-ACCESS not-accessible
    STATUS     current
    DESCRIPTION
    "Table Entry for Skin Tone Detection Strength"
    INDEX { slotId }
::= { enc1P881skinToneDetectionStrengthTable 1 }

Enc1P881skinToneDetectionStrengthEntry ::= SEQUENCE {
    enc1P881skinToneDetectionStrengthValue    INTEGER
}

enc1P881skinToneDetectionStrengthValue OBJECT-TYPE
    SYNTAX     INTEGER
    MAX-ACCESS read-write
    STATUS     current
    DESCRIPTION
    "Skin tone detection filter strength."
::= { enc1P881skinToneDetectionStrengthEntry 1 }

enc1P882skinToneDetectionDeltaQPMaxTable OBJECT-TYPE
    SYNTAX SEQUENCE OF Enc1P882skinToneDetectionDeltaQPMaxEntry
    MAX-ACCESS not-accessible
    STATUS     current
    DESCRIPTION
    "
    Name      : Skin Tone Detection Delta QP Max
    Menu Path : /Video/Compression/Advanced Parameters
    Units     : 
    Precision : 0
    Low Range : 0
    High Range: 6
    Details   : Maximum decrease in QP for skin tone macroblocks.

     NOTE: Precision/Units/Ranges represent the state of the
           parameter during the MIB generation, and does not
           neccessary reflect the current state of the parameter
    "
::= { enc1Params 882 }

enc1P882skinToneDetectionDeltaQPMaxEntry OBJECT-TYPE
    SYNTAX Enc1P882skinToneDetectionDeltaQPMaxEntry
    MAX-ACCESS not-accessible
    STATUS     current
    DESCRIPTION
    "Table Entry for Skin Tone Detection Delta QP Max"
    INDEX { slotId }
::= { enc1P882skinToneDetectionDeltaQPMaxTable 1 }

Enc1P882skinToneDetectionDeltaQPMaxEntry ::= SEQUENCE {
    enc1P882skinToneDetectionDeltaQPMaxValue    INTEGER
}

enc1P882skinToneDetectionDeltaQPMaxValue OBJECT-TYPE
    SYNTAX     INTEGER
    MAX-ACCESS read-write
    STATUS     current
    DESCRIPTION
    "Maximum decrease in QP for skin tone macroblocks."
::= { enc1P882skinToneDetectionDeltaQPMaxEntry 1 }

enc1P884dynamicGopTable OBJECT-TYPE
    SYNTAX SEQUENCE OF Enc1P884dynamicGopEntry
    MAX-ACCESS not-accessible
    STATUS     current
    DESCRIPTION
    "
    Name      : Dynamic Gop
    Menu Path : /Video/Compression/Advanced Parameters
    Details   : Enable/Disable dynamic GOP.
    "
::= { enc1Params 884 }

enc1P884dynamicGopEntry OBJECT-TYPE
    SYNTAX Enc1P884dynamicGopEntry
    MAX-ACCESS not-accessible
    STATUS     current
    DESCRIPTION
    "Table Entry for Dynamic Gop"
    INDEX { slotId }
::= { enc1P884dynamicGopTable 1 }

Enc1P884dynamicGopEntry ::= SEQUENCE {
    enc1P884dynamicGopValue    Enc1E0enumObj
}

enc1P884dynamicGopValue OBJECT-TYPE
    SYNTAX     Enc1E0enumObj
    MAX-ACCESS read-write
    STATUS     current
    DESCRIPTION
    "Enable/Disable dynamic GOP."
::= { enc1P884dynamicGopEntry 1 }

enc1P885dynamicGopMinMTable OBJECT-TYPE
    SYNTAX SEQUENCE OF Enc1P885dynamicGopMinMEntry
    MAX-ACCESS not-accessible
    STATUS     current
    DESCRIPTION
    "
    Name      : Dynamic Gop Min M
    Menu Path : /Video/Compression/Advanced Parameters
    Details   : Min Gop size used when dynamic GOP is enabled.
    "
::= { enc1Params 885 }

enc1P885dynamicGopMinMEntry OBJECT-TYPE
    SYNTAX Enc1P885dynamicGopMinMEntry
    MAX-ACCESS not-accessible
    STATUS     current
    DESCRIPTION
    "Table Entry for Dynamic Gop Min M"
    INDEX { slotId }
::= { enc1P885dynamicGopMinMTable 1 }

Enc1P885dynamicGopMinMEntry ::= SEQUENCE {
    enc1P885dynamicGopMinMValue    Enc1E62enumObj
}

enc1P885dynamicGopMinMValue OBJECT-TYPE
    SYNTAX     Enc1E62enumObj
    MAX-ACCESS read-write
    STATUS     current
    DESCRIPTION
    "Min Gop size used when dynamic GOP is enabled."
::= { enc1P885dynamicGopMinMEntry 1 }

enc1P886dynamicGopMaxMTable OBJECT-TYPE
    SYNTAX SEQUENCE OF Enc1P886dynamicGopMaxMEntry
    MAX-ACCESS not-accessible
    STATUS     current
    DESCRIPTION
    "
    Name      : Dynamic Gop Max M
    Menu Path : /Video/Compression/Advanced Parameters
    Details   : Max GOP structure when dynamic GOP is enabled
    "
::= { enc1Params 886 }

enc1P886dynamicGopMaxMEntry OBJECT-TYPE
    SYNTAX Enc1P886dynamicGopMaxMEntry
    MAX-ACCESS not-accessible
    STATUS     current
    DESCRIPTION
    "Table Entry for Dynamic Gop Max M"
    INDEX { slotId }
::= { enc1P886dynamicGopMaxMTable 1 }

Enc1P886dynamicGopMaxMEntry ::= SEQUENCE {
    enc1P886dynamicGopMaxMValue    Enc1E62enumObj
}

enc1P886dynamicGopMaxMValue OBJECT-TYPE
    SYNTAX     Enc1E62enumObj
    MAX-ACCESS read-write
    STATUS     current
    DESCRIPTION
    "Max GOP structure when dynamic GOP is enabled"
::= { enc1P886dynamicGopMaxMEntry 1 }

enc1P887gopStructureTable OBJECT-TYPE
    SYNTAX SEQUENCE OF Enc1P887gopStructureEntry
    MAX-ACCESS not-accessible
    STATUS     current
    DESCRIPTION
    "
    Name      : Gop Structure
    Menu Path : /Video/Compression/Advanced Parameters
    Details   : Specifies GOP structure to be used for encoding.
    "
::= { enc1Params 887 }

enc1P887gopStructureEntry OBJECT-TYPE
    SYNTAX Enc1P887gopStructureEntry
    MAX-ACCESS not-accessible
    STATUS     current
    DESCRIPTION
    "Table Entry for Gop Structure"
    INDEX { slotId }
::= { enc1P887gopStructureTable 1 }

Enc1P887gopStructureEntry ::= SEQUENCE {
    enc1P887gopStructureValue    Enc1E62enumObj
}

enc1P887gopStructureValue OBJECT-TYPE
    SYNTAX     Enc1E62enumObj
    MAX-ACCESS read-write
    STATUS     current
    DESCRIPTION
    "Specifies GOP structure to be used for encoding."
::= { enc1P887gopStructureEntry 1 }

enc1P888gopSizeTable OBJECT-TYPE
    SYNTAX SEQUENCE OF Enc1P888gopSizeEntry
    MAX-ACCESS not-accessible
    STATUS     current
    DESCRIPTION
    "
    Name      : Gop Size
    Menu Path : /Video/Compression/Advanced Parameters
    Units     : 
    Precision : 0
    Low Range : 0
    High Range: 120
    Details   : Specifies GOP size to be used while encoding.

     NOTE: Precision/Units/Ranges represent the state of the
           parameter during the MIB generation, and does not
           neccessary reflect the current state of the parameter
    "
::= { enc1Params 888 }

enc1P888gopSizeEntry OBJECT-TYPE
    SYNTAX Enc1P888gopSizeEntry
    MAX-ACCESS not-accessible
    STATUS     current
    DESCRIPTION
    "Table Entry for Gop Size"
    INDEX { slotId }
::= { enc1P888gopSizeTable 1 }

Enc1P888gopSizeEntry ::= SEQUENCE {
    enc1P888gopSizeValue    INTEGER
}

enc1P888gopSizeValue OBJECT-TYPE
    SYNTAX     INTEGER
    MAX-ACCESS read-write
    STATUS     current
    DESCRIPTION
    "Specifies GOP size to be used while encoding."
::= { enc1P888gopSizeEntry 1 }

enc1P889closedGopTable OBJECT-TYPE
    SYNTAX SEQUENCE OF Enc1P889closedGopEntry
    MAX-ACCESS not-accessible
    STATUS     current
    DESCRIPTION
    "
    Name      : Closed Gop
    Menu Path : /Video/Compression/Advanced Parameters
    Details   : Enable/Disable closed GOP.
    "
::= { enc1Params 889 }

enc1P889closedGopEntry OBJECT-TYPE
    SYNTAX Enc1P889closedGopEntry
    MAX-ACCESS not-accessible
    STATUS     current
    DESCRIPTION
    "Table Entry for Closed Gop"
    INDEX { slotId }
::= { enc1P889closedGopTable 1 }

Enc1P889closedGopEntry ::= SEQUENCE {
    enc1P889closedGopValue    Enc1E1enumObj
}

enc1P889closedGopValue OBJECT-TYPE
    SYNTAX     Enc1E1enumObj
    MAX-ACCESS read-write
    STATUS     current
    DESCRIPTION
    "Enable/Disable closed GOP."
::= { enc1P889closedGopEntry 1 }

enc1P890me1ZeroBiasTable OBJECT-TYPE
    SYNTAX SEQUENCE OF Enc1P890me1ZeroBiasEntry
    MAX-ACCESS not-accessible
    STATUS     current
    DESCRIPTION
    "
    Name      : ME1 Zero Bias
    Menu Path : /Video/Compression/Advanced Parameters
    Units     : 
    Precision : 0
    Low Range : 0
    High Range: 1024
    Details   : Bias for zero motion vectors in ME1.

     NOTE: Precision/Units/Ranges represent the state of the
           parameter during the MIB generation, and does not
           neccessary reflect the current state of the parameter
    "
::= { enc1Params 890 }

enc1P890me1ZeroBiasEntry OBJECT-TYPE
    SYNTAX Enc1P890me1ZeroBiasEntry
    MAX-ACCESS not-accessible
    STATUS     current
    DESCRIPTION
    "Table Entry for ME1 Zero Bias"
    INDEX { slotId }
::= { enc1P890me1ZeroBiasTable 1 }

Enc1P890me1ZeroBiasEntry ::= SEQUENCE {
    enc1P890me1ZeroBiasValue    INTEGER
}

enc1P890me1ZeroBiasValue OBJECT-TYPE
    SYNTAX     INTEGER
    MAX-ACCESS read-write
    STATUS     current
    DESCRIPTION
    "Bias for zero motion vectors in ME1."
::= { enc1P890me1ZeroBiasEntry 1 }

enc1P891me2ZeroBiasTable OBJECT-TYPE
    SYNTAX SEQUENCE OF Enc1P891me2ZeroBiasEntry
    MAX-ACCESS not-accessible
    STATUS     current
    DESCRIPTION
    "
    Name      : ME2 Zero Bias
    Menu Path : /Video/Compression/Advanced Parameters
    Units     : 
    Precision : 0
    Low Range : 0
    High Range: 1024
    Details   : Bias for zero motion vectors in ME2.

     NOTE: Precision/Units/Ranges represent the state of the
           parameter during the MIB generation, and does not
           neccessary reflect the current state of the parameter
    "
::= { enc1Params 891 }

enc1P891me2ZeroBiasEntry OBJECT-TYPE
    SYNTAX Enc1P891me2ZeroBiasEntry
    MAX-ACCESS not-accessible
    STATUS     current
    DESCRIPTION
    "Table Entry for ME2 Zero Bias"
    INDEX { slotId }
::= { enc1P891me2ZeroBiasTable 1 }

Enc1P891me2ZeroBiasEntry ::= SEQUENCE {
    enc1P891me2ZeroBiasValue    INTEGER
}

enc1P891me2ZeroBiasValue OBJECT-TYPE
    SYNTAX     INTEGER
    MAX-ACCESS read-write
    STATUS     current
    DESCRIPTION
    "Bias for zero motion vectors in ME2."
::= { enc1P891me2ZeroBiasEntry 1 }

enc1P892adaptiveQuantizationTable OBJECT-TYPE
    SYNTAX SEQUENCE OF Enc1P892adaptiveQuantizationEntry
    MAX-ACCESS not-accessible
    STATUS     current
    DESCRIPTION
    "
    Name      : Adaptive Quantization
    Menu Path : /Video/Compression/Advanced Parameters
    Details   : Enable/Disable adaptive quantization.
    "
::= { enc1Params 892 }

enc1P892adaptiveQuantizationEntry OBJECT-TYPE
    SYNTAX Enc1P892adaptiveQuantizationEntry
    MAX-ACCESS not-accessible
    STATUS     current
    DESCRIPTION
    "Table Entry for Adaptive Quantization"
    INDEX { slotId }
::= { enc1P892adaptiveQuantizationTable 1 }

Enc1P892adaptiveQuantizationEntry ::= SEQUENCE {
    enc1P892adaptiveQuantizationValue    Enc1E0enumObj
}

enc1P892adaptiveQuantizationValue OBJECT-TYPE
    SYNTAX     Enc1E0enumObj
    MAX-ACCESS read-write
    STATUS     current
    DESCRIPTION
    "Enable/Disable adaptive quantization."
::= { enc1P892adaptiveQuantizationEntry 1 }

enc1P893h264QPIOffsetTable OBJECT-TYPE
    SYNTAX SEQUENCE OF Enc1P893h264QPIOffsetEntry
    MAX-ACCESS not-accessible
    STATUS     current
    DESCRIPTION
    "
    Name      : H264 QPIOffset
    Menu Path : /Video/Compression/Advanced Parameters
    Units     : 
    Precision : 0
    Low Range : -8
    High Range: 8
    Details   : QP offset to apply to I frames for H264 encoding.

     NOTE: Precision/Units/Ranges represent the state of the
           parameter during the MIB generation, and does not
           neccessary reflect the current state of the parameter
    "
::= { enc1Params 893 }

enc1P893h264QPIOffsetEntry OBJECT-TYPE
    SYNTAX Enc1P893h264QPIOffsetEntry
    MAX-ACCESS not-accessible
    STATUS     current
    DESCRIPTION
    "Table Entry for H264 QPIOffset"
    INDEX { slotId }
::= { enc1P893h264QPIOffsetTable 1 }

Enc1P893h264QPIOffsetEntry ::= SEQUENCE {
    enc1P893h264QPIOffsetValue    INTEGER
}

enc1P893h264QPIOffsetValue OBJECT-TYPE
    SYNTAX     INTEGER
    MAX-ACCESS read-write
    STATUS     current
    DESCRIPTION
    "QP offset to apply to I frames for H264 encoding."
::= { enc1P893h264QPIOffsetEntry 1 }

enc1P894h264QPBOffsetTable OBJECT-TYPE
    SYNTAX SEQUENCE OF Enc1P894h264QPBOffsetEntry
    MAX-ACCESS not-accessible
    STATUS     current
    DESCRIPTION
    "
    Name      : H264 QPBOffset
    Menu Path : /Video/Compression/Advanced Parameters
    Units     : 
    Precision : 0
    Low Range : -8
    High Range: 8
    Details   : QP offset to apply to B frames for H264 encoding.

     NOTE: Precision/Units/Ranges represent the state of the
           parameter during the MIB generation, and does not
           neccessary reflect the current state of the parameter
    "
::= { enc1Params 894 }

enc1P894h264QPBOffsetEntry OBJECT-TYPE
    SYNTAX Enc1P894h264QPBOffsetEntry
    MAX-ACCESS not-accessible
    STATUS     current
    DESCRIPTION
    "Table Entry for H264 QPBOffset"
    INDEX { slotId }
::= { enc1P894h264QPBOffsetTable 1 }

Enc1P894h264QPBOffsetEntry ::= SEQUENCE {
    enc1P894h264QPBOffsetValue    INTEGER
}

enc1P894h264QPBOffsetValue OBJECT-TYPE
    SYNTAX     INTEGER
    MAX-ACCESS read-write
    STATUS     current
    DESCRIPTION
    "QP offset to apply to B frames for H264 encoding."
::= { enc1P894h264QPBOffsetEntry 1 }

enc1P895h264QPChromaOffsetTable OBJECT-TYPE
    SYNTAX SEQUENCE OF Enc1P895h264QPChromaOffsetEntry
    MAX-ACCESS not-accessible
    STATUS     current
    DESCRIPTION
    "
    Name      : H264 QPChromaOffset
    Menu Path : /Video/Compression/Advanced Parameters
    Units     : 
    Precision : 0
    Low Range : -12
    High Range: 12
    Details   : QP offset for chrominance relative to luminance for H264 encoding.

     NOTE: Precision/Units/Ranges represent the state of the
           parameter during the MIB generation, and does not
           neccessary reflect the current state of the parameter
    "
::= { enc1Params 895 }

enc1P895h264QPChromaOffsetEntry OBJECT-TYPE
    SYNTAX Enc1P895h264QPChromaOffsetEntry
    MAX-ACCESS not-accessible
    STATUS     current
    DESCRIPTION
    "Table Entry for H264 QPChromaOffset"
    INDEX { slotId }
::= { enc1P895h264QPChromaOffsetTable 1 }

Enc1P895h264QPChromaOffsetEntry ::= SEQUENCE {
    enc1P895h264QPChromaOffsetValue    INTEGER
}

enc1P895h264QPChromaOffsetValue OBJECT-TYPE
    SYNTAX     INTEGER
    MAX-ACCESS read-write
    STATUS     current
    DESCRIPTION
    "QP offset for chrominance relative to luminance for H264 encoding."
::= { enc1P895h264QPChromaOffsetEntry 1 }

enc1P896referenceBFramesTable OBJECT-TYPE
    SYNTAX SEQUENCE OF Enc1P896referenceBFramesEntry
    MAX-ACCESS not-accessible
    STATUS     current
    DESCRIPTION
    "
    Name      : Reference B Frames
    Menu Path : /Video/Compression/Advanced Parameters
    Details   : Enable/Disable reference B frames.
    "
::= { enc1Params 896 }

enc1P896referenceBFramesEntry OBJECT-TYPE
    SYNTAX Enc1P896referenceBFramesEntry
    MAX-ACCESS not-accessible
    STATUS     current
    DESCRIPTION
    "Table Entry for Reference B Frames"
    INDEX { slotId }
::= { enc1P896referenceBFramesTable 1 }

Enc1P896referenceBFramesEntry ::= SEQUENCE {
    enc1P896referenceBFramesValue    Enc1E0enumObj
}

enc1P896referenceBFramesValue OBJECT-TYPE
    SYNTAX     Enc1E0enumObj
    MAX-ACCESS read-write
    STATUS     current
    DESCRIPTION
    "Enable/Disable reference B frames."
::= { enc1P896referenceBFramesEntry 1 }

enc1P897x88TransformTable OBJECT-TYPE
    SYNTAX SEQUENCE OF Enc1P897x88TransformEntry
    MAX-ACCESS not-accessible
    STATUS     current
    DESCRIPTION
    "
    Name      : 8x8 Transform
    Menu Path : /Video/Compression/Advanced Parameters
    Details   : Enable/Disable 8x8 transform.
    "
::= { enc1Params 897 }

enc1P897x88TransformEntry OBJECT-TYPE
    SYNTAX Enc1P897x88TransformEntry
    MAX-ACCESS not-accessible
    STATUS     current
    DESCRIPTION
    "Table Entry for 8x8 Transform"
    INDEX { slotId }
::= { enc1P897x88TransformTable 1 }

Enc1P897x88TransformEntry ::= SEQUENCE {
    enc1P897x88TransformValue    Enc1E0enumObj
}

enc1P897x88TransformValue OBJECT-TYPE
    SYNTAX     Enc1E0enumObj
    MAX-ACCESS read-write
    STATUS     current
    DESCRIPTION
    "Enable/Disable 8x8 transform."
::= { enc1P897x88TransformEntry 1 }

enc1P898cabacTable OBJECT-TYPE
    SYNTAX SEQUENCE OF Enc1P898cabacEntry
    MAX-ACCESS not-accessible
    STATUS     current
    DESCRIPTION
    "
    Name      : CABAC
    Menu Path : /Video/Compression/Advanced Parameters
    Details   : Enable/Disable CABAC.
    "
::= { enc1Params 898 }

enc1P898cabacEntry OBJECT-TYPE
    SYNTAX Enc1P898cabacEntry
    MAX-ACCESS not-accessible
    STATUS     current
    DESCRIPTION
    "Table Entry for CABAC"
    INDEX { slotId }
::= { enc1P898cabacTable 1 }

Enc1P898cabacEntry ::= SEQUENCE {
    enc1P898cabacValue    Enc1E0enumObj
}

enc1P898cabacValue OBJECT-TYPE
    SYNTAX     Enc1E0enumObj
    MAX-ACCESS read-write
    STATUS     current
    DESCRIPTION
    "Enable/Disable CABAC."
::= { enc1P898cabacEntry 1 }

enc1P899loopFilterTable OBJECT-TYPE
    SYNTAX SEQUENCE OF Enc1P899loopFilterEntry
    MAX-ACCESS not-accessible
    STATUS     current
    DESCRIPTION
    "
    Name      : Loop Filter
    Menu Path : /Video/Compression/Advanced Parameters
    Details   : Enable/Disable H264 loop filter.
    "
::= { enc1Params 899 }

enc1P899loopFilterEntry OBJECT-TYPE
    SYNTAX Enc1P899loopFilterEntry
    MAX-ACCESS not-accessible
    STATUS     current
    DESCRIPTION
    "Table Entry for Loop Filter"
    INDEX { slotId }
::= { enc1P899loopFilterTable 1 }

Enc1P899loopFilterEntry ::= SEQUENCE {
    enc1P899loopFilterValue    Enc1E1enumObj
}

enc1P899loopFilterValue OBJECT-TYPE
    SYNTAX     Enc1E1enumObj
    MAX-ACCESS read-write
    STATUS     current
    DESCRIPTION
    "Enable/Disable H264 loop filter."
::= { enc1P899loopFilterEntry 1 }

enc1P900loopFilterAlphaTable OBJECT-TYPE
    SYNTAX SEQUENCE OF Enc1P900loopFilterAlphaEntry
    MAX-ACCESS not-accessible
    STATUS     current
    DESCRIPTION
    "
    Name      : Loop Filter Alpha
    Menu Path : /Video/Compression/Advanced Parameters
    Units     : 
    Precision : 0
    Low Range : -6
    High Range: 6
    Details   : Specifies H264 loop filter alpha.

     NOTE: Precision/Units/Ranges represent the state of the
           parameter during the MIB generation, and does not
           neccessary reflect the current state of the parameter
    "
::= { enc1Params 900 }

enc1P900loopFilterAlphaEntry OBJECT-TYPE
    SYNTAX Enc1P900loopFilterAlphaEntry
    MAX-ACCESS not-accessible
    STATUS     current
    DESCRIPTION
    "Table Entry for Loop Filter Alpha"
    INDEX { slotId }
::= { enc1P900loopFilterAlphaTable 1 }

Enc1P900loopFilterAlphaEntry ::= SEQUENCE {
    enc1P900loopFilterAlphaValue    INTEGER
}

enc1P900loopFilterAlphaValue OBJECT-TYPE
    SYNTAX     INTEGER
    MAX-ACCESS read-write
    STATUS     current
    DESCRIPTION
    "Specifies H264 loop filter alpha."
::= { enc1P900loopFilterAlphaEntry 1 }

enc1P901loopFilterBetaTable OBJECT-TYPE
    SYNTAX SEQUENCE OF Enc1P901loopFilterBetaEntry
    MAX-ACCESS not-accessible
    STATUS     current
    DESCRIPTION
    "
    Name      : Loop Filter Beta
    Menu Path : /Video/Compression/Advanced Parameters
    Units     : 
    Precision : 0
    Low Range : -6
    High Range: 6
    Details   : Specifies H264 loop filter beta.

     NOTE: Precision/Units/Ranges represent the state of the
           parameter during the MIB generation, and does not
           neccessary reflect the current state of the parameter
    "
::= { enc1Params 901 }

enc1P901loopFilterBetaEntry OBJECT-TYPE
    SYNTAX Enc1P901loopFilterBetaEntry
    MAX-ACCESS not-accessible
    STATUS     current
    DESCRIPTION
    "Table Entry for Loop Filter Beta"
    INDEX { slotId }
::= { enc1P901loopFilterBetaTable 1 }

Enc1P901loopFilterBetaEntry ::= SEQUENCE {
    enc1P901loopFilterBetaValue    INTEGER
}

enc1P901loopFilterBetaValue OBJECT-TYPE
    SYNTAX     INTEGER
    MAX-ACCESS read-write
    STATUS     current
    DESCRIPTION
    "Specifies H264 loop filter beta."
::= { enc1P901loopFilterBetaEntry 1 }

enc1P902mpeg2QPIOffsetTable OBJECT-TYPE
    SYNTAX SEQUENCE OF Enc1P902mpeg2QPIOffsetEntry
    MAX-ACCESS not-accessible
    STATUS     current
    DESCRIPTION
    "
    Name      : MPEG2 QPIOffset
    Menu Path : /Video/Compression/Advanced Parameters
    Units     : 
    Precision : 0
    Low Range : 0
    High Range: -1
    Details   : QP offset to apply to I frames for MPEG-2 encoding.

     NOTE: Precision/Units/Ranges represent the state of the
           parameter during the MIB generation, and does not
           neccessary reflect the current state of the parameter
    "
::= { enc1Params 902 }

enc1P902mpeg2QPIOffsetEntry OBJECT-TYPE
    SYNTAX Enc1P902mpeg2QPIOffsetEntry
    MAX-ACCESS not-accessible
    STATUS     current
    DESCRIPTION
    "Table Entry for MPEG2 QPIOffset"
    INDEX { slotId }
::= { enc1P902mpeg2QPIOffsetTable 1 }

Enc1P902mpeg2QPIOffsetEntry ::= SEQUENCE {
    enc1P902mpeg2QPIOffsetValue    INTEGER
}

enc1P902mpeg2QPIOffsetValue OBJECT-TYPE
    SYNTAX     INTEGER
    MAX-ACCESS read-write
    STATUS     current
    DESCRIPTION
    "QP offset to apply to I frames for MPEG-2 encoding."
::= { enc1P902mpeg2QPIOffsetEntry 1 }

enc1P903mpeg2QPBOffsetTable OBJECT-TYPE
    SYNTAX SEQUENCE OF Enc1P903mpeg2QPBOffsetEntry
    MAX-ACCESS not-accessible
    STATUS     current
    DESCRIPTION
    "
    Name      : MPEG2 QPBOffset
    Menu Path : /Video/Compression/Advanced Parameters
    Units     : 
    Precision : 0
    Low Range : 0
    High Range: -1
    Details   : QP offset to apply to B frames for MPEG-2 encoding

     NOTE: Precision/Units/Ranges represent the state of the
           parameter during the MIB generation, and does not
           neccessary reflect the current state of the parameter
    "
::= { enc1Params 903 }

enc1P903mpeg2QPBOffsetEntry OBJECT-TYPE
    SYNTAX Enc1P903mpeg2QPBOffsetEntry
    MAX-ACCESS not-accessible
    STATUS     current
    DESCRIPTION
    "Table Entry for MPEG2 QPBOffset"
    INDEX { slotId }
::= { enc1P903mpeg2QPBOffsetTable 1 }

Enc1P903mpeg2QPBOffsetEntry ::= SEQUENCE {
    enc1P903mpeg2QPBOffsetValue    INTEGER
}

enc1P903mpeg2QPBOffsetValue OBJECT-TYPE
    SYNTAX     INTEGER
    MAX-ACCESS read-write
    STATUS     current
    DESCRIPTION
    "QP offset to apply to B frames for MPEG-2 encoding"
::= { enc1P903mpeg2QPBOffsetEntry 1 }

enc1P904intraDCPrecisionTable OBJECT-TYPE
    SYNTAX SEQUENCE OF Enc1P904intraDCPrecisionEntry
    MAX-ACCESS not-accessible
    STATUS     current
    DESCRIPTION
    "
    Name      : Intra DC Precision
    Menu Path : /Video/Compression/Advanced Parameters
    Details   : Specifies MPEG2 Intra DC Precision value.
    "
::= { enc1Params 904 }

enc1P904intraDCPrecisionEntry OBJECT-TYPE
    SYNTAX Enc1P904intraDCPrecisionEntry
    MAX-ACCESS not-accessible
    STATUS     current
    DESCRIPTION
    "Table Entry for Intra DC Precision"
    INDEX { slotId }
::= { enc1P904intraDCPrecisionTable 1 }

Enc1P904intraDCPrecisionEntry ::= SEQUENCE {
    enc1P904intraDCPrecisionValue    Enc1E64enumObj
}

enc1P904intraDCPrecisionValue OBJECT-TYPE
    SYNTAX     Enc1E64enumObj
    MAX-ACCESS read-write
    STATUS     current
    DESCRIPTION
    "Specifies MPEG2 Intra DC Precision value."
::= { enc1P904intraDCPrecisionEntry 1 }

enc1P906intraVLCFormatTable OBJECT-TYPE
    SYNTAX SEQUENCE OF Enc1P906intraVLCFormatEntry
    MAX-ACCESS not-accessible
    STATUS     current
    DESCRIPTION
    "
    Name      : Intra VLC Format
    Menu Path : /Video/Compression/Advanced Parameters
    Details   : Specifies MPEG2 intra VLC format.
    "
::= { enc1Params 906 }

enc1P906intraVLCFormatEntry OBJECT-TYPE
    SYNTAX Enc1P906intraVLCFormatEntry
    MAX-ACCESS not-accessible
    STATUS     current
    DESCRIPTION
    "Table Entry for Intra VLC Format"
    INDEX { slotId }
::= { enc1P906intraVLCFormatTable 1 }

Enc1P906intraVLCFormatEntry ::= SEQUENCE {
    enc1P906intraVLCFormatValue    Enc1E66enumObj
}

enc1P906intraVLCFormatValue OBJECT-TYPE
    SYNTAX     Enc1E66enumObj
    MAX-ACCESS read-write
    STATUS     current
    DESCRIPTION
    "Specifies MPEG2 intra VLC format."
::= { enc1P906intraVLCFormatEntry 1 }

enc1P907alternateScanTable OBJECT-TYPE
    SYNTAX SEQUENCE OF Enc1P907alternateScanEntry
    MAX-ACCESS not-accessible
    STATUS     current
    DESCRIPTION
    "
    Name      : Alternate Scan
    Menu Path : /Video/Compression/Advanced Parameters
    Details   : Specifies MPEG2 alternate scan.
    "
::= { enc1Params 907 }

enc1P907alternateScanEntry OBJECT-TYPE
    SYNTAX Enc1P907alternateScanEntry
    MAX-ACCESS not-accessible
    STATUS     current
    DESCRIPTION
    "Table Entry for Alternate Scan"
    INDEX { slotId }
::= { enc1P907alternateScanTable 1 }

Enc1P907alternateScanEntry ::= SEQUENCE {
    enc1P907alternateScanValue    Enc1E67enumObj
}

enc1P907alternateScanValue OBJECT-TYPE
    SYNTAX     Enc1E67enumObj
    MAX-ACCESS read-write
    STATUS     current
    DESCRIPTION
    "Specifies MPEG2 alternate scan."
::= { enc1P907alternateScanEntry 1 }

enc1P909weightedPredictionTable OBJECT-TYPE
    SYNTAX SEQUENCE OF Enc1P909weightedPredictionEntry
    MAX-ACCESS not-accessible
    STATUS     current
    DESCRIPTION
    "
    Name      : Weighted Prediction
    Menu Path : /Video/Compression/Advanced Parameters
    Details   : Enable/Disable weighted prediction.
    "
::= { enc1Params 909 }

enc1P909weightedPredictionEntry OBJECT-TYPE
    SYNTAX Enc1P909weightedPredictionEntry
    MAX-ACCESS not-accessible
    STATUS     current
    DESCRIPTION
    "Table Entry for Weighted Prediction"
    INDEX { slotId }
::= { enc1P909weightedPredictionTable 1 }

Enc1P909weightedPredictionEntry ::= SEQUENCE {
    enc1P909weightedPredictionValue    Enc1E0enumObj
}

enc1P909weightedPredictionValue OBJECT-TYPE
    SYNTAX     Enc1E0enumObj
    MAX-ACCESS read-write
    STATUS     current
    DESCRIPTION
    "Enable/Disable weighted prediction."
::= { enc1P909weightedPredictionEntry 1 }

enc1P910mpeg2QPChromaOffsetTable OBJECT-TYPE
    SYNTAX SEQUENCE OF Enc1P910mpeg2QPChromaOffsetEntry
    MAX-ACCESS not-accessible
    STATUS     current
    DESCRIPTION
    "
    Name      : MPEG2 QPChromaOffset
    Menu Path : /Video/Compression/Advanced Parameters
    Units     : 
    Precision : 0
    Low Range : 0
    High Range: -1
    Details   : QP offset for chrominance relative to luminance for MPEG-2 encoding.

     NOTE: Precision/Units/Ranges represent the state of the
           parameter during the MIB generation, and does not
           neccessary reflect the current state of the parameter
    "
::= { enc1Params 910 }

enc1P910mpeg2QPChromaOffsetEntry OBJECT-TYPE
    SYNTAX Enc1P910mpeg2QPChromaOffsetEntry
    MAX-ACCESS not-accessible
    STATUS     current
    DESCRIPTION
    "Table Entry for MPEG2 QPChromaOffset"
    INDEX { slotId }
::= { enc1P910mpeg2QPChromaOffsetTable 1 }

Enc1P910mpeg2QPChromaOffsetEntry ::= SEQUENCE {
    enc1P910mpeg2QPChromaOffsetValue    INTEGER
}

enc1P910mpeg2QPChromaOffsetValue OBJECT-TYPE
    SYNTAX     INTEGER
    MAX-ACCESS read-write
    STATUS     current
    DESCRIPTION
    "QP offset for chrominance relative to luminance for MPEG-2 encoding."
::= { enc1P910mpeg2QPChromaOffsetEntry 1 }

enc1P911systemDelayTable OBJECT-TYPE
    SYNTAX SEQUENCE OF Enc1P911systemDelayEntry
    MAX-ACCESS not-accessible
    STATUS     current
    DESCRIPTION
    "
    Name      : System Delay
    Menu Path : /Video/Compression/Status
    Units     : msec
    Precision : 0
    Low Range : 0
    High Range: 5000
    Details   : Shows current encoder end to end delay (Units: msec)

     NOTE: Precision/Units/Ranges represent the state of the
           parameter during the MIB generation, and does not
           neccessary reflect the current state of the parameter
    "
::= { enc1Params 911 }

enc1P911systemDelayEntry OBJECT-TYPE
    SYNTAX Enc1P911systemDelayEntry
    MAX-ACCESS not-accessible
    STATUS     current
    DESCRIPTION
    "Table Entry for System Delay"
    INDEX { slotId }
::= { enc1P911systemDelayTable 1 }

Enc1P911systemDelayEntry ::= SEQUENCE {
    enc1P911systemDelayValue    INTEGER
}

enc1P911systemDelayValue OBJECT-TYPE
    SYNTAX     INTEGER
    MAX-ACCESS read-only
    STATUS     current
    DESCRIPTION
    "Shows current encoder end to end delay (Units: msec)"
::= { enc1P911systemDelayEntry 1 }

enc1P912metadataProgramTable OBJECT-TYPE
    SYNTAX SEQUENCE OF Enc1P912metadataProgramEntry
    MAX-ACCESS not-accessible
    STATUS     current
    DESCRIPTION
    "
    Name      : Metadata Program
    Menu Path : /Audio/Audio 1/Metadata
    Details   : Specifies the program index to select from the metadata source.
    "
::= { enc1Params 912 }

enc1P912metadataProgramEntry OBJECT-TYPE
    SYNTAX Enc1P912metadataProgramEntry
    MAX-ACCESS not-accessible
    STATUS     current
    DESCRIPTION
    "Table Entry for Metadata Program"
    INDEX { slotId }
::= { enc1P912metadataProgramTable 1 }

Enc1P912metadataProgramEntry ::= SEQUENCE {
    enc1P912metadataProgramValue    Enc1E97enumObj
}

enc1P912metadataProgramValue OBJECT-TYPE
    SYNTAX     Enc1E97enumObj
    MAX-ACCESS read-write
    STATUS     current
    DESCRIPTION
    "Specifies the program index to select from the metadata source."
::= { enc1P912metadataProgramEntry 1 }

enc1P913ecmstreamIDTable OBJECT-TYPE
    SYNTAX SEQUENCE OF Enc1P913ecmstreamIDEntry
    MAX-ACCESS not-accessible
    STATUS     current
    DESCRIPTION
    "
    Name      : ECM Stream ID
    Menu Path : /IP Encapsulation/ATSC MH IP
    Units     : 
    Precision : 0
    Low Range : 0
    High Range: 65535
    Details   : Specifies ECM Stream ID for program.

     NOTE: Precision/Units/Ranges represent the state of the
           parameter during the MIB generation, and does not
           neccessary reflect the current state of the parameter
    "
::= { enc1Params 913 }

enc1P913ecmstreamIDEntry OBJECT-TYPE
    SYNTAX Enc1P913ecmstreamIDEntry
    MAX-ACCESS not-accessible
    STATUS     current
    DESCRIPTION
    "Table Entry for ECM Stream ID"
    INDEX { slotId }
::= { enc1P913ecmstreamIDTable 1 }

Enc1P913ecmstreamIDEntry ::= SEQUENCE {
    enc1P913ecmstreamIDValue    INTEGER
}

enc1P913ecmstreamIDValue OBJECT-TYPE
    SYNTAX     INTEGER
    MAX-ACCESS read-write
    STATUS     current
    DESCRIPTION
    "Specifies ECM Stream ID for program."
::= { enc1P913ecmstreamIDEntry 1 }

enc1P914metadataProgramTable OBJECT-TYPE
    SYNTAX SEQUENCE OF Enc1P914metadataProgramEntry
    MAX-ACCESS not-accessible
    STATUS     current
    DESCRIPTION
    "
    Name      : Metadata Program
    Menu Path : /Audio/Audio 2/Metadata
    Details   : Specifies the program index to select from the metadata source.
    "
::= { enc1Params 914 }

enc1P914metadataProgramEntry OBJECT-TYPE
    SYNTAX Enc1P914metadataProgramEntry
    MAX-ACCESS not-accessible
    STATUS     current
    DESCRIPTION
    "Table Entry for Metadata Program"
    INDEX { slotId }
::= { enc1P914metadataProgramTable 1 }

Enc1P914metadataProgramEntry ::= SEQUENCE {
    enc1P914metadataProgramValue    Enc1E97enumObj
}

enc1P914metadataProgramValue OBJECT-TYPE
    SYNTAX     Enc1E97enumObj
    MAX-ACCESS read-write
    STATUS     current
    DESCRIPTION
    "Specifies the program index to select from the metadata source."
::= { enc1P914metadataProgramEntry 1 }

enc1P915bitDepthTable OBJECT-TYPE
    SYNTAX SEQUENCE OF Enc1P915bitDepthEntry
    MAX-ACCESS not-accessible
    STATUS     current
    DESCRIPTION
    "
    Name      : Bit Depth
    Menu Path : /Audio/Audio 3/Dolby E Encoder
    Details   : Specifies the bit depth of compressed data words.
    "
::= { enc1Params 915 }

enc1P915bitDepthEntry OBJECT-TYPE
    SYNTAX Enc1P915bitDepthEntry
    MAX-ACCESS not-accessible
    STATUS     current
    DESCRIPTION
    "Table Entry for Bit Depth"
    INDEX { slotId }
::= { enc1P915bitDepthTable 1 }

Enc1P915bitDepthEntry ::= SEQUENCE {
    enc1P915bitDepthValue    Enc1E98enumObj
}

enc1P915bitDepthValue OBJECT-TYPE
    SYNTAX     Enc1E98enumObj
    MAX-ACCESS read-write
    STATUS     current
    DESCRIPTION
    "Specifies the bit depth of compressed data words."
::= { enc1P915bitDepthEntry 1 }

enc1P916metadataProgramTable OBJECT-TYPE
    SYNTAX SEQUENCE OF Enc1P916metadataProgramEntry
    MAX-ACCESS not-accessible
    STATUS     current
    DESCRIPTION
    "
    Name      : Metadata Program
    Menu Path : /Audio/Audio 3/Metadata
    Details   : Specifies the program index to select from the metadata source.
    "
::= { enc1Params 916 }

enc1P916metadataProgramEntry OBJECT-TYPE
    SYNTAX Enc1P916metadataProgramEntry
    MAX-ACCESS not-accessible
    STATUS     current
    DESCRIPTION
    "Table Entry for Metadata Program"
    INDEX { slotId }
::= { enc1P916metadataProgramTable 1 }

Enc1P916metadataProgramEntry ::= SEQUENCE {
    enc1P916metadataProgramValue    Enc1E97enumObj
}

enc1P916metadataProgramValue OBJECT-TYPE
    SYNTAX     Enc1E97enumObj
    MAX-ACCESS read-write
    STATUS     current
    DESCRIPTION
    "Specifies the program index to select from the metadata source."
::= { enc1P916metadataProgramEntry 1 }

enc1P917bitDepthTable OBJECT-TYPE
    SYNTAX SEQUENCE OF Enc1P917bitDepthEntry
    MAX-ACCESS not-accessible
    STATUS     current
    DESCRIPTION
    "
    Name      : Bit Depth
    Menu Path : /Audio/Audio 4/Dolby E Encoder
    Details   : Specifies the bit depth of compressed data words.
    "
::= { enc1Params 917 }

enc1P917bitDepthEntry OBJECT-TYPE
    SYNTAX Enc1P917bitDepthEntry
    MAX-ACCESS not-accessible
    STATUS     current
    DESCRIPTION
    "Table Entry for Bit Depth"
    INDEX { slotId }
::= { enc1P917bitDepthTable 1 }

Enc1P917bitDepthEntry ::= SEQUENCE {
    enc1P917bitDepthValue    Enc1E98enumObj
}

enc1P917bitDepthValue OBJECT-TYPE
    SYNTAX     Enc1E98enumObj
    MAX-ACCESS read-write
    STATUS     current
    DESCRIPTION
    "Specifies the bit depth of compressed data words."
::= { enc1P917bitDepthEntry 1 }

enc1P918metadataProgramTable OBJECT-TYPE
    SYNTAX SEQUENCE OF Enc1P918metadataProgramEntry
    MAX-ACCESS not-accessible
    STATUS     current
    DESCRIPTION
    "
    Name      : Metadata Program
    Menu Path : /Audio/Audio 4/Metadata
    Details   : Specifies the program index to select from the metadata source.
    "
::= { enc1Params 918 }

enc1P918metadataProgramEntry OBJECT-TYPE
    SYNTAX Enc1P918metadataProgramEntry
    MAX-ACCESS not-accessible
    STATUS     current
    DESCRIPTION
    "Table Entry for Metadata Program"
    INDEX { slotId }
::= { enc1P918metadataProgramTable 1 }

Enc1P918metadataProgramEntry ::= SEQUENCE {
    enc1P918metadataProgramValue    Enc1E97enumObj
}

enc1P918metadataProgramValue OBJECT-TYPE
    SYNTAX     Enc1E97enumObj
    MAX-ACCESS read-write
    STATUS     current
    DESCRIPTION
    "Specifies the program index to select from the metadata source."
::= { enc1P918metadataProgramEntry 1 }

enc1P919bitDepthTable OBJECT-TYPE
    SYNTAX SEQUENCE OF Enc1P919bitDepthEntry
    MAX-ACCESS not-accessible
    STATUS     current
    DESCRIPTION
    "
    Name      : Bit Depth
    Menu Path : /Audio/Audio 5/Dolby E Encoder
    Details   : Specifies the bit depth of compressed data words.
    "
::= { enc1Params 919 }

enc1P919bitDepthEntry OBJECT-TYPE
    SYNTAX Enc1P919bitDepthEntry
    MAX-ACCESS not-accessible
    STATUS     current
    DESCRIPTION
    "Table Entry for Bit Depth"
    INDEX { slotId }
::= { enc1P919bitDepthTable 1 }

Enc1P919bitDepthEntry ::= SEQUENCE {
    enc1P919bitDepthValue    Enc1E98enumObj
}

enc1P919bitDepthValue OBJECT-TYPE
    SYNTAX     Enc1E98enumObj
    MAX-ACCESS read-write
    STATUS     current
    DESCRIPTION
    "Specifies the bit depth of compressed data words."
::= { enc1P919bitDepthEntry 1 }

enc1P920metadataProgramTable OBJECT-TYPE
    SYNTAX SEQUENCE OF Enc1P920metadataProgramEntry
    MAX-ACCESS not-accessible
    STATUS     current
    DESCRIPTION
    "
    Name      : Metadata Program
    Menu Path : /Audio/Audio 5/Metadata
    Details   : Specifies the program index to select from the metadata source.
    "
::= { enc1Params 920 }

enc1P920metadataProgramEntry OBJECT-TYPE
    SYNTAX Enc1P920metadataProgramEntry
    MAX-ACCESS not-accessible
    STATUS     current
    DESCRIPTION
    "Table Entry for Metadata Program"
    INDEX { slotId }
::= { enc1P920metadataProgramTable 1 }

Enc1P920metadataProgramEntry ::= SEQUENCE {
    enc1P920metadataProgramValue    Enc1E97enumObj
}

enc1P920metadataProgramValue OBJECT-TYPE
    SYNTAX     Enc1E97enumObj
    MAX-ACCESS read-write
    STATUS     current
    DESCRIPTION
    "Specifies the program index to select from the metadata source."
::= { enc1P920metadataProgramEntry 1 }

enc1P921bitDepthTable OBJECT-TYPE
    SYNTAX SEQUENCE OF Enc1P921bitDepthEntry
    MAX-ACCESS not-accessible
    STATUS     current
    DESCRIPTION
    "
    Name      : Bit Depth
    Menu Path : /Audio/Audio 6/Dolby E Encoder
    Details   : Specifies the bit depth of compressed data words.
    "
::= { enc1Params 921 }

enc1P921bitDepthEntry OBJECT-TYPE
    SYNTAX Enc1P921bitDepthEntry
    MAX-ACCESS not-accessible
    STATUS     current
    DESCRIPTION
    "Table Entry for Bit Depth"
    INDEX { slotId }
::= { enc1P921bitDepthTable 1 }

Enc1P921bitDepthEntry ::= SEQUENCE {
    enc1P921bitDepthValue    Enc1E98enumObj
}

enc1P921bitDepthValue OBJECT-TYPE
    SYNTAX     Enc1E98enumObj
    MAX-ACCESS read-write
    STATUS     current
    DESCRIPTION
    "Specifies the bit depth of compressed data words."
::= { enc1P921bitDepthEntry 1 }

enc1P922metadataProgramTable OBJECT-TYPE
    SYNTAX SEQUENCE OF Enc1P922metadataProgramEntry
    MAX-ACCESS not-accessible
    STATUS     current
    DESCRIPTION
    "
    Name      : Metadata Program
    Menu Path : /Audio/Audio 6/Metadata
    Details   : Specifies the program index to select from the metadata source.
    "
::= { enc1Params 922 }

enc1P922metadataProgramEntry OBJECT-TYPE
    SYNTAX Enc1P922metadataProgramEntry
    MAX-ACCESS not-accessible
    STATUS     current
    DESCRIPTION
    "Table Entry for Metadata Program"
    INDEX { slotId }
::= { enc1P922metadataProgramTable 1 }

Enc1P922metadataProgramEntry ::= SEQUENCE {
    enc1P922metadataProgramValue    Enc1E97enumObj
}

enc1P922metadataProgramValue OBJECT-TYPE
    SYNTAX     Enc1E97enumObj
    MAX-ACCESS read-write
    STATUS     current
    DESCRIPTION
    "Specifies the program index to select from the metadata source."
::= { enc1P922metadataProgramEntry 1 }

enc1P923bitDepthTable OBJECT-TYPE
    SYNTAX SEQUENCE OF Enc1P923bitDepthEntry
    MAX-ACCESS not-accessible
    STATUS     current
    DESCRIPTION
    "
    Name      : Bit Depth
    Menu Path : /Audio/Audio 7/Dolby E Encoder
    Details   : Specifies the bit depth of compressed data words.
    "
::= { enc1Params 923 }

enc1P923bitDepthEntry OBJECT-TYPE
    SYNTAX Enc1P923bitDepthEntry
    MAX-ACCESS not-accessible
    STATUS     current
    DESCRIPTION
    "Table Entry for Bit Depth"
    INDEX { slotId }
::= { enc1P923bitDepthTable 1 }

Enc1P923bitDepthEntry ::= SEQUENCE {
    enc1P923bitDepthValue    Enc1E98enumObj
}

enc1P923bitDepthValue OBJECT-TYPE
    SYNTAX     Enc1E98enumObj
    MAX-ACCESS read-write
    STATUS     current
    DESCRIPTION
    "Specifies the bit depth of compressed data words."
::= { enc1P923bitDepthEntry 1 }

enc1P924metadataProgramTable OBJECT-TYPE
    SYNTAX SEQUENCE OF Enc1P924metadataProgramEntry
    MAX-ACCESS not-accessible
    STATUS     current
    DESCRIPTION
    "
    Name      : Metadata Program
    Menu Path : /Audio/Audio 7/Metadata
    Details   : Specifies the program index to select from the metadata source.
    "
::= { enc1Params 924 }

enc1P924metadataProgramEntry OBJECT-TYPE
    SYNTAX Enc1P924metadataProgramEntry
    MAX-ACCESS not-accessible
    STATUS     current
    DESCRIPTION
    "Table Entry for Metadata Program"
    INDEX { slotId }
::= { enc1P924metadataProgramTable 1 }

Enc1P924metadataProgramEntry ::= SEQUENCE {
    enc1P924metadataProgramValue    Enc1E97enumObj
}

enc1P924metadataProgramValue OBJECT-TYPE
    SYNTAX     Enc1E97enumObj
    MAX-ACCESS read-write
    STATUS     current
    DESCRIPTION
    "Specifies the program index to select from the metadata source."
::= { enc1P924metadataProgramEntry 1 }

enc1P925bitDepthTable OBJECT-TYPE
    SYNTAX SEQUENCE OF Enc1P925bitDepthEntry
    MAX-ACCESS not-accessible
    STATUS     current
    DESCRIPTION
    "
    Name      : Bit Depth
    Menu Path : /Audio/Audio 8/Dolby E Encoder
    Details   : Specifies the bit depth of compressed data words.
    "
::= { enc1Params 925 }

enc1P925bitDepthEntry OBJECT-TYPE
    SYNTAX Enc1P925bitDepthEntry
    MAX-ACCESS not-accessible
    STATUS     current
    DESCRIPTION
    "Table Entry for Bit Depth"
    INDEX { slotId }
::= { enc1P925bitDepthTable 1 }

Enc1P925bitDepthEntry ::= SEQUENCE {
    enc1P925bitDepthValue    Enc1E98enumObj
}

enc1P925bitDepthValue OBJECT-TYPE
    SYNTAX     Enc1E98enumObj
    MAX-ACCESS read-write
    STATUS     current
    DESCRIPTION
    "Specifies the bit depth of compressed data words."
::= { enc1P925bitDepthEntry 1 }

enc1P926metadataProgramTable OBJECT-TYPE
    SYNTAX SEQUENCE OF Enc1P926metadataProgramEntry
    MAX-ACCESS not-accessible
    STATUS     current
    DESCRIPTION
    "
    Name      : Metadata Program
    Menu Path : /Audio/Audio 8/Metadata
    Details   : Specifies the program index to select from the metadata source.
    "
::= { enc1Params 926 }

enc1P926metadataProgramEntry OBJECT-TYPE
    SYNTAX Enc1P926metadataProgramEntry
    MAX-ACCESS not-accessible
    STATUS     current
    DESCRIPTION
    "Table Entry for Metadata Program"
    INDEX { slotId }
::= { enc1P926metadataProgramTable 1 }

Enc1P926metadataProgramEntry ::= SEQUENCE {
    enc1P926metadataProgramValue    Enc1E97enumObj
}

enc1P926metadataProgramValue OBJECT-TYPE
    SYNTAX     Enc1E97enumObj
    MAX-ACCESS read-write
    STATUS     current
    DESCRIPTION
    "Specifies the program index to select from the metadata source."
::= { enc1P926metadataProgramEntry 1 }

enc1P927programSelectTable OBJECT-TYPE
    SYNTAX SEQUENCE OF Enc1P927programSelectEntry
    MAX-ACCESS not-accessible
    STATUS     current
    DESCRIPTION
    "
    Name      : Program Select
    Menu Path : /Audio/Metadata Generator 1
    Details   : Select one of eight audio metadata programs to display/modify.
    "
::= { enc1Params 927 }

enc1P927programSelectEntry OBJECT-TYPE
    SYNTAX Enc1P927programSelectEntry
    MAX-ACCESS not-accessible
    STATUS     current
    DESCRIPTION
    "Table Entry for Program Select"
    INDEX { slotId }
::= { enc1P927programSelectTable 1 }

Enc1P927programSelectEntry ::= SEQUENCE {
    enc1P927programSelectValue    Enc1E97enumObj
}

enc1P927programSelectValue OBJECT-TYPE
    SYNTAX     Enc1E97enumObj
    MAX-ACCESS read-write
    STATUS     current
    DESCRIPTION
    "Select one of eight audio metadata programs to display/modify."
::= { enc1P927programSelectEntry 1 }

enc1P929bitstreamModeTable OBJECT-TYPE
    SYNTAX SEQUENCE OF Enc1P929bitstreamModeEntry
    MAX-ACCESS not-accessible
    STATUS     current
    DESCRIPTION
    "
    Name      : Bitstream Mode
    Menu Path : /Audio/Metadata Generator 1
    Details   : Describes the audio service contained within the Dolby Digital bitstream.
    "
::= { enc1Params 929 }

enc1P929bitstreamModeEntry OBJECT-TYPE
    SYNTAX Enc1P929bitstreamModeEntry
    MAX-ACCESS not-accessible
    STATUS     current
    DESCRIPTION
    "Table Entry for Bitstream Mode"
    INDEX { slotId }
::= { enc1P929bitstreamModeTable 1 }

Enc1P929bitstreamModeEntry ::= SEQUENCE {
    enc1P929bitstreamModeValue    Enc1E85enumObj
}

enc1P929bitstreamModeValue OBJECT-TYPE
    SYNTAX     Enc1E85enumObj
    MAX-ACCESS read-write
    STATUS     current
    DESCRIPTION
    "Describes the audio service contained within the Dolby Digital bitstream."
::= { enc1P929bitstreamModeEntry 1 }

enc1P930codingModeTable OBJECT-TYPE
    SYNTAX SEQUENCE OF Enc1P930codingModeEntry
    MAX-ACCESS not-accessible
    STATUS     current
    DESCRIPTION
    "
    Name      : Coding Mode
    Menu Path : /Audio/Metadata Generator 1
    Details   : Indicates the active channels within the encoded bitstream.
    "
::= { enc1Params 930 }

enc1P930codingModeEntry OBJECT-TYPE
    SYNTAX Enc1P930codingModeEntry
    MAX-ACCESS not-accessible
    STATUS     current
    DESCRIPTION
    "Table Entry for Coding Mode"
    INDEX { slotId }
::= { enc1P930codingModeTable 1 }

Enc1P930codingModeEntry ::= SEQUENCE {
    enc1P930codingModeValue    Enc1E86enumObj
}

enc1P930codingModeValue OBJECT-TYPE
    SYNTAX     Enc1E86enumObj
    MAX-ACCESS read-write
    STATUS     current
    DESCRIPTION
    "Indicates the active channels within the encoded bitstream."
::= { enc1P930codingModeEntry 1 }

enc1P931centerMixLevelTable OBJECT-TYPE
    SYNTAX SEQUENCE OF Enc1P931centerMixLevelEntry
    MAX-ACCESS not-accessible
    STATUS     current
    DESCRIPTION
    "
    Name      : Center Mix Level
    Menu Path : /Audio/Metadata Generator 1
    Details   : Nominal level for center channel in a stereo downmix.
    "
::= { enc1Params 931 }

enc1P931centerMixLevelEntry OBJECT-TYPE
    SYNTAX Enc1P931centerMixLevelEntry
    MAX-ACCESS not-accessible
    STATUS     current
    DESCRIPTION
    "Table Entry for Center Mix Level"
    INDEX { slotId }
::= { enc1P931centerMixLevelTable 1 }

Enc1P931centerMixLevelEntry ::= SEQUENCE {
    enc1P931centerMixLevelValue    Enc1E87enumObj
}

enc1P931centerMixLevelValue OBJECT-TYPE
    SYNTAX     Enc1E87enumObj
    MAX-ACCESS read-write
    STATUS     current
    DESCRIPTION
    "Nominal level for center channel in a stereo downmix."
::= { enc1P931centerMixLevelEntry 1 }

enc1P932surroundMixLevelTable OBJECT-TYPE
    SYNTAX SEQUENCE OF Enc1P932surroundMixLevelEntry
    MAX-ACCESS not-accessible
    STATUS     current
    DESCRIPTION
    "
    Name      : Surround Mix Level
    Menu Path : /Audio/Metadata Generator 1
    Details   : Nominal level for surround channel(s) in a stereo downmix.
    "
::= { enc1Params 932 }

enc1P932surroundMixLevelEntry OBJECT-TYPE
    SYNTAX Enc1P932surroundMixLevelEntry
    MAX-ACCESS not-accessible
    STATUS     current
    DESCRIPTION
    "Table Entry for Surround Mix Level"
    INDEX { slotId }
::= { enc1P932surroundMixLevelTable 1 }

Enc1P932surroundMixLevelEntry ::= SEQUENCE {
    enc1P932surroundMixLevelValue    Enc1E88enumObj
}

enc1P932surroundMixLevelValue OBJECT-TYPE
    SYNTAX     Enc1E88enumObj
    MAX-ACCESS read-write
    STATUS     current
    DESCRIPTION
    "Nominal level for surround channel(s) in a stereo downmix."
::= { enc1P932surroundMixLevelEntry 1 }

enc1P933dolbySurroundModeTable OBJECT-TYPE
    SYNTAX SEQUENCE OF Enc1P933dolbySurroundModeEntry
    MAX-ACCESS not-accessible
    STATUS     current
    DESCRIPTION
    "
    Name      : Dolby Surround Mode
    Menu Path : /Audio/Metadata Generator 1
    Details   : Indicates whether this is a 2 channel Dolby Surround encoding intended for a Dolby Pro Logic decoder.
    "
::= { enc1Params 933 }

enc1P933dolbySurroundModeEntry OBJECT-TYPE
    SYNTAX Enc1P933dolbySurroundModeEntry
    MAX-ACCESS not-accessible
    STATUS     current
    DESCRIPTION
    "Table Entry for Dolby Surround Mode"
    INDEX { slotId }
::= { enc1P933dolbySurroundModeTable 1 }

Enc1P933dolbySurroundModeEntry ::= SEQUENCE {
    enc1P933dolbySurroundModeValue    Enc1E89enumObj
}

enc1P933dolbySurroundModeValue OBJECT-TYPE
    SYNTAX     Enc1E89enumObj
    MAX-ACCESS read-write
    STATUS     current
    DESCRIPTION
    "Indicates whether this is a 2 channel Dolby Surround encoding intended for a Dolby Pro Logic decoder."
::= { enc1P933dolbySurroundModeEntry 1 }

enc1P934lfechannelTable OBJECT-TYPE
    SYNTAX SEQUENCE OF Enc1P934lfechannelEntry
    MAX-ACCESS not-accessible
    STATUS     current
    DESCRIPTION
    "
    Name      : LFE Channel
    Menu Path : /Audio/Metadata Generator 1
    Details   : Indicates whether a Low Frequency Effects channel is present.
    "
::= { enc1Params 934 }

enc1P934lfechannelEntry OBJECT-TYPE
    SYNTAX Enc1P934lfechannelEntry
    MAX-ACCESS not-accessible
    STATUS     current
    DESCRIPTION
    "Table Entry for LFE Channel"
    INDEX { slotId }
::= { enc1P934lfechannelTable 1 }

Enc1P934lfechannelEntry ::= SEQUENCE {
    enc1P934lfechannelValue    Enc1E1enumObj
}

enc1P934lfechannelValue OBJECT-TYPE
    SYNTAX     Enc1E1enumObj
    MAX-ACCESS read-write
    STATUS     current
    DESCRIPTION
    "Indicates whether a Low Frequency Effects channel is present."
::= { enc1P934lfechannelEntry 1 }

enc1P935dialogNormalizationTable OBJECT-TYPE
    SYNTAX SEQUENCE OF Enc1P935dialogNormalizationEntry
    MAX-ACCESS not-accessible
    STATUS     current
    DESCRIPTION
    "
    Name      : Dialog Normalization
    Menu Path : /Audio/Metadata Generator 1
    Units     : dB
    Precision : 0
    Low Range : -31
    High Range: -1
    Details   : Specifies the long-term A-weighted average level of dialogue, Leq(A), equivalent to dBEq/LKFS.

     NOTE: Precision/Units/Ranges represent the state of the
           parameter during the MIB generation, and does not
           neccessary reflect the current state of the parameter
    "
::= { enc1Params 935 }

enc1P935dialogNormalizationEntry OBJECT-TYPE
    SYNTAX Enc1P935dialogNormalizationEntry
    MAX-ACCESS not-accessible
    STATUS     current
    DESCRIPTION
    "Table Entry for Dialog Normalization"
    INDEX { slotId }
::= { enc1P935dialogNormalizationTable 1 }

Enc1P935dialogNormalizationEntry ::= SEQUENCE {
    enc1P935dialogNormalizationValue    INTEGER
}

enc1P935dialogNormalizationValue OBJECT-TYPE
    SYNTAX     INTEGER
    MAX-ACCESS read-write
    STATUS     current
    DESCRIPTION
    "Specifies the long-term A-weighted average level of dialogue, Leq(A), equivalent to dBEq/LKFS."
::= { enc1P935dialogNormalizationEntry 1 }

enc1P936audioProductionInfoTable OBJECT-TYPE
    SYNTAX SEQUENCE OF Enc1P936audioProductionInfoEntry
    MAX-ACCESS not-accessible
    STATUS     current
    DESCRIPTION
    "
    Name      : Audio Production Info
    Menu Path : /Audio/Metadata Generator 1
    Details   : Indicates if audio production parameters (Mix Level and Room Type) are specified.
    "
::= { enc1Params 936 }

enc1P936audioProductionInfoEntry OBJECT-TYPE
    SYNTAX Enc1P936audioProductionInfoEntry
    MAX-ACCESS not-accessible
    STATUS     current
    DESCRIPTION
    "Table Entry for Audio Production Info"
    INDEX { slotId }
::= { enc1P936audioProductionInfoTable 1 }

Enc1P936audioProductionInfoEntry ::= SEQUENCE {
    enc1P936audioProductionInfoValue    Enc1E11enumObj
}

enc1P936audioProductionInfoValue OBJECT-TYPE
    SYNTAX     Enc1E11enumObj
    MAX-ACCESS read-write
    STATUS     current
    DESCRIPTION
    "Indicates if audio production parameters (Mix Level and Room Type) are specified."
::= { enc1P936audioProductionInfoEntry 1 }

enc1P937mixLevelTable OBJECT-TYPE
    SYNTAX SEQUENCE OF Enc1P937mixLevelEntry
    MAX-ACCESS not-accessible
    STATUS     current
    DESCRIPTION
    "
    Name      : Mix Level
    Menu Path : /Audio/Metadata Generator 1
    Units     : dB
    Precision : 0
    Low Range : 80
    High Range: 111
    Details   : Specifies the peak sound pressure level (SPL) used during final audio mixing.

     NOTE: Precision/Units/Ranges represent the state of the
           parameter during the MIB generation, and does not
           neccessary reflect the current state of the parameter
    "
::= { enc1Params 937 }

enc1P937mixLevelEntry OBJECT-TYPE
    SYNTAX Enc1P937mixLevelEntry
    MAX-ACCESS not-accessible
    STATUS     current
    DESCRIPTION
    "Table Entry for Mix Level"
    INDEX { slotId }
::= { enc1P937mixLevelTable 1 }

Enc1P937mixLevelEntry ::= SEQUENCE {
    enc1P937mixLevelValue    INTEGER
}

enc1P937mixLevelValue OBJECT-TYPE
    SYNTAX     INTEGER
    MAX-ACCESS read-write
    STATUS     current
    DESCRIPTION
    "Specifies the peak sound pressure level (SPL) used during final audio mixing."
::= { enc1P937mixLevelEntry 1 }

enc1P938roomTypeTable OBJECT-TYPE
    SYNTAX SEQUENCE OF Enc1P938roomTypeEntry
    MAX-ACCESS not-accessible
    STATUS     current
    DESCRIPTION
    "
    Name      : Room Type
    Menu Path : /Audio/Metadata Generator 1
    Details   : Describes equalization used during the final mixing. Large is X-curve, small is flat.
    "
::= { enc1Params 938 }

enc1P938roomTypeEntry OBJECT-TYPE
    SYNTAX Enc1P938roomTypeEntry
    MAX-ACCESS not-accessible
    STATUS     current
    DESCRIPTION
    "Table Entry for Room Type"
    INDEX { slotId }
::= { enc1P938roomTypeTable 1 }

Enc1P938roomTypeEntry ::= SEQUENCE {
    enc1P938roomTypeValue    Enc1E96enumObj
}

enc1P938roomTypeValue OBJECT-TYPE
    SYNTAX     Enc1E96enumObj
    MAX-ACCESS read-write
    STATUS     current
    DESCRIPTION
    "Describes equalization used during the final mixing. Large is X-curve, small is flat."
::= { enc1P938roomTypeEntry 1 }

enc1P939copyrightProtectedTable OBJECT-TYPE
    SYNTAX SEQUENCE OF Enc1P939copyrightProtectedEntry
    MAX-ACCESS not-accessible
    STATUS     current
    DESCRIPTION
    "
    Name      : Copyright Protected
    Menu Path : /Audio/Metadata Generator 1
    Details   : Indicates whether the source material is copyright protected.
    "
::= { enc1Params 939 }

enc1P939copyrightProtectedEntry OBJECT-TYPE
    SYNTAX Enc1P939copyrightProtectedEntry
    MAX-ACCESS not-accessible
    STATUS     current
    DESCRIPTION
    "Table Entry for Copyright Protected"
    INDEX { slotId }
::= { enc1P939copyrightProtectedTable 1 }

Enc1P939copyrightProtectedEntry ::= SEQUENCE {
    enc1P939copyrightProtectedValue    Enc1E11enumObj
}

enc1P939copyrightProtectedValue OBJECT-TYPE
    SYNTAX     Enc1E11enumObj
    MAX-ACCESS read-write
    STATUS     current
    DESCRIPTION
    "Indicates whether the source material is copyright protected."
::= { enc1P939copyrightProtectedEntry 1 }

enc1P940originalBitstreamTable OBJECT-TYPE
    SYNTAX SEQUENCE OF Enc1P940originalBitstreamEntry
    MAX-ACCESS not-accessible
    STATUS     current
    DESCRIPTION
    "
    Name      : Original Bitstream
    Menu Path : /Audio/Metadata Generator 1
    Details   : Indicates whether the source material is the master version or a copy.
    "
::= { enc1Params 940 }

enc1P940originalBitstreamEntry OBJECT-TYPE
    SYNTAX Enc1P940originalBitstreamEntry
    MAX-ACCESS not-accessible
    STATUS     current
    DESCRIPTION
    "Table Entry for Original Bitstream"
    INDEX { slotId }
::= { enc1P940originalBitstreamTable 1 }

Enc1P940originalBitstreamEntry ::= SEQUENCE {
    enc1P940originalBitstreamValue    Enc1E11enumObj
}

enc1P940originalBitstreamValue OBJECT-TYPE
    SYNTAX     Enc1E11enumObj
    MAX-ACCESS read-write
    STATUS     current
    DESCRIPTION
    "Indicates whether the source material is the master version or a copy."
::= { enc1P940originalBitstreamEntry 1 }

enc1P941extendedBitstreamInformationTable OBJECT-TYPE
    SYNTAX SEQUENCE OF Enc1P941extendedBitstreamInformationEntry
    MAX-ACCESS not-accessible
    STATUS     current
    DESCRIPTION
    "
    Name      : Extended Bitstream Information
    Menu Path : /Audio/Metadata Generator 1
    Details   : Enables extended bitstream parameters (Ext:).
    "
::= { enc1Params 941 }

enc1P941extendedBitstreamInformationEntry OBJECT-TYPE
    SYNTAX Enc1P941extendedBitstreamInformationEntry
    MAX-ACCESS not-accessible
    STATUS     current
    DESCRIPTION
    "Table Entry for Extended Bitstream Information"
    INDEX { slotId }
::= { enc1P941extendedBitstreamInformationTable 1 }

Enc1P941extendedBitstreamInformationEntry ::= SEQUENCE {
    enc1P941extendedBitstreamInformationValue    Enc1E0enumObj
}

enc1P941extendedBitstreamInformationValue OBJECT-TYPE
    SYNTAX     Enc1E0enumObj
    MAX-ACCESS read-write
    STATUS     current
    DESCRIPTION
    "Enables extended bitstream parameters (Ext:)."
::= { enc1P941extendedBitstreamInformationEntry 1 }

enc1P943extPreferredStereoDownmixTable OBJECT-TYPE
    SYNTAX SEQUENCE OF Enc1P943extPreferredStereoDownmixEntry
    MAX-ACCESS not-accessible
    STATUS     current
    DESCRIPTION
    "
    Name      : Ext: Preferred Stereo Downmix
    Menu Path : /Audio/Metadata Generator 1
    Details   : Indicates the preferred type of stereo downmix.
    "
::= { enc1Params 943 }

enc1P943extPreferredStereoDownmixEntry OBJECT-TYPE
    SYNTAX Enc1P943extPreferredStereoDownmixEntry
    MAX-ACCESS not-accessible
    STATUS     current
    DESCRIPTION
    "Table Entry for Ext: Preferred Stereo Downmix"
    INDEX { slotId }
::= { enc1P943extPreferredStereoDownmixTable 1 }

Enc1P943extPreferredStereoDownmixEntry ::= SEQUENCE {
    enc1P943extPreferredStereoDownmixValue    Enc1E90enumObj
}

enc1P943extPreferredStereoDownmixValue OBJECT-TYPE
    SYNTAX     Enc1E90enumObj
    MAX-ACCESS read-write
    STATUS     current
    DESCRIPTION
    "Indicates the preferred type of stereo downmix."
::= { enc1P943extPreferredStereoDownmixEntry 1 }

enc1P944extLtRtCenterMixLevelTable OBJECT-TYPE
    SYNTAX SEQUENCE OF Enc1P944extLtRtCenterMixLevelEntry
    MAX-ACCESS not-accessible
    STATUS     current
    DESCRIPTION
    "
    Name      : Ext: LtRt Center Mix Level
    Menu Path : /Audio/Metadata Generator 1
    Details   : Level shift applied to the center channel during an Lt/Rt downmix.
    "
::= { enc1Params 944 }

enc1P944extLtRtCenterMixLevelEntry OBJECT-TYPE
    SYNTAX Enc1P944extLtRtCenterMixLevelEntry
    MAX-ACCESS not-accessible
    STATUS     current
    DESCRIPTION
    "Table Entry for Ext: LtRt Center Mix Level"
    INDEX { slotId }
::= { enc1P944extLtRtCenterMixLevelTable 1 }

Enc1P944extLtRtCenterMixLevelEntry ::= SEQUENCE {
    enc1P944extLtRtCenterMixLevelValue    Enc1E91enumObj
}

enc1P944extLtRtCenterMixLevelValue OBJECT-TYPE
    SYNTAX     Enc1E91enumObj
    MAX-ACCESS read-write
    STATUS     current
    DESCRIPTION
    "Level shift applied to the center channel during an Lt/Rt downmix."
::= { enc1P944extLtRtCenterMixLevelEntry 1 }

enc1P945extLtRtSurroundMixLevelTable OBJECT-TYPE
    SYNTAX SEQUENCE OF Enc1P945extLtRtSurroundMixLevelEntry
    MAX-ACCESS not-accessible
    STATUS     current
    DESCRIPTION
    "
    Name      : Ext: LtRt Surround Mix Level
    Menu Path : /Audio/Metadata Generator 1
    Details   : Level shift applied to the surround channel(s) during an Lt/Rt downmix.
    "
::= { enc1Params 945 }

enc1P945extLtRtSurroundMixLevelEntry OBJECT-TYPE
    SYNTAX Enc1P945extLtRtSurroundMixLevelEntry
    MAX-ACCESS not-accessible
    STATUS     current
    DESCRIPTION
    "Table Entry for Ext: LtRt Surround Mix Level"
    INDEX { slotId }
::= { enc1P945extLtRtSurroundMixLevelTable 1 }

Enc1P945extLtRtSurroundMixLevelEntry ::= SEQUENCE {
    enc1P945extLtRtSurroundMixLevelValue    Enc1E92enumObj
}

enc1P945extLtRtSurroundMixLevelValue OBJECT-TYPE
    SYNTAX     Enc1E92enumObj
    MAX-ACCESS read-write
    STATUS     current
    DESCRIPTION
    "Level shift applied to the surround channel(s) during an Lt/Rt downmix."
::= { enc1P945extLtRtSurroundMixLevelEntry 1 }

enc1P946extLoRoCenterMixLevelTable OBJECT-TYPE
    SYNTAX SEQUENCE OF Enc1P946extLoRoCenterMixLevelEntry
    MAX-ACCESS not-accessible
    STATUS     current
    DESCRIPTION
    "
    Name      : Ext: LoRo Center Mix Level
    Menu Path : /Audio/Metadata Generator 1
    Details   : Level shift applied to the center channel during an Lo/Ro downmix. (Replaces Center Mix Level)
    "
::= { enc1Params 946 }

enc1P946extLoRoCenterMixLevelEntry OBJECT-TYPE
    SYNTAX Enc1P946extLoRoCenterMixLevelEntry
    MAX-ACCESS not-accessible
    STATUS     current
    DESCRIPTION
    "Table Entry for Ext: LoRo Center Mix Level"
    INDEX { slotId }
::= { enc1P946extLoRoCenterMixLevelTable 1 }

Enc1P946extLoRoCenterMixLevelEntry ::= SEQUENCE {
    enc1P946extLoRoCenterMixLevelValue    Enc1E91enumObj
}

enc1P946extLoRoCenterMixLevelValue OBJECT-TYPE
    SYNTAX     Enc1E91enumObj
    MAX-ACCESS read-write
    STATUS     current
    DESCRIPTION
    "Level shift applied to the center channel during an Lo/Ro downmix. (Replaces Center Mix Level)"
::= { enc1P946extLoRoCenterMixLevelEntry 1 }

enc1P947extLoRoSurroundMixLevelTable OBJECT-TYPE
    SYNTAX SEQUENCE OF Enc1P947extLoRoSurroundMixLevelEntry
    MAX-ACCESS not-accessible
    STATUS     current
    DESCRIPTION
    "
    Name      : Ext: LoRo Surround Mix Level
    Menu Path : /Audio/Metadata Generator 1
    Details   : Level shift applied to the surround channel(s) during an Lo/Ro downmix.
    "
::= { enc1Params 947 }

enc1P947extLoRoSurroundMixLevelEntry OBJECT-TYPE
    SYNTAX Enc1P947extLoRoSurroundMixLevelEntry
    MAX-ACCESS not-accessible
    STATUS     current
    DESCRIPTION
    "Table Entry for Ext: LoRo Surround Mix Level"
    INDEX { slotId }
::= { enc1P947extLoRoSurroundMixLevelTable 1 }

Enc1P947extLoRoSurroundMixLevelEntry ::= SEQUENCE {
    enc1P947extLoRoSurroundMixLevelValue    Enc1E92enumObj
}

enc1P947extLoRoSurroundMixLevelValue OBJECT-TYPE
    SYNTAX     Enc1E92enumObj
    MAX-ACCESS read-write
    STATUS     current
    DESCRIPTION
    "Level shift applied to the surround channel(s) during an Lo/Ro downmix."
::= { enc1P947extLoRoSurroundMixLevelEntry 1 }

enc1P949extDolbyDigitalSurroundEXModeTable OBJECT-TYPE
    SYNTAX SEQUENCE OF Enc1P949extDolbyDigitalSurroundEXModeEntry
    MAX-ACCESS not-accessible
    STATUS     current
    DESCRIPTION
    "
    Name      : Ext: Dolby Digital Surround EX Mode
    Menu Path : /Audio/Metadata Generator 1
    Details   : Indicates whether the source material is a 5.1 channel Dolby Digital Surround EX encoding.
    "
::= { enc1Params 949 }

enc1P949extDolbyDigitalSurroundEXModeEntry OBJECT-TYPE
    SYNTAX Enc1P949extDolbyDigitalSurroundEXModeEntry
    MAX-ACCESS not-accessible
    STATUS     current
    DESCRIPTION
    "Table Entry for Ext: Dolby Digital Surround EX Mode"
    INDEX { slotId }
::= { enc1P949extDolbyDigitalSurroundEXModeTable 1 }

Enc1P949extDolbyDigitalSurroundEXModeEntry ::= SEQUENCE {
    enc1P949extDolbyDigitalSurroundEXModeValue    Enc1E89enumObj
}

enc1P949extDolbyDigitalSurroundEXModeValue OBJECT-TYPE
    SYNTAX     Enc1E89enumObj
    MAX-ACCESS read-write
    STATUS     current
    DESCRIPTION
    "Indicates whether the source material is a 5.1 channel Dolby Digital Surround EX encoding."
::= { enc1P949extDolbyDigitalSurroundEXModeEntry 1 }

enc1P950extA-to-DTypeTable OBJECT-TYPE
    SYNTAX SEQUENCE OF Enc1P950extA-to-DTypeEntry
    MAX-ACCESS not-accessible
    STATUS     current
    DESCRIPTION
    "
    Name      : Ext: A-to-D Type
    Menu Path : /Audio/Metadata Generator 1
    Details   : Indicates the type of A/D converter used to capture the program.
    "
::= { enc1Params 950 }

enc1P950extA-to-DTypeEntry OBJECT-TYPE
    SYNTAX Enc1P950extA-to-DTypeEntry
    MAX-ACCESS not-accessible
    STATUS     current
    DESCRIPTION
    "Table Entry for Ext: A-to-D Type"
    INDEX { slotId }
::= { enc1P950extA-to-DTypeTable 1 }

Enc1P950extA-to-DTypeEntry ::= SEQUENCE {
    enc1P950extA-to-DTypeValue    Enc1E93enumObj
}

enc1P950extA-to-DTypeValue OBJECT-TYPE
    SYNTAX     Enc1E93enumObj
    MAX-ACCESS read-write
    STATUS     current
    DESCRIPTION
    "Indicates the type of A/D converter used to capture the program."
::= { enc1P950extA-to-DTypeEntry 1 }

enc1P951dchigh-PassFilterTable OBJECT-TYPE
    SYNTAX SEQUENCE OF Enc1P951dchigh-PassFilterEntry
    MAX-ACCESS not-accessible
    STATUS     current
    DESCRIPTION
    "
    Name      : DC High-Pass Filter
    Menu Path : /Audio/Metadata Generator 1
    Details   : Applies a DC-blocking 3 Hz high-pass filter.
    "
::= { enc1Params 951 }

enc1P951dchigh-PassFilterEntry OBJECT-TYPE
    SYNTAX Enc1P951dchigh-PassFilterEntry
    MAX-ACCESS not-accessible
    STATUS     current
    DESCRIPTION
    "Table Entry for DC High-Pass Filter"
    INDEX { slotId }
::= { enc1P951dchigh-PassFilterTable 1 }

Enc1P951dchigh-PassFilterEntry ::= SEQUENCE {
    enc1P951dchigh-PassFilterValue    Enc1E0enumObj
}

enc1P951dchigh-PassFilterValue OBJECT-TYPE
    SYNTAX     Enc1E0enumObj
    MAX-ACCESS read-write
    STATUS     current
    DESCRIPTION
    "Applies a DC-blocking 3 Hz high-pass filter."
::= { enc1P951dchigh-PassFilterEntry 1 }

enc1P952low-PassFilterTable OBJECT-TYPE
    SYNTAX SEQUENCE OF Enc1P952low-PassFilterEntry
    MAX-ACCESS not-accessible
    STATUS     current
    DESCRIPTION
    "
    Name      : Low-Pass Filter
    Menu Path : /Audio/Metadata Generator 1
    Details   : Applies a low-pass filter to remove unencoded frequencies.
    "
::= { enc1Params 952 }

enc1P952low-PassFilterEntry OBJECT-TYPE
    SYNTAX Enc1P952low-PassFilterEntry
    MAX-ACCESS not-accessible
    STATUS     current
    DESCRIPTION
    "Table Entry for Low-Pass Filter"
    INDEX { slotId }
::= { enc1P952low-PassFilterTable 1 }

Enc1P952low-PassFilterEntry ::= SEQUENCE {
    enc1P952low-PassFilterValue    Enc1E0enumObj
}

enc1P952low-PassFilterValue OBJECT-TYPE
    SYNTAX     Enc1E0enumObj
    MAX-ACCESS read-write
    STATUS     current
    DESCRIPTION
    "Applies a low-pass filter to remove unencoded frequencies."
::= { enc1P952low-PassFilterEntry 1 }

enc1P953lfelow-PassFilterTable OBJECT-TYPE
    SYNTAX SEQUENCE OF Enc1P953lfelow-PassFilterEntry
    MAX-ACCESS not-accessible
    STATUS     current
    DESCRIPTION
    "
    Name      : LFE Low-Pass Filter
    Menu Path : /Audio/Metadata Generator 1
    Details   : Applies a 120 Hz low-pass filter to the LFE channel (if present) prior to encoding.
    "
::= { enc1Params 953 }

enc1P953lfelow-PassFilterEntry OBJECT-TYPE
    SYNTAX Enc1P953lfelow-PassFilterEntry
    MAX-ACCESS not-accessible
    STATUS     current
    DESCRIPTION
    "Table Entry for LFE Low-Pass Filter"
    INDEX { slotId }
::= { enc1P953lfelow-PassFilterTable 1 }

Enc1P953lfelow-PassFilterEntry ::= SEQUENCE {
    enc1P953lfelow-PassFilterValue    Enc1E0enumObj
}

enc1P953lfelow-PassFilterValue OBJECT-TYPE
    SYNTAX     Enc1E0enumObj
    MAX-ACCESS read-write
    STATUS     current
    DESCRIPTION
    "Applies a 120 Hz low-pass filter to the LFE channel (if present) prior to encoding."
::= { enc1P953lfelow-PassFilterEntry 1 }

enc1P954surroundChannelPhaseShiftTable OBJECT-TYPE
    SYNTAX SEQUENCE OF Enc1P954surroundChannelPhaseShiftEntry
    MAX-ACCESS not-accessible
    STATUS     current
    DESCRIPTION
    "
    Name      : Surround Channel Phase Shift
    Menu Path : /Audio/Metadata Generator 1
    Details   : Applies a 90-degree phase shift to the surround channel(s) (useful for Lt/Rt downmix).
    "
::= { enc1Params 954 }

enc1P954surroundChannelPhaseShiftEntry OBJECT-TYPE
    SYNTAX Enc1P954surroundChannelPhaseShiftEntry
    MAX-ACCESS not-accessible
    STATUS     current
    DESCRIPTION
    "Table Entry for Surround Channel Phase Shift"
    INDEX { slotId }
::= { enc1P954surroundChannelPhaseShiftTable 1 }

Enc1P954surroundChannelPhaseShiftEntry ::= SEQUENCE {
    enc1P954surroundChannelPhaseShiftValue    Enc1E0enumObj
}

enc1P954surroundChannelPhaseShiftValue OBJECT-TYPE
    SYNTAX     Enc1E0enumObj
    MAX-ACCESS read-write
    STATUS     current
    DESCRIPTION
    "Applies a 90-degree phase shift to the surround channel(s) (useful for Lt/Rt downmix)."
::= { enc1P954surroundChannelPhaseShiftEntry 1 }

enc1P955surroundChannelAttenuationTable OBJECT-TYPE
    SYNTAX SEQUENCE OF Enc1P955surroundChannelAttenuationEntry
    MAX-ACCESS not-accessible
    STATUS     current
    DESCRIPTION
    "
    Name      : Surround Channel Attenuation
    Menu Path : /Audio/Metadata Generator 1
    Details   : Applies 3 dB of additional attenuation to the surround channel(s) (for older film formats).
    "
::= { enc1Params 955 }

enc1P955surroundChannelAttenuationEntry OBJECT-TYPE
    SYNTAX Enc1P955surroundChannelAttenuationEntry
    MAX-ACCESS not-accessible
    STATUS     current
    DESCRIPTION
    "Table Entry for Surround Channel Attenuation"
    INDEX { slotId }
::= { enc1P955surroundChannelAttenuationTable 1 }

Enc1P955surroundChannelAttenuationEntry ::= SEQUENCE {
    enc1P955surroundChannelAttenuationValue    Enc1E0enumObj
}

enc1P955surroundChannelAttenuationValue OBJECT-TYPE
    SYNTAX     Enc1E0enumObj
    MAX-ACCESS read-write
    STATUS     current
    DESCRIPTION
    "Applies 3 dB of additional attenuation to the surround channel(s) (for older film formats)."
::= { enc1P955surroundChannelAttenuationEntry 1 }

enc1P956rfmodeDynamicRangeProfileTable OBJECT-TYPE
    SYNTAX SEQUENCE OF Enc1P956rfmodeDynamicRangeProfileEntry
    MAX-ACCESS not-accessible
    STATUS     current
    DESCRIPTION
    "
    Name      : RF Mode Dynamic Range Profile
    Menu Path : /Audio/Metadata Generator 1
    Details   : Specifies the dynamic range compression profile for RF output at the decoder (analog TV signal).
    "
::= { enc1Params 956 }

enc1P956rfmodeDynamicRangeProfileEntry OBJECT-TYPE
    SYNTAX Enc1P956rfmodeDynamicRangeProfileEntry
    MAX-ACCESS not-accessible
    STATUS     current
    DESCRIPTION
    "Table Entry for RF Mode Dynamic Range Profile"
    INDEX { slotId }
::= { enc1P956rfmodeDynamicRangeProfileTable 1 }

Enc1P956rfmodeDynamicRangeProfileEntry ::= SEQUENCE {
    enc1P956rfmodeDynamicRangeProfileValue    Enc1E95enumObj
}

enc1P956rfmodeDynamicRangeProfileValue OBJECT-TYPE
    SYNTAX     Enc1E95enumObj
    MAX-ACCESS read-write
    STATUS     current
    DESCRIPTION
    "Specifies the dynamic range compression profile for RF output at the decoder (analog TV signal)."
::= { enc1P956rfmodeDynamicRangeProfileEntry 1 }

enc1P957lineModeDynamicRangeProfileTable OBJECT-TYPE
    SYNTAX SEQUENCE OF Enc1P957lineModeDynamicRangeProfileEntry
    MAX-ACCESS not-accessible
    STATUS     current
    DESCRIPTION
    "
    Name      : Line Mode Dynamic Range Profile
    Menu Path : /Audio/Metadata Generator 1
    Details   : Specifies the dynamic range compression profile for line output at the decoder.
    "
::= { enc1Params 957 }

enc1P957lineModeDynamicRangeProfileEntry OBJECT-TYPE
    SYNTAX Enc1P957lineModeDynamicRangeProfileEntry
    MAX-ACCESS not-accessible
    STATUS     current
    DESCRIPTION
    "Table Entry for Line Mode Dynamic Range Profile"
    INDEX { slotId }
::= { enc1P957lineModeDynamicRangeProfileTable 1 }

Enc1P957lineModeDynamicRangeProfileEntry ::= SEQUENCE {
    enc1P957lineModeDynamicRangeProfileValue    Enc1E95enumObj
}

enc1P957lineModeDynamicRangeProfileValue OBJECT-TYPE
    SYNTAX     Enc1E95enumObj
    MAX-ACCESS read-write
    STATUS     current
    DESCRIPTION
    "Specifies the dynamic range compression profile for line output at the decoder."
::= { enc1P957lineModeDynamicRangeProfileEntry 1 }

enc1P958programSelectTable OBJECT-TYPE
    SYNTAX SEQUENCE OF Enc1P958programSelectEntry
    MAX-ACCESS not-accessible
    STATUS     current
    DESCRIPTION
    "
    Name      : Program Select
    Menu Path : /Audio/Metadata Generator 2
    Details   : Select one of eight audio metadata programs to display/modify.
    "
::= { enc1Params 958 }

enc1P958programSelectEntry OBJECT-TYPE
    SYNTAX Enc1P958programSelectEntry
    MAX-ACCESS not-accessible
    STATUS     current
    DESCRIPTION
    "Table Entry for Program Select"
    INDEX { slotId }
::= { enc1P958programSelectTable 1 }

Enc1P958programSelectEntry ::= SEQUENCE {
    enc1P958programSelectValue    Enc1E97enumObj
}

enc1P958programSelectValue OBJECT-TYPE
    SYNTAX     Enc1E97enumObj
    MAX-ACCESS read-write
    STATUS     current
    DESCRIPTION
    "Select one of eight audio metadata programs to display/modify."
::= { enc1P958programSelectEntry 1 }

enc1P960bitstreamModeTable OBJECT-TYPE
    SYNTAX SEQUENCE OF Enc1P960bitstreamModeEntry
    MAX-ACCESS not-accessible
    STATUS     current
    DESCRIPTION
    "
    Name      : Bitstream Mode
    Menu Path : /Audio/Metadata Generator 2
    Details   : Describes the audio service contained within the Dolby Digital bitstream.
    "
::= { enc1Params 960 }

enc1P960bitstreamModeEntry OBJECT-TYPE
    SYNTAX Enc1P960bitstreamModeEntry
    MAX-ACCESS not-accessible
    STATUS     current
    DESCRIPTION
    "Table Entry for Bitstream Mode"
    INDEX { slotId }
::= { enc1P960bitstreamModeTable 1 }

Enc1P960bitstreamModeEntry ::= SEQUENCE {
    enc1P960bitstreamModeValue    Enc1E85enumObj
}

enc1P960bitstreamModeValue OBJECT-TYPE
    SYNTAX     Enc1E85enumObj
    MAX-ACCESS read-write
    STATUS     current
    DESCRIPTION
    "Describes the audio service contained within the Dolby Digital bitstream."
::= { enc1P960bitstreamModeEntry 1 }

enc1P961codingModeTable OBJECT-TYPE
    SYNTAX SEQUENCE OF Enc1P961codingModeEntry
    MAX-ACCESS not-accessible
    STATUS     current
    DESCRIPTION
    "
    Name      : Coding Mode
    Menu Path : /Audio/Metadata Generator 2
    Details   : Indicates the active channels within the encoded bitstream.
    "
::= { enc1Params 961 }

enc1P961codingModeEntry OBJECT-TYPE
    SYNTAX Enc1P961codingModeEntry
    MAX-ACCESS not-accessible
    STATUS     current
    DESCRIPTION
    "Table Entry for Coding Mode"
    INDEX { slotId }
::= { enc1P961codingModeTable 1 }

Enc1P961codingModeEntry ::= SEQUENCE {
    enc1P961codingModeValue    Enc1E86enumObj
}

enc1P961codingModeValue OBJECT-TYPE
    SYNTAX     Enc1E86enumObj
    MAX-ACCESS read-write
    STATUS     current
    DESCRIPTION
    "Indicates the active channels within the encoded bitstream."
::= { enc1P961codingModeEntry 1 }

enc1P962centerMixLevelTable OBJECT-TYPE
    SYNTAX SEQUENCE OF Enc1P962centerMixLevelEntry
    MAX-ACCESS not-accessible
    STATUS     current
    DESCRIPTION
    "
    Name      : Center Mix Level
    Menu Path : /Audio/Metadata Generator 2
    Details   : Nominal level for center channel in a stereo downmix.
    "
::= { enc1Params 962 }

enc1P962centerMixLevelEntry OBJECT-TYPE
    SYNTAX Enc1P962centerMixLevelEntry
    MAX-ACCESS not-accessible
    STATUS     current
    DESCRIPTION
    "Table Entry for Center Mix Level"
    INDEX { slotId }
::= { enc1P962centerMixLevelTable 1 }

Enc1P962centerMixLevelEntry ::= SEQUENCE {
    enc1P962centerMixLevelValue    Enc1E87enumObj
}

enc1P962centerMixLevelValue OBJECT-TYPE
    SYNTAX     Enc1E87enumObj
    MAX-ACCESS read-write
    STATUS     current
    DESCRIPTION
    "Nominal level for center channel in a stereo downmix."
::= { enc1P962centerMixLevelEntry 1 }

enc1P963surroundMixLevelTable OBJECT-TYPE
    SYNTAX SEQUENCE OF Enc1P963surroundMixLevelEntry
    MAX-ACCESS not-accessible
    STATUS     current
    DESCRIPTION
    "
    Name      : Surround Mix Level
    Menu Path : /Audio/Metadata Generator 2
    Details   : Nominal level for surround channel(s) in a stereo downmix.
    "
::= { enc1Params 963 }

enc1P963surroundMixLevelEntry OBJECT-TYPE
    SYNTAX Enc1P963surroundMixLevelEntry
    MAX-ACCESS not-accessible
    STATUS     current
    DESCRIPTION
    "Table Entry for Surround Mix Level"
    INDEX { slotId }
::= { enc1P963surroundMixLevelTable 1 }

Enc1P963surroundMixLevelEntry ::= SEQUENCE {
    enc1P963surroundMixLevelValue    Enc1E88enumObj
}

enc1P963surroundMixLevelValue OBJECT-TYPE
    SYNTAX     Enc1E88enumObj
    MAX-ACCESS read-write
    STATUS     current
    DESCRIPTION
    "Nominal level for surround channel(s) in a stereo downmix."
::= { enc1P963surroundMixLevelEntry 1 }

enc1P964dolbySurroundModeTable OBJECT-TYPE
    SYNTAX SEQUENCE OF Enc1P964dolbySurroundModeEntry
    MAX-ACCESS not-accessible
    STATUS     current
    DESCRIPTION
    "
    Name      : Dolby Surround Mode
    Menu Path : /Audio/Metadata Generator 2
    Details   : Indicates whether this is a 2 channel Dolby Surround encoding intended for a Dolby Pro Logic decoder.
    "
::= { enc1Params 964 }

enc1P964dolbySurroundModeEntry OBJECT-TYPE
    SYNTAX Enc1P964dolbySurroundModeEntry
    MAX-ACCESS not-accessible
    STATUS     current
    DESCRIPTION
    "Table Entry for Dolby Surround Mode"
    INDEX { slotId }
::= { enc1P964dolbySurroundModeTable 1 }

Enc1P964dolbySurroundModeEntry ::= SEQUENCE {
    enc1P964dolbySurroundModeValue    Enc1E89enumObj
}

enc1P964dolbySurroundModeValue OBJECT-TYPE
    SYNTAX     Enc1E89enumObj
    MAX-ACCESS read-write
    STATUS     current
    DESCRIPTION
    "Indicates whether this is a 2 channel Dolby Surround encoding intended for a Dolby Pro Logic decoder."
::= { enc1P964dolbySurroundModeEntry 1 }

enc1P965lfechannelTable OBJECT-TYPE
    SYNTAX SEQUENCE OF Enc1P965lfechannelEntry
    MAX-ACCESS not-accessible
    STATUS     current
    DESCRIPTION
    "
    Name      : LFE Channel
    Menu Path : /Audio/Metadata Generator 2
    Details   : Indicates whether a Low Frequency Effects channel is present.
    "
::= { enc1Params 965 }

enc1P965lfechannelEntry OBJECT-TYPE
    SYNTAX Enc1P965lfechannelEntry
    MAX-ACCESS not-accessible
    STATUS     current
    DESCRIPTION
    "Table Entry for LFE Channel"
    INDEX { slotId }
::= { enc1P965lfechannelTable 1 }

Enc1P965lfechannelEntry ::= SEQUENCE {
    enc1P965lfechannelValue    Enc1E1enumObj
}

enc1P965lfechannelValue OBJECT-TYPE
    SYNTAX     Enc1E1enumObj
    MAX-ACCESS read-write
    STATUS     current
    DESCRIPTION
    "Indicates whether a Low Frequency Effects channel is present."
::= { enc1P965lfechannelEntry 1 }

enc1P966dialogNormalizationTable OBJECT-TYPE
    SYNTAX SEQUENCE OF Enc1P966dialogNormalizationEntry
    MAX-ACCESS not-accessible
    STATUS     current
    DESCRIPTION
    "
    Name      : Dialog Normalization
    Menu Path : /Audio/Metadata Generator 2
    Units     : dB
    Precision : 0
    Low Range : -31
    High Range: -1
    Details   : Specifies the long-term A-weighted average level of dialogue, Leq(A), equivalent to dBEq/LKFS.

     NOTE: Precision/Units/Ranges represent the state of the
           parameter during the MIB generation, and does not
           neccessary reflect the current state of the parameter
    "
::= { enc1Params 966 }

enc1P966dialogNormalizationEntry OBJECT-TYPE
    SYNTAX Enc1P966dialogNormalizationEntry
    MAX-ACCESS not-accessible
    STATUS     current
    DESCRIPTION
    "Table Entry for Dialog Normalization"
    INDEX { slotId }
::= { enc1P966dialogNormalizationTable 1 }

Enc1P966dialogNormalizationEntry ::= SEQUENCE {
    enc1P966dialogNormalizationValue    INTEGER
}

enc1P966dialogNormalizationValue OBJECT-TYPE
    SYNTAX     INTEGER
    MAX-ACCESS read-write
    STATUS     current
    DESCRIPTION
    "Specifies the long-term A-weighted average level of dialogue, Leq(A), equivalent to dBEq/LKFS."
::= { enc1P966dialogNormalizationEntry 1 }

enc1P967audioProductionInfoTable OBJECT-TYPE
    SYNTAX SEQUENCE OF Enc1P967audioProductionInfoEntry
    MAX-ACCESS not-accessible
    STATUS     current
    DESCRIPTION
    "
    Name      : Audio Production Info
    Menu Path : /Audio/Metadata Generator 2
    Details   : Indicates if audio production parameters (Mix Level and Room Type) are specified.
    "
::= { enc1Params 967 }

enc1P967audioProductionInfoEntry OBJECT-TYPE
    SYNTAX Enc1P967audioProductionInfoEntry
    MAX-ACCESS not-accessible
    STATUS     current
    DESCRIPTION
    "Table Entry for Audio Production Info"
    INDEX { slotId }
::= { enc1P967audioProductionInfoTable 1 }

Enc1P967audioProductionInfoEntry ::= SEQUENCE {
    enc1P967audioProductionInfoValue    Enc1E11enumObj
}

enc1P967audioProductionInfoValue OBJECT-TYPE
    SYNTAX     Enc1E11enumObj
    MAX-ACCESS read-write
    STATUS     current
    DESCRIPTION
    "Indicates if audio production parameters (Mix Level and Room Type) are specified."
::= { enc1P967audioProductionInfoEntry 1 }

enc1P968mixLevelTable OBJECT-TYPE
    SYNTAX SEQUENCE OF Enc1P968mixLevelEntry
    MAX-ACCESS not-accessible
    STATUS     current
    DESCRIPTION
    "
    Name      : Mix Level
    Menu Path : /Audio/Metadata Generator 2
    Units     : dB
    Precision : 0
    Low Range : 80
    High Range: 111
    Details   : Specifies the peak sound pressure level (SPL) used during final audio mixing.

     NOTE: Precision/Units/Ranges represent the state of the
           parameter during the MIB generation, and does not
           neccessary reflect the current state of the parameter
    "
::= { enc1Params 968 }

enc1P968mixLevelEntry OBJECT-TYPE
    SYNTAX Enc1P968mixLevelEntry
    MAX-ACCESS not-accessible
    STATUS     current
    DESCRIPTION
    "Table Entry for Mix Level"
    INDEX { slotId }
::= { enc1P968mixLevelTable 1 }

Enc1P968mixLevelEntry ::= SEQUENCE {
    enc1P968mixLevelValue    INTEGER
}

enc1P968mixLevelValue OBJECT-TYPE
    SYNTAX     INTEGER
    MAX-ACCESS read-write
    STATUS     current
    DESCRIPTION
    "Specifies the peak sound pressure level (SPL) used during final audio mixing."
::= { enc1P968mixLevelEntry 1 }

enc1P969roomTypeTable OBJECT-TYPE
    SYNTAX SEQUENCE OF Enc1P969roomTypeEntry
    MAX-ACCESS not-accessible
    STATUS     current
    DESCRIPTION
    "
    Name      : Room Type
    Menu Path : /Audio/Metadata Generator 2
    Details   : Describes equalization used during the final mixing. Large is X-curve, small is flat.
    "
::= { enc1Params 969 }

enc1P969roomTypeEntry OBJECT-TYPE
    SYNTAX Enc1P969roomTypeEntry
    MAX-ACCESS not-accessible
    STATUS     current
    DESCRIPTION
    "Table Entry for Room Type"
    INDEX { slotId }
::= { enc1P969roomTypeTable 1 }

Enc1P969roomTypeEntry ::= SEQUENCE {
    enc1P969roomTypeValue    Enc1E96enumObj
}

enc1P969roomTypeValue OBJECT-TYPE
    SYNTAX     Enc1E96enumObj
    MAX-ACCESS read-write
    STATUS     current
    DESCRIPTION
    "Describes equalization used during the final mixing. Large is X-curve, small is flat."
::= { enc1P969roomTypeEntry 1 }

enc1P970copyrightProtectedTable OBJECT-TYPE
    SYNTAX SEQUENCE OF Enc1P970copyrightProtectedEntry
    MAX-ACCESS not-accessible
    STATUS     current
    DESCRIPTION
    "
    Name      : Copyright Protected
    Menu Path : /Audio/Metadata Generator 2
    Details   : Indicates whether the source material is copyright protected.
    "
::= { enc1Params 970 }

enc1P970copyrightProtectedEntry OBJECT-TYPE
    SYNTAX Enc1P970copyrightProtectedEntry
    MAX-ACCESS not-accessible
    STATUS     current
    DESCRIPTION
    "Table Entry for Copyright Protected"
    INDEX { slotId }
::= { enc1P970copyrightProtectedTable 1 }

Enc1P970copyrightProtectedEntry ::= SEQUENCE {
    enc1P970copyrightProtectedValue    Enc1E11enumObj
}

enc1P970copyrightProtectedValue OBJECT-TYPE
    SYNTAX     Enc1E11enumObj
    MAX-ACCESS read-write
    STATUS     current
    DESCRIPTION
    "Indicates whether the source material is copyright protected."
::= { enc1P970copyrightProtectedEntry 1 }

enc1P971originalBitstreamTable OBJECT-TYPE
    SYNTAX SEQUENCE OF Enc1P971originalBitstreamEntry
    MAX-ACCESS not-accessible
    STATUS     current
    DESCRIPTION
    "
    Name      : Original Bitstream
    Menu Path : /Audio/Metadata Generator 2
    Details   : Indicates whether the source material is the master version or a copy.
    "
::= { enc1Params 971 }

enc1P971originalBitstreamEntry OBJECT-TYPE
    SYNTAX Enc1P971originalBitstreamEntry
    MAX-ACCESS not-accessible
    STATUS     current
    DESCRIPTION
    "Table Entry for Original Bitstream"
    INDEX { slotId }
::= { enc1P971originalBitstreamTable 1 }

Enc1P971originalBitstreamEntry ::= SEQUENCE {
    enc1P971originalBitstreamValue    Enc1E11enumObj
}

enc1P971originalBitstreamValue OBJECT-TYPE
    SYNTAX     Enc1E11enumObj
    MAX-ACCESS read-write
    STATUS     current
    DESCRIPTION
    "Indicates whether the source material is the master version or a copy."
::= { enc1P971originalBitstreamEntry 1 }

enc1P972extendedBitstreamInformationTable OBJECT-TYPE
    SYNTAX SEQUENCE OF Enc1P972extendedBitstreamInformationEntry
    MAX-ACCESS not-accessible
    STATUS     current
    DESCRIPTION
    "
    Name      : Extended Bitstream Information
    Menu Path : /Audio/Metadata Generator 2
    Details   : Enables extended bitstream parameters (Ext:).
    "
::= { enc1Params 972 }

enc1P972extendedBitstreamInformationEntry OBJECT-TYPE
    SYNTAX Enc1P972extendedBitstreamInformationEntry
    MAX-ACCESS not-accessible
    STATUS     current
    DESCRIPTION
    "Table Entry for Extended Bitstream Information"
    INDEX { slotId }
::= { enc1P972extendedBitstreamInformationTable 1 }

Enc1P972extendedBitstreamInformationEntry ::= SEQUENCE {
    enc1P972extendedBitstreamInformationValue    Enc1E0enumObj
}

enc1P972extendedBitstreamInformationValue OBJECT-TYPE
    SYNTAX     Enc1E0enumObj
    MAX-ACCESS read-write
    STATUS     current
    DESCRIPTION
    "Enables extended bitstream parameters (Ext:)."
::= { enc1P972extendedBitstreamInformationEntry 1 }

enc1P974extPreferredStereoDownmixTable OBJECT-TYPE
    SYNTAX SEQUENCE OF Enc1P974extPreferredStereoDownmixEntry
    MAX-ACCESS not-accessible
    STATUS     current
    DESCRIPTION
    "
    Name      : Ext: Preferred Stereo Downmix
    Menu Path : /Audio/Metadata Generator 2
    Details   : Indicates the preferred type of stereo downmix.
    "
::= { enc1Params 974 }

enc1P974extPreferredStereoDownmixEntry OBJECT-TYPE
    SYNTAX Enc1P974extPreferredStereoDownmixEntry
    MAX-ACCESS not-accessible
    STATUS     current
    DESCRIPTION
    "Table Entry for Ext: Preferred Stereo Downmix"
    INDEX { slotId }
::= { enc1P974extPreferredStereoDownmixTable 1 }

Enc1P974extPreferredStereoDownmixEntry ::= SEQUENCE {
    enc1P974extPreferredStereoDownmixValue    Enc1E90enumObj
}

enc1P974extPreferredStereoDownmixValue OBJECT-TYPE
    SYNTAX     Enc1E90enumObj
    MAX-ACCESS read-write
    STATUS     current
    DESCRIPTION
    "Indicates the preferred type of stereo downmix."
::= { enc1P974extPreferredStereoDownmixEntry 1 }

enc1P975extLtRtCenterMixLevelTable OBJECT-TYPE
    SYNTAX SEQUENCE OF Enc1P975extLtRtCenterMixLevelEntry
    MAX-ACCESS not-accessible
    STATUS     current
    DESCRIPTION
    "
    Name      : Ext: LtRt Center Mix Level
    Menu Path : /Audio/Metadata Generator 2
    Details   : Level shift applied to the center channel during an Lt/Rt downmix.
    "
::= { enc1Params 975 }

enc1P975extLtRtCenterMixLevelEntry OBJECT-TYPE
    SYNTAX Enc1P975extLtRtCenterMixLevelEntry
    MAX-ACCESS not-accessible
    STATUS     current
    DESCRIPTION
    "Table Entry for Ext: LtRt Center Mix Level"
    INDEX { slotId }
::= { enc1P975extLtRtCenterMixLevelTable 1 }

Enc1P975extLtRtCenterMixLevelEntry ::= SEQUENCE {
    enc1P975extLtRtCenterMixLevelValue    Enc1E91enumObj
}

enc1P975extLtRtCenterMixLevelValue OBJECT-TYPE
    SYNTAX     Enc1E91enumObj
    MAX-ACCESS read-write
    STATUS     current
    DESCRIPTION
    "Level shift applied to the center channel during an Lt/Rt downmix."
::= { enc1P975extLtRtCenterMixLevelEntry 1 }

enc1P976extLtRtSurroundMixLevelTable OBJECT-TYPE
    SYNTAX SEQUENCE OF Enc1P976extLtRtSurroundMixLevelEntry
    MAX-ACCESS not-accessible
    STATUS     current
    DESCRIPTION
    "
    Name      : Ext: LtRt Surround Mix Level
    Menu Path : /Audio/Metadata Generator 2
    Details   : Level shift applied to the surround channel(s) during an Lt/Rt downmix.
    "
::= { enc1Params 976 }

enc1P976extLtRtSurroundMixLevelEntry OBJECT-TYPE
    SYNTAX Enc1P976extLtRtSurroundMixLevelEntry
    MAX-ACCESS not-accessible
    STATUS     current
    DESCRIPTION
    "Table Entry for Ext: LtRt Surround Mix Level"
    INDEX { slotId }
::= { enc1P976extLtRtSurroundMixLevelTable 1 }

Enc1P976extLtRtSurroundMixLevelEntry ::= SEQUENCE {
    enc1P976extLtRtSurroundMixLevelValue    Enc1E92enumObj
}

enc1P976extLtRtSurroundMixLevelValue OBJECT-TYPE
    SYNTAX     Enc1E92enumObj
    MAX-ACCESS read-write
    STATUS     current
    DESCRIPTION
    "Level shift applied to the surround channel(s) during an Lt/Rt downmix."
::= { enc1P976extLtRtSurroundMixLevelEntry 1 }

enc1P977extLoRoCenterMixLevelTable OBJECT-TYPE
    SYNTAX SEQUENCE OF Enc1P977extLoRoCenterMixLevelEntry
    MAX-ACCESS not-accessible
    STATUS     current
    DESCRIPTION
    "
    Name      : Ext: LoRo Center Mix Level
    Menu Path : /Audio/Metadata Generator 2
    Details   : Level shift applied to the center channel during an Lo/Ro downmix. (Replaces Center Mix Level)
    "
::= { enc1Params 977 }

enc1P977extLoRoCenterMixLevelEntry OBJECT-TYPE
    SYNTAX Enc1P977extLoRoCenterMixLevelEntry
    MAX-ACCESS not-accessible
    STATUS     current
    DESCRIPTION
    "Table Entry for Ext: LoRo Center Mix Level"
    INDEX { slotId }
::= { enc1P977extLoRoCenterMixLevelTable 1 }

Enc1P977extLoRoCenterMixLevelEntry ::= SEQUENCE {
    enc1P977extLoRoCenterMixLevelValue    Enc1E91enumObj
}

enc1P977extLoRoCenterMixLevelValue OBJECT-TYPE
    SYNTAX     Enc1E91enumObj
    MAX-ACCESS read-write
    STATUS     current
    DESCRIPTION
    "Level shift applied to the center channel during an Lo/Ro downmix. (Replaces Center Mix Level)"
::= { enc1P977extLoRoCenterMixLevelEntry 1 }

enc1P978extLoRoSurroundMixLevelTable OBJECT-TYPE
    SYNTAX SEQUENCE OF Enc1P978extLoRoSurroundMixLevelEntry
    MAX-ACCESS not-accessible
    STATUS     current
    DESCRIPTION
    "
    Name      : Ext: LoRo Surround Mix Level
    Menu Path : /Audio/Metadata Generator 2
    Details   : Level shift applied to the surround channel(s) during an Lo/Ro downmix.
    "
::= { enc1Params 978 }

enc1P978extLoRoSurroundMixLevelEntry OBJECT-TYPE
    SYNTAX Enc1P978extLoRoSurroundMixLevelEntry
    MAX-ACCESS not-accessible
    STATUS     current
    DESCRIPTION
    "Table Entry for Ext: LoRo Surround Mix Level"
    INDEX { slotId }
::= { enc1P978extLoRoSurroundMixLevelTable 1 }

Enc1P978extLoRoSurroundMixLevelEntry ::= SEQUENCE {
    enc1P978extLoRoSurroundMixLevelValue    Enc1E92enumObj
}

enc1P978extLoRoSurroundMixLevelValue OBJECT-TYPE
    SYNTAX     Enc1E92enumObj
    MAX-ACCESS read-write
    STATUS     current
    DESCRIPTION
    "Level shift applied to the surround channel(s) during an Lo/Ro downmix."
::= { enc1P978extLoRoSurroundMixLevelEntry 1 }

enc1P980extDolbyDigitalSurroundEXModeTable OBJECT-TYPE
    SYNTAX SEQUENCE OF Enc1P980extDolbyDigitalSurroundEXModeEntry
    MAX-ACCESS not-accessible
    STATUS     current
    DESCRIPTION
    "
    Name      : Ext: Dolby Digital Surround EX Mode
    Menu Path : /Audio/Metadata Generator 2
    Details   : Indicates whether the source material is a 5.1 channel Dolby Digital Surround EX encoding.
    "
::= { enc1Params 980 }

enc1P980extDolbyDigitalSurroundEXModeEntry OBJECT-TYPE
    SYNTAX Enc1P980extDolbyDigitalSurroundEXModeEntry
    MAX-ACCESS not-accessible
    STATUS     current
    DESCRIPTION
    "Table Entry for Ext: Dolby Digital Surround EX Mode"
    INDEX { slotId }
::= { enc1P980extDolbyDigitalSurroundEXModeTable 1 }

Enc1P980extDolbyDigitalSurroundEXModeEntry ::= SEQUENCE {
    enc1P980extDolbyDigitalSurroundEXModeValue    Enc1E89enumObj
}

enc1P980extDolbyDigitalSurroundEXModeValue OBJECT-TYPE
    SYNTAX     Enc1E89enumObj
    MAX-ACCESS read-write
    STATUS     current
    DESCRIPTION
    "Indicates whether the source material is a 5.1 channel Dolby Digital Surround EX encoding."
::= { enc1P980extDolbyDigitalSurroundEXModeEntry 1 }

enc1P981extA-to-DTypeTable OBJECT-TYPE
    SYNTAX SEQUENCE OF Enc1P981extA-to-DTypeEntry
    MAX-ACCESS not-accessible
    STATUS     current
    DESCRIPTION
    "
    Name      : Ext A-to-D Type
    Menu Path : /Audio/Metadata Generator 2
    Details   : Indicates the type of A/D converter used to capture the program.
    "
::= { enc1Params 981 }

enc1P981extA-to-DTypeEntry OBJECT-TYPE
    SYNTAX Enc1P981extA-to-DTypeEntry
    MAX-ACCESS not-accessible
    STATUS     current
    DESCRIPTION
    "Table Entry for Ext A-to-D Type"
    INDEX { slotId }
::= { enc1P981extA-to-DTypeTable 1 }

Enc1P981extA-to-DTypeEntry ::= SEQUENCE {
    enc1P981extA-to-DTypeValue    Enc1E93enumObj
}

enc1P981extA-to-DTypeValue OBJECT-TYPE
    SYNTAX     Enc1E93enumObj
    MAX-ACCESS read-write
    STATUS     current
    DESCRIPTION
    "Indicates the type of A/D converter used to capture the program."
::= { enc1P981extA-to-DTypeEntry 1 }

enc1P982dchigh-PassFilterTable OBJECT-TYPE
    SYNTAX SEQUENCE OF Enc1P982dchigh-PassFilterEntry
    MAX-ACCESS not-accessible
    STATUS     current
    DESCRIPTION
    "
    Name      : DC High-Pass Filter
    Menu Path : /Audio/Metadata Generator 2
    Details   : Applies a DC-blocking 3 Hz high-pass filter.
    "
::= { enc1Params 982 }

enc1P982dchigh-PassFilterEntry OBJECT-TYPE
    SYNTAX Enc1P982dchigh-PassFilterEntry
    MAX-ACCESS not-accessible
    STATUS     current
    DESCRIPTION
    "Table Entry for DC High-Pass Filter"
    INDEX { slotId }
::= { enc1P982dchigh-PassFilterTable 1 }

Enc1P982dchigh-PassFilterEntry ::= SEQUENCE {
    enc1P982dchigh-PassFilterValue    Enc1E0enumObj
}

enc1P982dchigh-PassFilterValue OBJECT-TYPE
    SYNTAX     Enc1E0enumObj
    MAX-ACCESS read-write
    STATUS     current
    DESCRIPTION
    "Applies a DC-blocking 3 Hz high-pass filter."
::= { enc1P982dchigh-PassFilterEntry 1 }

enc1P983low-PassFilterTable OBJECT-TYPE
    SYNTAX SEQUENCE OF Enc1P983low-PassFilterEntry
    MAX-ACCESS not-accessible
    STATUS     current
    DESCRIPTION
    "
    Name      : Low-Pass Filter
    Menu Path : /Audio/Metadata Generator 2
    Details   : Applies a low-pass filter to remove unencoded frequencies.
    "
::= { enc1Params 983 }

enc1P983low-PassFilterEntry OBJECT-TYPE
    SYNTAX Enc1P983low-PassFilterEntry
    MAX-ACCESS not-accessible
    STATUS     current
    DESCRIPTION
    "Table Entry for Low-Pass Filter"
    INDEX { slotId }
::= { enc1P983low-PassFilterTable 1 }

Enc1P983low-PassFilterEntry ::= SEQUENCE {
    enc1P983low-PassFilterValue    Enc1E0enumObj
}

enc1P983low-PassFilterValue OBJECT-TYPE
    SYNTAX     Enc1E0enumObj
    MAX-ACCESS read-write
    STATUS     current
    DESCRIPTION
    "Applies a low-pass filter to remove unencoded frequencies."
::= { enc1P983low-PassFilterEntry 1 }

enc1P984lfelow-PassFilterTable OBJECT-TYPE
    SYNTAX SEQUENCE OF Enc1P984lfelow-PassFilterEntry
    MAX-ACCESS not-accessible
    STATUS     current
    DESCRIPTION
    "
    Name      : LFE Low-Pass Filter
    Menu Path : /Audio/Metadata Generator 2
    Details   : Applies a 120 Hz low-pass filter to the LFE channel (if present) prior to encoding.
    "
::= { enc1Params 984 }

enc1P984lfelow-PassFilterEntry OBJECT-TYPE
    SYNTAX Enc1P984lfelow-PassFilterEntry
    MAX-ACCESS not-accessible
    STATUS     current
    DESCRIPTION
    "Table Entry for LFE Low-Pass Filter"
    INDEX { slotId }
::= { enc1P984lfelow-PassFilterTable 1 }

Enc1P984lfelow-PassFilterEntry ::= SEQUENCE {
    enc1P984lfelow-PassFilterValue    Enc1E0enumObj
}

enc1P984lfelow-PassFilterValue OBJECT-TYPE
    SYNTAX     Enc1E0enumObj
    MAX-ACCESS read-write
    STATUS     current
    DESCRIPTION
    "Applies a 120 Hz low-pass filter to the LFE channel (if present) prior to encoding."
::= { enc1P984lfelow-PassFilterEntry 1 }

enc1P985surroundChannelPhaseShiftFilterTable OBJECT-TYPE
    SYNTAX SEQUENCE OF Enc1P985surroundChannelPhaseShiftFilterEntry
    MAX-ACCESS not-accessible
    STATUS     current
    DESCRIPTION
    "
    Name      : Surround Channel Phase Shift Filter
    Menu Path : /Audio/Metadata Generator 2
    Details   : Applies a 90-degree phase shift to the surround channel(s) (useful for Lt/Rt downmix).
    "
::= { enc1Params 985 }

enc1P985surroundChannelPhaseShiftFilterEntry OBJECT-TYPE
    SYNTAX Enc1P985surroundChannelPhaseShiftFilterEntry
    MAX-ACCESS not-accessible
    STATUS     current
    DESCRIPTION
    "Table Entry for Surround Channel Phase Shift Filter"
    INDEX { slotId }
::= { enc1P985surroundChannelPhaseShiftFilterTable 1 }

Enc1P985surroundChannelPhaseShiftFilterEntry ::= SEQUENCE {
    enc1P985surroundChannelPhaseShiftFilterValue    Enc1E0enumObj
}

enc1P985surroundChannelPhaseShiftFilterValue OBJECT-TYPE
    SYNTAX     Enc1E0enumObj
    MAX-ACCESS read-write
    STATUS     current
    DESCRIPTION
    "Applies a 90-degree phase shift to the surround channel(s) (useful for Lt/Rt downmix)."
::= { enc1P985surroundChannelPhaseShiftFilterEntry 1 }

enc1P986surroundChannelAttenuationTable OBJECT-TYPE
    SYNTAX SEQUENCE OF Enc1P986surroundChannelAttenuationEntry
    MAX-ACCESS not-accessible
    STATUS     current
    DESCRIPTION
    "
    Name      : Surround Channel Attenuation
    Menu Path : /Audio/Metadata Generator 2
    Details   : Applies 3 dB of additional attenuation to the surround channel(s) (for older film formats).
    "
::= { enc1Params 986 }

enc1P986surroundChannelAttenuationEntry OBJECT-TYPE
    SYNTAX Enc1P986surroundChannelAttenuationEntry
    MAX-ACCESS not-accessible
    STATUS     current
    DESCRIPTION
    "Table Entry for Surround Channel Attenuation"
    INDEX { slotId }
::= { enc1P986surroundChannelAttenuationTable 1 }

Enc1P986surroundChannelAttenuationEntry ::= SEQUENCE {
    enc1P986surroundChannelAttenuationValue    Enc1E0enumObj
}

enc1P986surroundChannelAttenuationValue OBJECT-TYPE
    SYNTAX     Enc1E0enumObj
    MAX-ACCESS read-write
    STATUS     current
    DESCRIPTION
    "Applies 3 dB of additional attenuation to the surround channel(s) (for older film formats)."
::= { enc1P986surroundChannelAttenuationEntry 1 }

enc1P987rfmodeDynamicRangeProfileTable OBJECT-TYPE
    SYNTAX SEQUENCE OF Enc1P987rfmodeDynamicRangeProfileEntry
    MAX-ACCESS not-accessible
    STATUS     current
    DESCRIPTION
    "
    Name      : RF Mode Dynamic Range Profile
    Menu Path : /Audio/Metadata Generator 2
    Details   : Specifies the dynamic range compression profile for RF output at the decoder (analog TV signal).
    "
::= { enc1Params 987 }

enc1P987rfmodeDynamicRangeProfileEntry OBJECT-TYPE
    SYNTAX Enc1P987rfmodeDynamicRangeProfileEntry
    MAX-ACCESS not-accessible
    STATUS     current
    DESCRIPTION
    "Table Entry for RF Mode Dynamic Range Profile"
    INDEX { slotId }
::= { enc1P987rfmodeDynamicRangeProfileTable 1 }

Enc1P987rfmodeDynamicRangeProfileEntry ::= SEQUENCE {
    enc1P987rfmodeDynamicRangeProfileValue    Enc1E95enumObj
}

enc1P987rfmodeDynamicRangeProfileValue OBJECT-TYPE
    SYNTAX     Enc1E95enumObj
    MAX-ACCESS read-write
    STATUS     current
    DESCRIPTION
    "Specifies the dynamic range compression profile for RF output at the decoder (analog TV signal)."
::= { enc1P987rfmodeDynamicRangeProfileEntry 1 }

enc1P988lineModeDynamicRangeProfileTable OBJECT-TYPE
    SYNTAX SEQUENCE OF Enc1P988lineModeDynamicRangeProfileEntry
    MAX-ACCESS not-accessible
    STATUS     current
    DESCRIPTION
    "
    Name      : Line Mode Dynamic Range Profile
    Menu Path : /Audio/Metadata Generator 2
    Details   : Specifies the dynamic range compression profile for line output at the decoder.
    "
::= { enc1Params 988 }

enc1P988lineModeDynamicRangeProfileEntry OBJECT-TYPE
    SYNTAX Enc1P988lineModeDynamicRangeProfileEntry
    MAX-ACCESS not-accessible
    STATUS     current
    DESCRIPTION
    "Table Entry for Line Mode Dynamic Range Profile"
    INDEX { slotId }
::= { enc1P988lineModeDynamicRangeProfileTable 1 }

Enc1P988lineModeDynamicRangeProfileEntry ::= SEQUENCE {
    enc1P988lineModeDynamicRangeProfileValue    Enc1E95enumObj
}

enc1P988lineModeDynamicRangeProfileValue OBJECT-TYPE
    SYNTAX     Enc1E95enumObj
    MAX-ACCESS read-write
    STATUS     current
    DESCRIPTION
    "Specifies the dynamic range compression profile for line output at the decoder."
::= { enc1P988lineModeDynamicRangeProfileEntry 1 }

enc1P989copyrightTable OBJECT-TYPE
    SYNTAX SEQUENCE OF Enc1P989copyrightEntry
    MAX-ACCESS not-accessible
    STATUS     current
    DESCRIPTION
    "
    Name      : Copyright
    Menu Path : /Audio/Audio 1
    Details   : Copyright indication.
    "
::= { enc1Params 989 }

enc1P989copyrightEntry OBJECT-TYPE
    SYNTAX Enc1P989copyrightEntry
    MAX-ACCESS not-accessible
    STATUS     current
    DESCRIPTION
    "Table Entry for Copyright"
    INDEX { slotId }
::= { enc1P989copyrightTable 1 }

Enc1P989copyrightEntry ::= SEQUENCE {
    enc1P989copyrightValue    Enc1E11enumObj
}

enc1P989copyrightValue OBJECT-TYPE
    SYNTAX     Enc1E11enumObj
    MAX-ACCESS read-write
    STATUS     current
    DESCRIPTION
    "Copyright indication."
::= { enc1P989copyrightEntry 1 }

enc1P990originalTable OBJECT-TYPE
    SYNTAX SEQUENCE OF Enc1P990originalEntry
    MAX-ACCESS not-accessible
    STATUS     current
    DESCRIPTION
    "
    Name      : Original
    Menu Path : /Audio/Audio 1
    Details   : Specifies input is an original audio master.
    "
::= { enc1Params 990 }

enc1P990originalEntry OBJECT-TYPE
    SYNTAX Enc1P990originalEntry
    MAX-ACCESS not-accessible
    STATUS     current
    DESCRIPTION
    "Table Entry for Original"
    INDEX { slotId }
::= { enc1P990originalTable 1 }

Enc1P990originalEntry ::= SEQUENCE {
    enc1P990originalValue    Enc1E11enumObj
}

enc1P990originalValue OBJECT-TYPE
    SYNTAX     Enc1E11enumObj
    MAX-ACCESS read-write
    STATUS     current
    DESCRIPTION
    "Specifies input is an original audio master."
::= { enc1P990originalEntry 1 }

enc1P991copyrightTable OBJECT-TYPE
    SYNTAX SEQUENCE OF Enc1P991copyrightEntry
    MAX-ACCESS not-accessible
    STATUS     current
    DESCRIPTION
    "
    Name      : Copyright
    Menu Path : /Audio/Audio 2
    Details   : Copyright indication.
    "
::= { enc1Params 991 }

enc1P991copyrightEntry OBJECT-TYPE
    SYNTAX Enc1P991copyrightEntry
    MAX-ACCESS not-accessible
    STATUS     current
    DESCRIPTION
    "Table Entry for Copyright"
    INDEX { slotId }
::= { enc1P991copyrightTable 1 }

Enc1P991copyrightEntry ::= SEQUENCE {
    enc1P991copyrightValue    Enc1E11enumObj
}

enc1P991copyrightValue OBJECT-TYPE
    SYNTAX     Enc1E11enumObj
    MAX-ACCESS read-write
    STATUS     current
    DESCRIPTION
    "Copyright indication."
::= { enc1P991copyrightEntry 1 }

enc1P992originalTable OBJECT-TYPE
    SYNTAX SEQUENCE OF Enc1P992originalEntry
    MAX-ACCESS not-accessible
    STATUS     current
    DESCRIPTION
    "
    Name      : Original
    Menu Path : /Audio/Audio 2
    Details   : Specifies input is an original audio master.
    "
::= { enc1Params 992 }

enc1P992originalEntry OBJECT-TYPE
    SYNTAX Enc1P992originalEntry
    MAX-ACCESS not-accessible
    STATUS     current
    DESCRIPTION
    "Table Entry for Original"
    INDEX { slotId }
::= { enc1P992originalTable 1 }

Enc1P992originalEntry ::= SEQUENCE {
    enc1P992originalValue    Enc1E11enumObj
}

enc1P992originalValue OBJECT-TYPE
    SYNTAX     Enc1E11enumObj
    MAX-ACCESS read-write
    STATUS     current
    DESCRIPTION
    "Specifies input is an original audio master."
::= { enc1P992originalEntry 1 }

enc1P993copyrightTable OBJECT-TYPE
    SYNTAX SEQUENCE OF Enc1P993copyrightEntry
    MAX-ACCESS not-accessible
    STATUS     current
    DESCRIPTION
    "
    Name      : Copyright
    Menu Path : /Audio/Audio 3
    Details   : Copyright indication.
    "
::= { enc1Params 993 }

enc1P993copyrightEntry OBJECT-TYPE
    SYNTAX Enc1P993copyrightEntry
    MAX-ACCESS not-accessible
    STATUS     current
    DESCRIPTION
    "Table Entry for Copyright"
    INDEX { slotId }
::= { enc1P993copyrightTable 1 }

Enc1P993copyrightEntry ::= SEQUENCE {
    enc1P993copyrightValue    Enc1E11enumObj
}

enc1P993copyrightValue OBJECT-TYPE
    SYNTAX     Enc1E11enumObj
    MAX-ACCESS read-write
    STATUS     current
    DESCRIPTION
    "Copyright indication."
::= { enc1P993copyrightEntry 1 }

enc1P994originalTable OBJECT-TYPE
    SYNTAX SEQUENCE OF Enc1P994originalEntry
    MAX-ACCESS not-accessible
    STATUS     current
    DESCRIPTION
    "
    Name      : Original
    Menu Path : /Audio/Audio 3
    Details   : Specifies input is an original audio master.
    "
::= { enc1Params 994 }

enc1P994originalEntry OBJECT-TYPE
    SYNTAX Enc1P994originalEntry
    MAX-ACCESS not-accessible
    STATUS     current
    DESCRIPTION
    "Table Entry for Original"
    INDEX { slotId }
::= { enc1P994originalTable 1 }

Enc1P994originalEntry ::= SEQUENCE {
    enc1P994originalValue    Enc1E11enumObj
}

enc1P994originalValue OBJECT-TYPE
    SYNTAX     Enc1E11enumObj
    MAX-ACCESS read-write
    STATUS     current
    DESCRIPTION
    "Specifies input is an original audio master."
::= { enc1P994originalEntry 1 }

enc1P995copyrightTable OBJECT-TYPE
    SYNTAX SEQUENCE OF Enc1P995copyrightEntry
    MAX-ACCESS not-accessible
    STATUS     current
    DESCRIPTION
    "
    Name      : Copyright
    Menu Path : /Audio/Audio 4
    Details   : Copyright indication.
    "
::= { enc1Params 995 }

enc1P995copyrightEntry OBJECT-TYPE
    SYNTAX Enc1P995copyrightEntry
    MAX-ACCESS not-accessible
    STATUS     current
    DESCRIPTION
    "Table Entry for Copyright"
    INDEX { slotId }
::= { enc1P995copyrightTable 1 }

Enc1P995copyrightEntry ::= SEQUENCE {
    enc1P995copyrightValue    Enc1E11enumObj
}

enc1P995copyrightValue OBJECT-TYPE
    SYNTAX     Enc1E11enumObj
    MAX-ACCESS read-write
    STATUS     current
    DESCRIPTION
    "Copyright indication."
::= { enc1P995copyrightEntry 1 }

enc1P996originalTable OBJECT-TYPE
    SYNTAX SEQUENCE OF Enc1P996originalEntry
    MAX-ACCESS not-accessible
    STATUS     current
    DESCRIPTION
    "
    Name      : Original
    Menu Path : /Audio/Audio 4
    Details   : Specifies input is an original audio master.
    "
::= { enc1Params 996 }

enc1P996originalEntry OBJECT-TYPE
    SYNTAX Enc1P996originalEntry
    MAX-ACCESS not-accessible
    STATUS     current
    DESCRIPTION
    "Table Entry for Original"
    INDEX { slotId }
::= { enc1P996originalTable 1 }

Enc1P996originalEntry ::= SEQUENCE {
    enc1P996originalValue    Enc1E11enumObj
}

enc1P996originalValue OBJECT-TYPE
    SYNTAX     Enc1E11enumObj
    MAX-ACCESS read-write
    STATUS     current
    DESCRIPTION
    "Specifies input is an original audio master."
::= { enc1P996originalEntry 1 }

enc1P997copyrightTable OBJECT-TYPE
    SYNTAX SEQUENCE OF Enc1P997copyrightEntry
    MAX-ACCESS not-accessible
    STATUS     current
    DESCRIPTION
    "
    Name      : Copyright
    Menu Path : /Audio/Audio 5
    Details   : Copyright indication.
    "
::= { enc1Params 997 }

enc1P997copyrightEntry OBJECT-TYPE
    SYNTAX Enc1P997copyrightEntry
    MAX-ACCESS not-accessible
    STATUS     current
    DESCRIPTION
    "Table Entry for Copyright"
    INDEX { slotId }
::= { enc1P997copyrightTable 1 }

Enc1P997copyrightEntry ::= SEQUENCE {
    enc1P997copyrightValue    Enc1E11enumObj
}

enc1P997copyrightValue OBJECT-TYPE
    SYNTAX     Enc1E11enumObj
    MAX-ACCESS read-write
    STATUS     current
    DESCRIPTION
    "Copyright indication."
::= { enc1P997copyrightEntry 1 }

enc1P998originalTable OBJECT-TYPE
    SYNTAX SEQUENCE OF Enc1P998originalEntry
    MAX-ACCESS not-accessible
    STATUS     current
    DESCRIPTION
    "
    Name      : Original
    Menu Path : /Audio/Audio 5
    Details   : Specifies input is an original audio master.
    "
::= { enc1Params 998 }

enc1P998originalEntry OBJECT-TYPE
    SYNTAX Enc1P998originalEntry
    MAX-ACCESS not-accessible
    STATUS     current
    DESCRIPTION
    "Table Entry for Original"
    INDEX { slotId }
::= { enc1P998originalTable 1 }

Enc1P998originalEntry ::= SEQUENCE {
    enc1P998originalValue    Enc1E11enumObj
}

enc1P998originalValue OBJECT-TYPE
    SYNTAX     Enc1E11enumObj
    MAX-ACCESS read-write
    STATUS     current
    DESCRIPTION
    "Specifies input is an original audio master."
::= { enc1P998originalEntry 1 }

enc1P999copyrightTable OBJECT-TYPE
    SYNTAX SEQUENCE OF Enc1P999copyrightEntry
    MAX-ACCESS not-accessible
    STATUS     current
    DESCRIPTION
    "
    Name      : Copyright
    Menu Path : /Audio/Audio 6
    Details   : Copyright indication.
    "
::= { enc1Params 999 }

enc1P999copyrightEntry OBJECT-TYPE
    SYNTAX Enc1P999copyrightEntry
    MAX-ACCESS not-accessible
    STATUS     current
    DESCRIPTION
    "Table Entry for Copyright"
    INDEX { slotId }
::= { enc1P999copyrightTable 1 }

Enc1P999copyrightEntry ::= SEQUENCE {
    enc1P999copyrightValue    Enc1E11enumObj
}

enc1P999copyrightValue OBJECT-TYPE
    SYNTAX     Enc1E11enumObj
    MAX-ACCESS read-write
    STATUS     current
    DESCRIPTION
    "Copyright indication."
::= { enc1P999copyrightEntry 1 }

enc1P1000originalTable OBJECT-TYPE
    SYNTAX SEQUENCE OF Enc1P1000originalEntry
    MAX-ACCESS not-accessible
    STATUS     current
    DESCRIPTION
    "
    Name      : Original
    Menu Path : /Audio/Audio 6
    Details   : Specifies input is an original audio master.
    "
::= { enc1Params 1000 }

enc1P1000originalEntry OBJECT-TYPE
    SYNTAX Enc1P1000originalEntry
    MAX-ACCESS not-accessible
    STATUS     current
    DESCRIPTION
    "Table Entry for Original"
    INDEX { slotId }
::= { enc1P1000originalTable 1 }

Enc1P1000originalEntry ::= SEQUENCE {
    enc1P1000originalValue    Enc1E11enumObj
}

enc1P1000originalValue OBJECT-TYPE
    SYNTAX     Enc1E11enumObj
    MAX-ACCESS read-write
    STATUS     current
    DESCRIPTION
    "Specifies input is an original audio master."
::= { enc1P1000originalEntry 1 }

enc1P1001copyrightTable OBJECT-TYPE
    SYNTAX SEQUENCE OF Enc1P1001copyrightEntry
    MAX-ACCESS not-accessible
    STATUS     current
    DESCRIPTION
    "
    Name      : Copyright
    Menu Path : /Audio/Audio 7
    Details   : Copyright indication.
    "
::= { enc1Params 1001 }

enc1P1001copyrightEntry OBJECT-TYPE
    SYNTAX Enc1P1001copyrightEntry
    MAX-ACCESS not-accessible
    STATUS     current
    DESCRIPTION
    "Table Entry for Copyright"
    INDEX { slotId }
::= { enc1P1001copyrightTable 1 }

Enc1P1001copyrightEntry ::= SEQUENCE {
    enc1P1001copyrightValue    Enc1E11enumObj
}

enc1P1001copyrightValue OBJECT-TYPE
    SYNTAX     Enc1E11enumObj
    MAX-ACCESS read-write
    STATUS     current
    DESCRIPTION
    "Copyright indication."
::= { enc1P1001copyrightEntry 1 }

enc1P1002originalTable OBJECT-TYPE
    SYNTAX SEQUENCE OF Enc1P1002originalEntry
    MAX-ACCESS not-accessible
    STATUS     current
    DESCRIPTION
    "
    Name      : Original
    Menu Path : /Audio/Audio 7
    Details   : Specifies input is an original audio master.
    "
::= { enc1Params 1002 }

enc1P1002originalEntry OBJECT-TYPE
    SYNTAX Enc1P1002originalEntry
    MAX-ACCESS not-accessible
    STATUS     current
    DESCRIPTION
    "Table Entry for Original"
    INDEX { slotId }
::= { enc1P1002originalTable 1 }

Enc1P1002originalEntry ::= SEQUENCE {
    enc1P1002originalValue    Enc1E11enumObj
}

enc1P1002originalValue OBJECT-TYPE
    SYNTAX     Enc1E11enumObj
    MAX-ACCESS read-write
    STATUS     current
    DESCRIPTION
    "Specifies input is an original audio master."
::= { enc1P1002originalEntry 1 }

enc1P1003copyrightTable OBJECT-TYPE
    SYNTAX SEQUENCE OF Enc1P1003copyrightEntry
    MAX-ACCESS not-accessible
    STATUS     current
    DESCRIPTION
    "
    Name      : Copyright
    Menu Path : /Audio/Audio 8
    Details   : Copyright indication.
    "
::= { enc1Params 1003 }

enc1P1003copyrightEntry OBJECT-TYPE
    SYNTAX Enc1P1003copyrightEntry
    MAX-ACCESS not-accessible
    STATUS     current
    DESCRIPTION
    "Table Entry for Copyright"
    INDEX { slotId }
::= { enc1P1003copyrightTable 1 }

Enc1P1003copyrightEntry ::= SEQUENCE {
    enc1P1003copyrightValue    Enc1E11enumObj
}

enc1P1003copyrightValue OBJECT-TYPE
    SYNTAX     Enc1E11enumObj
    MAX-ACCESS read-write
    STATUS     current
    DESCRIPTION
    "Copyright indication."
::= { enc1P1003copyrightEntry 1 }

enc1P1004originalTable OBJECT-TYPE
    SYNTAX SEQUENCE OF Enc1P1004originalEntry
    MAX-ACCESS not-accessible
    STATUS     current
    DESCRIPTION
    "
    Name      : Original
    Menu Path : /Audio/Audio 8
    Details   : Specifies input is an original audio master.
    "
::= { enc1Params 1004 }

enc1P1004originalEntry OBJECT-TYPE
    SYNTAX Enc1P1004originalEntry
    MAX-ACCESS not-accessible
    STATUS     current
    DESCRIPTION
    "Table Entry for Original"
    INDEX { slotId }
::= { enc1P1004originalTable 1 }

Enc1P1004originalEntry ::= SEQUENCE {
    enc1P1004originalValue    Enc1E11enumObj
}

enc1P1004originalValue OBJECT-TYPE
    SYNTAX     Enc1E11enumObj
    MAX-ACCESS read-write
    STATUS     current
    DESCRIPTION
    "Specifies input is an original audio master."
::= { enc1P1004originalEntry 1 }

enc1P1005bitDepthTable OBJECT-TYPE
    SYNTAX SEQUENCE OF Enc1P1005bitDepthEntry
    MAX-ACCESS not-accessible
    STATUS     current
    DESCRIPTION
    "
    Name      : Bit Depth
    Menu Path : /Audio/Audio 2/Dolby E Encoder
    Details   : Specifies the bit depth of compressed data words.
    "
::= { enc1Params 1005 }

enc1P1005bitDepthEntry OBJECT-TYPE
    SYNTAX Enc1P1005bitDepthEntry
    MAX-ACCESS not-accessible
    STATUS     current
    DESCRIPTION
    "Table Entry for Bit Depth"
    INDEX { slotId }
::= { enc1P1005bitDepthTable 1 }

Enc1P1005bitDepthEntry ::= SEQUENCE {
    enc1P1005bitDepthValue    Enc1E98enumObj
}

enc1P1005bitDepthValue OBJECT-TYPE
    SYNTAX     Enc1E98enumObj
    MAX-ACCESS read-write
    STATUS     current
    DESCRIPTION
    "Specifies the bit depth of compressed data words."
::= { enc1P1005bitDepthEntry 1 }

enc1P1006bitDepthTable OBJECT-TYPE
    SYNTAX SEQUENCE OF Enc1P1006bitDepthEntry
    MAX-ACCESS not-accessible
    STATUS     current
    DESCRIPTION
    "
    Name      : Bit Depth
    Menu Path : /Audio/Audio 1/Dolby E Encoder
    Details   : Specifies the bit depth of compressed data words.
    "
::= { enc1Params 1006 }

enc1P1006bitDepthEntry OBJECT-TYPE
    SYNTAX Enc1P1006bitDepthEntry
    MAX-ACCESS not-accessible
    STATUS     current
    DESCRIPTION
    "Table Entry for Bit Depth"
    INDEX { slotId }
::= { enc1P1006bitDepthTable 1 }

Enc1P1006bitDepthEntry ::= SEQUENCE {
    enc1P1006bitDepthValue    Enc1E98enumObj
}

enc1P1006bitDepthValue OBJECT-TYPE
    SYNTAX     Enc1E98enumObj
    MAX-ACCESS read-write
    STATUS     current
    DESCRIPTION
    "Specifies the bit depth of compressed data words."
::= { enc1P1006bitDepthEntry 1 }

enc1P1011clearStatusTable OBJECT-TYPE
    SYNTAX SEQUENCE OF Enc1P1011clearStatusEntry
    MAX-ACCESS not-accessible
    STATUS     current
    DESCRIPTION
    "
    Name      : Clear Status
    Menu Path : /Misc
    Details   : Clear module status counters.
    "
::= { enc1Params 1011 }

enc1P1011clearStatusEntry OBJECT-TYPE
    SYNTAX Enc1P1011clearStatusEntry
    MAX-ACCESS not-accessible
    STATUS     current
    DESCRIPTION
    "Table Entry for Clear Status"
    INDEX { slotId }
::= { enc1P1011clearStatusTable 1 }

Enc1P1011clearStatusEntry ::= SEQUENCE {
    enc1P1011clearStatusValue    Enc1E20enumObj
}

enc1P1011clearStatusValue OBJECT-TYPE
    SYNTAX     Enc1E20enumObj
    MAX-ACCESS read-write
    STATUS     current
    DESCRIPTION
    "Clear module status counters."
::= { enc1P1011clearStatusEntry 1 }

enc1P1012clearStatusTable OBJECT-TYPE
    SYNTAX SEQUENCE OF Enc1P1012clearStatusEntry
    MAX-ACCESS not-accessible
    STATUS     current
    DESCRIPTION
    "
    Name      : Clear Status
    Menu Path : /Video/Input/Status
    Details   : Clear module status counters
    "
::= { enc1Params 1012 }

enc1P1012clearStatusEntry OBJECT-TYPE
    SYNTAX Enc1P1012clearStatusEntry
    MAX-ACCESS not-accessible
    STATUS     current
    DESCRIPTION
    "Table Entry for Clear Status"
    INDEX { slotId }
::= { enc1P1012clearStatusTable 1 }

Enc1P1012clearStatusEntry ::= SEQUENCE {
    enc1P1012clearStatusValue    Enc1E20enumObj
}

enc1P1012clearStatusValue OBJECT-TYPE
    SYNTAX     Enc1E20enumObj
    MAX-ACCESS read-write
    STATUS     current
    DESCRIPTION
    "Clear module status counters"
::= { enc1P1012clearStatusEntry 1 }

enc1P1013isdbccpidTable OBJECT-TYPE
    SYNTAX SEQUENCE OF Enc1P1013isdbccpidEntry
    MAX-ACCESS not-accessible
    STATUS     current
    DESCRIPTION
    "
    Name      : ISDB CC PID
    Menu Path : /TS Mux/MPEG Parameters/Main Program
    Units     : 
    Precision : 0
    Low Range : 16
    High Range: 8190
    Details   : Specifies the PID used for ISDB captions.

     NOTE: Precision/Units/Ranges represent the state of the
           parameter during the MIB generation, and does not
           neccessary reflect the current state of the parameter
    "
::= { enc1Params 1013 }

enc1P1013isdbccpidEntry OBJECT-TYPE
    SYNTAX Enc1P1013isdbccpidEntry
    MAX-ACCESS not-accessible
    STATUS     current
    DESCRIPTION
    "Table Entry for ISDB CC PID"
    INDEX { slotId }
::= { enc1P1013isdbccpidTable 1 }

Enc1P1013isdbccpidEntry ::= SEQUENCE {
    enc1P1013isdbccpidValue    INTEGER
}

enc1P1013isdbccpidValue OBJECT-TYPE
    SYNTAX     INTEGER
    MAX-ACCESS read-write
    STATUS     current
    DESCRIPTION
    "Specifies the PID used for ISDB captions."
::= { enc1P1013isdbccpidEntry 1 }

enc1P1014sourceTable OBJECT-TYPE
    SYNTAX SEQUENCE OF Enc1P1014sourceEntry
    MAX-ACCESS not-accessible
    STATUS     current
    DESCRIPTION
    "
    Name      : Source
    Menu Path : /Data/Subtitles
    Details   : Specifies the subtitle source for this program.
    "
::= { enc1Params 1014 }

enc1P1014sourceEntry OBJECT-TYPE
    SYNTAX Enc1P1014sourceEntry
    MAX-ACCESS not-accessible
    STATUS     current
    DESCRIPTION
    "Table Entry for Source"
    INDEX { slotId }
::= { enc1P1014sourceTable 1 }

Enc1P1014sourceEntry ::= SEQUENCE {
    enc1P1014sourceValue    Enc1E117enumObj
}

enc1P1014sourceValue OBJECT-TYPE
    SYNTAX     Enc1E117enumObj
    MAX-ACCESS read-write
    STATUS     current
    DESCRIPTION
    "Specifies the subtitle source for this program."
::= { enc1P1014sourceEntry 1 }

enc1P1015subtitleRateTable OBJECT-TYPE
    SYNTAX SEQUENCE OF Enc1P1015subtitleRateEntry
    MAX-ACCESS not-accessible
    STATUS     current
    DESCRIPTION
    "
    Name      : Subtitle Rate
    Menu Path : /Data/Subtitles
    Units     : Mbits/sec
    Precision : 6
    Low Range : 0
    High Range: 2000000
    Details   : Specifies maximum TS rate dedicated to Subtitle data. (Units: Mbits/sec)

     NOTE: Precision/Units/Ranges represent the state of the
           parameter during the MIB generation, and does not
           neccessary reflect the current state of the parameter
    "
::= { enc1Params 1015 }

enc1P1015subtitleRateEntry OBJECT-TYPE
    SYNTAX Enc1P1015subtitleRateEntry
    MAX-ACCESS not-accessible
    STATUS     current
    DESCRIPTION
    "Table Entry for Subtitle Rate"
    INDEX { slotId }
::= { enc1P1015subtitleRateTable 1 }

Enc1P1015subtitleRateEntry ::= SEQUENCE {
    enc1P1015subtitleRateValue    INTEGER
}

enc1P1015subtitleRateValue OBJECT-TYPE
    SYNTAX     INTEGER
    MAX-ACCESS read-write
    STATUS     current
    DESCRIPTION
    "Specifies maximum TS rate dedicated to Subtitle data. (Units: Mbits/sec)"
::= { enc1P1015subtitleRateEntry 1 }

enc1P1017metadataOverrideTable OBJECT-TYPE
    SYNTAX SEQUENCE OF Enc1P1017metadataOverrideEntry
    MAX-ACCESS not-accessible
    STATUS     current
    DESCRIPTION
    "
    Name      : Metadata Override
    Menu Path : /Audio/Audio 1/Metadata
    Details   : Specifies external metadata elements to override from generator
    "
::= { enc1Params 1017 }

enc1P1017metadataOverrideEntry OBJECT-TYPE
    SYNTAX Enc1P1017metadataOverrideEntry
    MAX-ACCESS not-accessible
    STATUS     current
    DESCRIPTION
    "Table Entry for Metadata Override"
    INDEX { slotId }
::= { enc1P1017metadataOverrideTable 1 }

Enc1P1017metadataOverrideEntry ::= SEQUENCE {
    enc1P1017metadataOverrideValue    Enc1E99enumObj
}

enc1P1017metadataOverrideValue OBJECT-TYPE
    SYNTAX     Enc1E99enumObj
    MAX-ACCESS read-write
    STATUS     current
    DESCRIPTION
    "Specifies external metadata elements to override from generator"
::= { enc1P1017metadataOverrideEntry 1 }

enc1P1018metadataOverrideTable OBJECT-TYPE
    SYNTAX SEQUENCE OF Enc1P1018metadataOverrideEntry
    MAX-ACCESS not-accessible
    STATUS     current
    DESCRIPTION
    "
    Name      : Metadata Override
    Menu Path : /Audio/Audio 2/Metadata
    Details   : Specifies external metadata elements to override from generator
    "
::= { enc1Params 1018 }

enc1P1018metadataOverrideEntry OBJECT-TYPE
    SYNTAX Enc1P1018metadataOverrideEntry
    MAX-ACCESS not-accessible
    STATUS     current
    DESCRIPTION
    "Table Entry for Metadata Override"
    INDEX { slotId }
::= { enc1P1018metadataOverrideTable 1 }

Enc1P1018metadataOverrideEntry ::= SEQUENCE {
    enc1P1018metadataOverrideValue    Enc1E99enumObj
}

enc1P1018metadataOverrideValue OBJECT-TYPE
    SYNTAX     Enc1E99enumObj
    MAX-ACCESS read-write
    STATUS     current
    DESCRIPTION
    "Specifies external metadata elements to override from generator"
::= { enc1P1018metadataOverrideEntry 1 }

enc1P1019metadataOverrideTable OBJECT-TYPE
    SYNTAX SEQUENCE OF Enc1P1019metadataOverrideEntry
    MAX-ACCESS not-accessible
    STATUS     current
    DESCRIPTION
    "
    Name      : Metadata Override
    Menu Path : /Audio/Audio 3/Metadata
    Details   : Specifies external metadata elements to override from generator
    "
::= { enc1Params 1019 }

enc1P1019metadataOverrideEntry OBJECT-TYPE
    SYNTAX Enc1P1019metadataOverrideEntry
    MAX-ACCESS not-accessible
    STATUS     current
    DESCRIPTION
    "Table Entry for Metadata Override"
    INDEX { slotId }
::= { enc1P1019metadataOverrideTable 1 }

Enc1P1019metadataOverrideEntry ::= SEQUENCE {
    enc1P1019metadataOverrideValue    Enc1E99enumObj
}

enc1P1019metadataOverrideValue OBJECT-TYPE
    SYNTAX     Enc1E99enumObj
    MAX-ACCESS read-write
    STATUS     current
    DESCRIPTION
    "Specifies external metadata elements to override from generator"
::= { enc1P1019metadataOverrideEntry 1 }

enc1P1020metadataOverrideTable OBJECT-TYPE
    SYNTAX SEQUENCE OF Enc1P1020metadataOverrideEntry
    MAX-ACCESS not-accessible
    STATUS     current
    DESCRIPTION
    "
    Name      : Metadata Override
    Menu Path : /Audio/Audio 4/Metadata
    Details   : Specifies external metadata elements to override from generator
    "
::= { enc1Params 1020 }

enc1P1020metadataOverrideEntry OBJECT-TYPE
    SYNTAX Enc1P1020metadataOverrideEntry
    MAX-ACCESS not-accessible
    STATUS     current
    DESCRIPTION
    "Table Entry for Metadata Override"
    INDEX { slotId }
::= { enc1P1020metadataOverrideTable 1 }

Enc1P1020metadataOverrideEntry ::= SEQUENCE {
    enc1P1020metadataOverrideValue    Enc1E99enumObj
}

enc1P1020metadataOverrideValue OBJECT-TYPE
    SYNTAX     Enc1E99enumObj
    MAX-ACCESS read-write
    STATUS     current
    DESCRIPTION
    "Specifies external metadata elements to override from generator"
::= { enc1P1020metadataOverrideEntry 1 }

enc1P1021metadataOverrideTable OBJECT-TYPE
    SYNTAX SEQUENCE OF Enc1P1021metadataOverrideEntry
    MAX-ACCESS not-accessible
    STATUS     current
    DESCRIPTION
    "
    Name      : Metadata Override
    Menu Path : /Audio/Audio 5/Metadata
    Details   : Specifies external metadata elements to override from generator
    "
::= { enc1Params 1021 }

enc1P1021metadataOverrideEntry OBJECT-TYPE
    SYNTAX Enc1P1021metadataOverrideEntry
    MAX-ACCESS not-accessible
    STATUS     current
    DESCRIPTION
    "Table Entry for Metadata Override"
    INDEX { slotId }
::= { enc1P1021metadataOverrideTable 1 }

Enc1P1021metadataOverrideEntry ::= SEQUENCE {
    enc1P1021metadataOverrideValue    Enc1E99enumObj
}

enc1P1021metadataOverrideValue OBJECT-TYPE
    SYNTAX     Enc1E99enumObj
    MAX-ACCESS read-write
    STATUS     current
    DESCRIPTION
    "Specifies external metadata elements to override from generator"
::= { enc1P1021metadataOverrideEntry 1 }

enc1P1022metadataOverrideTable OBJECT-TYPE
    SYNTAX SEQUENCE OF Enc1P1022metadataOverrideEntry
    MAX-ACCESS not-accessible
    STATUS     current
    DESCRIPTION
    "
    Name      : Metadata Override
    Menu Path : /Audio/Audio 6/Metadata
    Details   : Specifies external metadata elements to override from generator
    "
::= { enc1Params 1022 }

enc1P1022metadataOverrideEntry OBJECT-TYPE
    SYNTAX Enc1P1022metadataOverrideEntry
    MAX-ACCESS not-accessible
    STATUS     current
    DESCRIPTION
    "Table Entry for Metadata Override"
    INDEX { slotId }
::= { enc1P1022metadataOverrideTable 1 }

Enc1P1022metadataOverrideEntry ::= SEQUENCE {
    enc1P1022metadataOverrideValue    Enc1E99enumObj
}

enc1P1022metadataOverrideValue OBJECT-TYPE
    SYNTAX     Enc1E99enumObj
    MAX-ACCESS read-write
    STATUS     current
    DESCRIPTION
    "Specifies external metadata elements to override from generator"
::= { enc1P1022metadataOverrideEntry 1 }

enc1P1023metadataOverrideTable OBJECT-TYPE
    SYNTAX SEQUENCE OF Enc1P1023metadataOverrideEntry
    MAX-ACCESS not-accessible
    STATUS     current
    DESCRIPTION
    "
    Name      : Metadata Override
    Menu Path : /Audio/Audio 7/Metadata
    Details   : Specifies external metadata elements to override from generator
    "
::= { enc1Params 1023 }

enc1P1023metadataOverrideEntry OBJECT-TYPE
    SYNTAX Enc1P1023metadataOverrideEntry
    MAX-ACCESS not-accessible
    STATUS     current
    DESCRIPTION
    "Table Entry for Metadata Override"
    INDEX { slotId }
::= { enc1P1023metadataOverrideTable 1 }

Enc1P1023metadataOverrideEntry ::= SEQUENCE {
    enc1P1023metadataOverrideValue    Enc1E99enumObj
}

enc1P1023metadataOverrideValue OBJECT-TYPE
    SYNTAX     Enc1E99enumObj
    MAX-ACCESS read-write
    STATUS     current
    DESCRIPTION
    "Specifies external metadata elements to override from generator"
::= { enc1P1023metadataOverrideEntry 1 }

enc1P1024metadataOverrideTable OBJECT-TYPE
    SYNTAX SEQUENCE OF Enc1P1024metadataOverrideEntry
    MAX-ACCESS not-accessible
    STATUS     current
    DESCRIPTION
    "
    Name      : Metadata Override
    Menu Path : /Audio/Audio 8/Metadata
    Details   : Specifies external metadata elements to override from generator
    "
::= { enc1Params 1024 }

enc1P1024metadataOverrideEntry OBJECT-TYPE
    SYNTAX Enc1P1024metadataOverrideEntry
    MAX-ACCESS not-accessible
    STATUS     current
    DESCRIPTION
    "Table Entry for Metadata Override"
    INDEX { slotId }
::= { enc1P1024metadataOverrideTable 1 }

Enc1P1024metadataOverrideEntry ::= SEQUENCE {
    enc1P1024metadataOverrideValue    Enc1E99enumObj
}

enc1P1024metadataOverrideValue OBJECT-TYPE
    SYNTAX     Enc1E99enumObj
    MAX-ACCESS read-write
    STATUS     current
    DESCRIPTION
    "Specifies external metadata elements to override from generator"
::= { enc1P1024metadataOverrideEntry 1 }

enc1P1025subtitle1PIDTable OBJECT-TYPE
    SYNTAX SEQUENCE OF Enc1P1025subtitle1PIDEntry
    MAX-ACCESS not-accessible
    STATUS     current
    DESCRIPTION
    "
    Name      : Subtitle 1 PID
    Menu Path : /TS Mux/MPEG Parameters/Main Program
    Units     : 
    Precision : 0
    Low Range : 16
    High Range: 8190
    Details   : Specifies the PID used for subtitles.

     NOTE: Precision/Units/Ranges represent the state of the
           parameter during the MIB generation, and does not
           neccessary reflect the current state of the parameter
    "
::= { enc1Params 1025 }

enc1P1025subtitle1PIDEntry OBJECT-TYPE
    SYNTAX Enc1P1025subtitle1PIDEntry
    MAX-ACCESS not-accessible
    STATUS     current
    DESCRIPTION
    "Table Entry for Subtitle 1 PID"
    INDEX { slotId }
::= { enc1P1025subtitle1PIDTable 1 }

Enc1P1025subtitle1PIDEntry ::= SEQUENCE {
    enc1P1025subtitle1PIDValue    INTEGER
}

enc1P1025subtitle1PIDValue OBJECT-TYPE
    SYNTAX     INTEGER
    MAX-ACCESS read-write
    STATUS     current
    DESCRIPTION
    "Specifies the PID used for subtitles."
::= { enc1P1025subtitle1PIDEntry 1 }

enc1P1026subtitle2PIDTable OBJECT-TYPE
    SYNTAX SEQUENCE OF Enc1P1026subtitle2PIDEntry
    MAX-ACCESS not-accessible
    STATUS     current
    DESCRIPTION
    "
    Name      : Subtitle 2 PID
    Menu Path : /TS Mux/MPEG Parameters/Main Program
    Units     : 
    Precision : 0
    Low Range : 16
    High Range: 8190
    Details   : Specifies the PID used for subtitle.

     NOTE: Precision/Units/Ranges represent the state of the
           parameter during the MIB generation, and does not
           neccessary reflect the current state of the parameter
    "
::= { enc1Params 1026 }

enc1P1026subtitle2PIDEntry OBJECT-TYPE
    SYNTAX Enc1P1026subtitle2PIDEntry
    MAX-ACCESS not-accessible
    STATUS     current
    DESCRIPTION
    "Table Entry for Subtitle 2 PID"
    INDEX { slotId }
::= { enc1P1026subtitle2PIDTable 1 }

Enc1P1026subtitle2PIDEntry ::= SEQUENCE {
    enc1P1026subtitle2PIDValue    INTEGER
}

enc1P1026subtitle2PIDValue OBJECT-TYPE
    SYNTAX     INTEGER
    MAX-ACCESS read-write
    STATUS     current
    DESCRIPTION
    "Specifies the PID used for subtitle."
::= { enc1P1026subtitle2PIDEntry 1 }

enc1P1027subtitle3PIDTable OBJECT-TYPE
    SYNTAX SEQUENCE OF Enc1P1027subtitle3PIDEntry
    MAX-ACCESS not-accessible
    STATUS     current
    DESCRIPTION
    "
    Name      : Subtitle 3 PID
    Menu Path : /TS Mux/MPEG Parameters/Main Program
    Units     : 
    Precision : 0
    Low Range : 16
    High Range: 8190
    Details   : Specifies the PID used for subtitle.

     NOTE: Precision/Units/Ranges represent the state of the
           parameter during the MIB generation, and does not
           neccessary reflect the current state of the parameter
    "
::= { enc1Params 1027 }

enc1P1027subtitle3PIDEntry OBJECT-TYPE
    SYNTAX Enc1P1027subtitle3PIDEntry
    MAX-ACCESS not-accessible
    STATUS     current
    DESCRIPTION
    "Table Entry for Subtitle 3 PID"
    INDEX { slotId }
::= { enc1P1027subtitle3PIDTable 1 }

Enc1P1027subtitle3PIDEntry ::= SEQUENCE {
    enc1P1027subtitle3PIDValue    INTEGER
}

enc1P1027subtitle3PIDValue OBJECT-TYPE
    SYNTAX     INTEGER
    MAX-ACCESS read-write
    STATUS     current
    DESCRIPTION
    "Specifies the PID used for subtitle."
::= { enc1P1027subtitle3PIDEntry 1 }

enc1P1028subtitle4PIDTable OBJECT-TYPE
    SYNTAX SEQUENCE OF Enc1P1028subtitle4PIDEntry
    MAX-ACCESS not-accessible
    STATUS     current
    DESCRIPTION
    "
    Name      : Subtitle 4 PID
    Menu Path : /TS Mux/MPEG Parameters/Main Program
    Units     : 
    Precision : 0
    Low Range : 16
    High Range: 8190
    Details   : Specifies the PID used for subtitle.

     NOTE: Precision/Units/Ranges represent the state of the
           parameter during the MIB generation, and does not
           neccessary reflect the current state of the parameter
    "
::= { enc1Params 1028 }

enc1P1028subtitle4PIDEntry OBJECT-TYPE
    SYNTAX Enc1P1028subtitle4PIDEntry
    MAX-ACCESS not-accessible
    STATUS     current
    DESCRIPTION
    "Table Entry for Subtitle 4 PID"
    INDEX { slotId }
::= { enc1P1028subtitle4PIDTable 1 }

Enc1P1028subtitle4PIDEntry ::= SEQUENCE {
    enc1P1028subtitle4PIDValue    INTEGER
}

enc1P1028subtitle4PIDValue OBJECT-TYPE
    SYNTAX     INTEGER
    MAX-ACCESS read-write
    STATUS     current
    DESCRIPTION
    "Specifies the PID used for subtitle."
::= { enc1P1028subtitle4PIDEntry 1 }

enc1P1029aes1StatusTable OBJECT-TYPE
    SYNTAX SEQUENCE OF Enc1P1029aes1StatusEntry
    MAX-ACCESS not-accessible
    STATUS     current
    DESCRIPTION
    "
    Name      : AES 1 Status
    Menu Path : /Audio/Input Status
    Details   : Summary of AES input status.
    "
::= { enc1Params 1029 }

enc1P1029aes1StatusEntry OBJECT-TYPE
    SYNTAX Enc1P1029aes1StatusEntry
    MAX-ACCESS not-accessible
    STATUS     current
    DESCRIPTION
    "Table Entry for AES 1 Status"
    INDEX { slotId }
::= { enc1P1029aes1StatusTable 1 }

Enc1P1029aes1StatusEntry ::= SEQUENCE {
    enc1P1029aes1StatusValue    Enc1E100enumObj
}

enc1P1029aes1StatusValue OBJECT-TYPE
    SYNTAX     Enc1E100enumObj
    MAX-ACCESS read-only
    STATUS     current
    DESCRIPTION
    "Summary of AES input status."
::= { enc1P1029aes1StatusEntry 1 }

enc1P1030aes2StatusTable OBJECT-TYPE
    SYNTAX SEQUENCE OF Enc1P1030aes2StatusEntry
    MAX-ACCESS not-accessible
    STATUS     current
    DESCRIPTION
    "
    Name      : AES 2 Status
    Menu Path : /Audio/Input Status
    Details   : Summary of AES input status.
    "
::= { enc1Params 1030 }

enc1P1030aes2StatusEntry OBJECT-TYPE
    SYNTAX Enc1P1030aes2StatusEntry
    MAX-ACCESS not-accessible
    STATUS     current
    DESCRIPTION
    "Table Entry for AES 2 Status"
    INDEX { slotId }
::= { enc1P1030aes2StatusTable 1 }

Enc1P1030aes2StatusEntry ::= SEQUENCE {
    enc1P1030aes2StatusValue    Enc1E100enumObj
}

enc1P1030aes2StatusValue OBJECT-TYPE
    SYNTAX     Enc1E100enumObj
    MAX-ACCESS read-only
    STATUS     current
    DESCRIPTION
    "Summary of AES input status."
::= { enc1P1030aes2StatusEntry 1 }

enc1P1031aes3StatusTable OBJECT-TYPE
    SYNTAX SEQUENCE OF Enc1P1031aes3StatusEntry
    MAX-ACCESS not-accessible
    STATUS     current
    DESCRIPTION
    "
    Name      : AES 3 Status
    Menu Path : /Audio/Input Status
    Details   : Summary of AES input status.
    "
::= { enc1Params 1031 }

enc1P1031aes3StatusEntry OBJECT-TYPE
    SYNTAX Enc1P1031aes3StatusEntry
    MAX-ACCESS not-accessible
    STATUS     current
    DESCRIPTION
    "Table Entry for AES 3 Status"
    INDEX { slotId }
::= { enc1P1031aes3StatusTable 1 }

Enc1P1031aes3StatusEntry ::= SEQUENCE {
    enc1P1031aes3StatusValue    Enc1E100enumObj
}

enc1P1031aes3StatusValue OBJECT-TYPE
    SYNTAX     Enc1E100enumObj
    MAX-ACCESS read-only
    STATUS     current
    DESCRIPTION
    "Summary of AES input status."
::= { enc1P1031aes3StatusEntry 1 }

enc1P1032aes4StatusTable OBJECT-TYPE
    SYNTAX SEQUENCE OF Enc1P1032aes4StatusEntry
    MAX-ACCESS not-accessible
    STATUS     current
    DESCRIPTION
    "
    Name      : AES 4 Status
    Menu Path : /Audio/Input Status
    Details   : Summary of AES input status.
    "
::= { enc1Params 1032 }

enc1P1032aes4StatusEntry OBJECT-TYPE
    SYNTAX Enc1P1032aes4StatusEntry
    MAX-ACCESS not-accessible
    STATUS     current
    DESCRIPTION
    "Table Entry for AES 4 Status"
    INDEX { slotId }
::= { enc1P1032aes4StatusTable 1 }

Enc1P1032aes4StatusEntry ::= SEQUENCE {
    enc1P1032aes4StatusValue    Enc1E100enumObj
}

enc1P1032aes4StatusValue OBJECT-TYPE
    SYNTAX     Enc1E100enumObj
    MAX-ACCESS read-only
    STATUS     current
    DESCRIPTION
    "Summary of AES input status."
::= { enc1P1032aes4StatusEntry 1 }

enc1P1033aes5StatusTable OBJECT-TYPE
    SYNTAX SEQUENCE OF Enc1P1033aes5StatusEntry
    MAX-ACCESS not-accessible
    STATUS     current
    DESCRIPTION
    "
    Name      : AES 5 Status
    Menu Path : /Audio/Input Status
    Details   : Summary of AES input status.
    "
::= { enc1Params 1033 }

enc1P1033aes5StatusEntry OBJECT-TYPE
    SYNTAX Enc1P1033aes5StatusEntry
    MAX-ACCESS not-accessible
    STATUS     current
    DESCRIPTION
    "Table Entry for AES 5 Status"
    INDEX { slotId }
::= { enc1P1033aes5StatusTable 1 }

Enc1P1033aes5StatusEntry ::= SEQUENCE {
    enc1P1033aes5StatusValue    Enc1E100enumObj
}

enc1P1033aes5StatusValue OBJECT-TYPE
    SYNTAX     Enc1E100enumObj
    MAX-ACCESS read-only
    STATUS     current
    DESCRIPTION
    "Summary of AES input status."
::= { enc1P1033aes5StatusEntry 1 }

enc1P1034aes6StatusTable OBJECT-TYPE
    SYNTAX SEQUENCE OF Enc1P1034aes6StatusEntry
    MAX-ACCESS not-accessible
    STATUS     current
    DESCRIPTION
    "
    Name      : AES 6 Status
    Menu Path : /Audio/Input Status
    Details   : Summary of AES input status.
    "
::= { enc1Params 1034 }

enc1P1034aes6StatusEntry OBJECT-TYPE
    SYNTAX Enc1P1034aes6StatusEntry
    MAX-ACCESS not-accessible
    STATUS     current
    DESCRIPTION
    "Table Entry for AES 6 Status"
    INDEX { slotId }
::= { enc1P1034aes6StatusTable 1 }

Enc1P1034aes6StatusEntry ::= SEQUENCE {
    enc1P1034aes6StatusValue    Enc1E100enumObj
}

enc1P1034aes6StatusValue OBJECT-TYPE
    SYNTAX     Enc1E100enumObj
    MAX-ACCESS read-only
    STATUS     current
    DESCRIPTION
    "Summary of AES input status."
::= { enc1P1034aes6StatusEntry 1 }

enc1P1035aes7StatusTable OBJECT-TYPE
    SYNTAX SEQUENCE OF Enc1P1035aes7StatusEntry
    MAX-ACCESS not-accessible
    STATUS     current
    DESCRIPTION
    "
    Name      : AES 7 Status
    Menu Path : /Audio/Input Status
    Details   : Summary of AES input status.
    "
::= { enc1Params 1035 }

enc1P1035aes7StatusEntry OBJECT-TYPE
    SYNTAX Enc1P1035aes7StatusEntry
    MAX-ACCESS not-accessible
    STATUS     current
    DESCRIPTION
    "Table Entry for AES 7 Status"
    INDEX { slotId }
::= { enc1P1035aes7StatusTable 1 }

Enc1P1035aes7StatusEntry ::= SEQUENCE {
    enc1P1035aes7StatusValue    Enc1E100enumObj
}

enc1P1035aes7StatusValue OBJECT-TYPE
    SYNTAX     Enc1E100enumObj
    MAX-ACCESS read-only
    STATUS     current
    DESCRIPTION
    "Summary of AES input status."
::= { enc1P1035aes7StatusEntry 1 }

enc1P1036aes8StatusTable OBJECT-TYPE
    SYNTAX SEQUENCE OF Enc1P1036aes8StatusEntry
    MAX-ACCESS not-accessible
    STATUS     current
    DESCRIPTION
    "
    Name      : AES 8 Status
    Menu Path : /Audio/Input Status
    Details   : Summary of AES input status.
    "
::= { enc1Params 1036 }

enc1P1036aes8StatusEntry OBJECT-TYPE
    SYNTAX Enc1P1036aes8StatusEntry
    MAX-ACCESS not-accessible
    STATUS     current
    DESCRIPTION
    "Table Entry for AES 8 Status"
    INDEX { slotId }
::= { enc1P1036aes8StatusTable 1 }

Enc1P1036aes8StatusEntry ::= SEQUENCE {
    enc1P1036aes8StatusValue    Enc1E100enumObj
}

enc1P1036aes8StatusValue OBJECT-TYPE
    SYNTAX     Enc1E100enumObj
    MAX-ACCESS read-only
    STATUS     current
    DESCRIPTION
    "Summary of AES input status."
::= { enc1P1036aes8StatusEntry 1 }

enc1P1037aes1SampleRateTable OBJECT-TYPE
    SYNTAX SEQUENCE OF Enc1P1037aes1SampleRateEntry
    MAX-ACCESS not-accessible
    STATUS     current
    DESCRIPTION
    "
    Name      : AES 1 Sample Rate
    Menu Path : /Audio/Input Status
    Details   : Sample rate specified in AES channel block.
    "
::= { enc1Params 1037 }

enc1P1037aes1SampleRateEntry OBJECT-TYPE
    SYNTAX Enc1P1037aes1SampleRateEntry
    MAX-ACCESS not-accessible
    STATUS     current
    DESCRIPTION
    "Table Entry for AES 1 Sample Rate"
    INDEX { slotId }
::= { enc1P1037aes1SampleRateTable 1 }

Enc1P1037aes1SampleRateEntry ::= SEQUENCE {
    enc1P1037aes1SampleRateValue    Enc1E102enumObj
}

enc1P1037aes1SampleRateValue OBJECT-TYPE
    SYNTAX     Enc1E102enumObj
    MAX-ACCESS read-only
    STATUS     current
    DESCRIPTION
    "Sample rate specified in AES channel block."
::= { enc1P1037aes1SampleRateEntry 1 }

enc1P1038aes2SampleRateTable OBJECT-TYPE
    SYNTAX SEQUENCE OF Enc1P1038aes2SampleRateEntry
    MAX-ACCESS not-accessible
    STATUS     current
    DESCRIPTION
    "
    Name      : AES 2 Sample Rate
    Menu Path : /Audio/Input Status
    Details   : Sample rate specified in AES channel block.
    "
::= { enc1Params 1038 }

enc1P1038aes2SampleRateEntry OBJECT-TYPE
    SYNTAX Enc1P1038aes2SampleRateEntry
    MAX-ACCESS not-accessible
    STATUS     current
    DESCRIPTION
    "Table Entry for AES 2 Sample Rate"
    INDEX { slotId }
::= { enc1P1038aes2SampleRateTable 1 }

Enc1P1038aes2SampleRateEntry ::= SEQUENCE {
    enc1P1038aes2SampleRateValue    Enc1E102enumObj
}

enc1P1038aes2SampleRateValue OBJECT-TYPE
    SYNTAX     Enc1E102enumObj
    MAX-ACCESS read-only
    STATUS     current
    DESCRIPTION
    "Sample rate specified in AES channel block."
::= { enc1P1038aes2SampleRateEntry 1 }

enc1P1039aes3SampleRateTable OBJECT-TYPE
    SYNTAX SEQUENCE OF Enc1P1039aes3SampleRateEntry
    MAX-ACCESS not-accessible
    STATUS     current
    DESCRIPTION
    "
    Name      : AES 3 Sample Rate
    Menu Path : /Audio/Input Status
    Details   : Sample rate specified in AES channel block.
    "
::= { enc1Params 1039 }

enc1P1039aes3SampleRateEntry OBJECT-TYPE
    SYNTAX Enc1P1039aes3SampleRateEntry
    MAX-ACCESS not-accessible
    STATUS     current
    DESCRIPTION
    "Table Entry for AES 3 Sample Rate"
    INDEX { slotId }
::= { enc1P1039aes3SampleRateTable 1 }

Enc1P1039aes3SampleRateEntry ::= SEQUENCE {
    enc1P1039aes3SampleRateValue    Enc1E102enumObj
}

enc1P1039aes3SampleRateValue OBJECT-TYPE
    SYNTAX     Enc1E102enumObj
    MAX-ACCESS read-only
    STATUS     current
    DESCRIPTION
    "Sample rate specified in AES channel block."
::= { enc1P1039aes3SampleRateEntry 1 }

enc1P1040aes4SampleRateTable OBJECT-TYPE
    SYNTAX SEQUENCE OF Enc1P1040aes4SampleRateEntry
    MAX-ACCESS not-accessible
    STATUS     current
    DESCRIPTION
    "
    Name      : AES 4 Sample Rate
    Menu Path : /Audio/Input Status
    Details   : Sample rate specified in AES channel block.
    "
::= { enc1Params 1040 }

enc1P1040aes4SampleRateEntry OBJECT-TYPE
    SYNTAX Enc1P1040aes4SampleRateEntry
    MAX-ACCESS not-accessible
    STATUS     current
    DESCRIPTION
    "Table Entry for AES 4 Sample Rate"
    INDEX { slotId }
::= { enc1P1040aes4SampleRateTable 1 }

Enc1P1040aes4SampleRateEntry ::= SEQUENCE {
    enc1P1040aes4SampleRateValue    Enc1E102enumObj
}

enc1P1040aes4SampleRateValue OBJECT-TYPE
    SYNTAX     Enc1E102enumObj
    MAX-ACCESS read-only
    STATUS     current
    DESCRIPTION
    "Sample rate specified in AES channel block."
::= { enc1P1040aes4SampleRateEntry 1 }

enc1P1041aes5SampleRateTable OBJECT-TYPE
    SYNTAX SEQUENCE OF Enc1P1041aes5SampleRateEntry
    MAX-ACCESS not-accessible
    STATUS     current
    DESCRIPTION
    "
    Name      : AES 5 Sample Rate
    Menu Path : /Audio/Input Status
    Details   : Sample rate specified in AES channel block.
    "
::= { enc1Params 1041 }

enc1P1041aes5SampleRateEntry OBJECT-TYPE
    SYNTAX Enc1P1041aes5SampleRateEntry
    MAX-ACCESS not-accessible
    STATUS     current
    DESCRIPTION
    "Table Entry for AES 5 Sample Rate"
    INDEX { slotId }
::= { enc1P1041aes5SampleRateTable 1 }

Enc1P1041aes5SampleRateEntry ::= SEQUENCE {
    enc1P1041aes5SampleRateValue    Enc1E102enumObj
}

enc1P1041aes5SampleRateValue OBJECT-TYPE
    SYNTAX     Enc1E102enumObj
    MAX-ACCESS read-only
    STATUS     current
    DESCRIPTION
    "Sample rate specified in AES channel block."
::= { enc1P1041aes5SampleRateEntry 1 }

enc1P1042aes6SampleRateTable OBJECT-TYPE
    SYNTAX SEQUENCE OF Enc1P1042aes6SampleRateEntry
    MAX-ACCESS not-accessible
    STATUS     current
    DESCRIPTION
    "
    Name      : AES 6 Sample Rate
    Menu Path : /Audio/Input Status
    Details   : Sample rate specified in AES channel block.
    "
::= { enc1Params 1042 }

enc1P1042aes6SampleRateEntry OBJECT-TYPE
    SYNTAX Enc1P1042aes6SampleRateEntry
    MAX-ACCESS not-accessible
    STATUS     current
    DESCRIPTION
    "Table Entry for AES 6 Sample Rate"
    INDEX { slotId }
::= { enc1P1042aes6SampleRateTable 1 }

Enc1P1042aes6SampleRateEntry ::= SEQUENCE {
    enc1P1042aes6SampleRateValue    Enc1E102enumObj
}

enc1P1042aes6SampleRateValue OBJECT-TYPE
    SYNTAX     Enc1E102enumObj
    MAX-ACCESS read-only
    STATUS     current
    DESCRIPTION
    "Sample rate specified in AES channel block."
::= { enc1P1042aes6SampleRateEntry 1 }

enc1P1043aes7SampleRateTable OBJECT-TYPE
    SYNTAX SEQUENCE OF Enc1P1043aes7SampleRateEntry
    MAX-ACCESS not-accessible
    STATUS     current
    DESCRIPTION
    "
    Name      : AES 7 Sample Rate
    Menu Path : /Audio/Input Status
    Details   : Sample rate specified in AES channel block.
    "
::= { enc1Params 1043 }

enc1P1043aes7SampleRateEntry OBJECT-TYPE
    SYNTAX Enc1P1043aes7SampleRateEntry
    MAX-ACCESS not-accessible
    STATUS     current
    DESCRIPTION
    "Table Entry for AES 7 Sample Rate"
    INDEX { slotId }
::= { enc1P1043aes7SampleRateTable 1 }

Enc1P1043aes7SampleRateEntry ::= SEQUENCE {
    enc1P1043aes7SampleRateValue    Enc1E102enumObj
}

enc1P1043aes7SampleRateValue OBJECT-TYPE
    SYNTAX     Enc1E102enumObj
    MAX-ACCESS read-only
    STATUS     current
    DESCRIPTION
    "Sample rate specified in AES channel block."
::= { enc1P1043aes7SampleRateEntry 1 }

enc1P1044aes8SampleRateTable OBJECT-TYPE
    SYNTAX SEQUENCE OF Enc1P1044aes8SampleRateEntry
    MAX-ACCESS not-accessible
    STATUS     current
    DESCRIPTION
    "
    Name      : AES 8 Sample Rate
    Menu Path : /Audio/Input Status
    Details   : Sample rate specified in AES channel block.
    "
::= { enc1Params 1044 }

enc1P1044aes8SampleRateEntry OBJECT-TYPE
    SYNTAX Enc1P1044aes8SampleRateEntry
    MAX-ACCESS not-accessible
    STATUS     current
    DESCRIPTION
    "Table Entry for AES 8 Sample Rate"
    INDEX { slotId }
::= { enc1P1044aes8SampleRateTable 1 }

Enc1P1044aes8SampleRateEntry ::= SEQUENCE {
    enc1P1044aes8SampleRateValue    Enc1E102enumObj
}

enc1P1044aes8SampleRateValue OBJECT-TYPE
    SYNTAX     Enc1E102enumObj
    MAX-ACCESS read-only
    STATUS     current
    DESCRIPTION
    "Sample rate specified in AES channel block."
::= { enc1P1044aes8SampleRateEntry 1 }

enc1P1045emb1A-1BG1P1StatusTable OBJECT-TYPE
    SYNTAX SEQUENCE OF Enc1P1045emb1A-1BG1P1StatusEntry
    MAX-ACCESS not-accessible
    STATUS     current
    DESCRIPTION
    "
    Name      : Emb 1A-1B (G1P1) Status
    Menu Path : /Audio/Input Status
    Details   : Summary of embedded audio status.
    "
::= { enc1Params 1045 }

enc1P1045emb1A-1BG1P1StatusEntry OBJECT-TYPE
    SYNTAX Enc1P1045emb1A-1BG1P1StatusEntry
    MAX-ACCESS not-accessible
    STATUS     current
    DESCRIPTION
    "Table Entry for Emb 1A-1B (G1P1) Status"
    INDEX { slotId }
::= { enc1P1045emb1A-1BG1P1StatusTable 1 }

Enc1P1045emb1A-1BG1P1StatusEntry ::= SEQUENCE {
    enc1P1045emb1A-1BG1P1StatusValue    Enc1E101enumObj
}

enc1P1045emb1A-1BG1P1StatusValue OBJECT-TYPE
    SYNTAX     Enc1E101enumObj
    MAX-ACCESS read-only
    STATUS     current
    DESCRIPTION
    "Summary of embedded audio status."
::= { enc1P1045emb1A-1BG1P1StatusEntry 1 }

enc1P1046emb2A-2BG1P2StatusTable OBJECT-TYPE
    SYNTAX SEQUENCE OF Enc1P1046emb2A-2BG1P2StatusEntry
    MAX-ACCESS not-accessible
    STATUS     current
    DESCRIPTION
    "
    Name      : Emb 2A-2B (G1P2) Status
    Menu Path : /Audio/Input Status
    Details   : Summary of embedded audio status.
    "
::= { enc1Params 1046 }

enc1P1046emb2A-2BG1P2StatusEntry OBJECT-TYPE
    SYNTAX Enc1P1046emb2A-2BG1P2StatusEntry
    MAX-ACCESS not-accessible
    STATUS     current
    DESCRIPTION
    "Table Entry for Emb 2A-2B (G1P2) Status"
    INDEX { slotId }
::= { enc1P1046emb2A-2BG1P2StatusTable 1 }

Enc1P1046emb2A-2BG1P2StatusEntry ::= SEQUENCE {
    enc1P1046emb2A-2BG1P2StatusValue    Enc1E101enumObj
}

enc1P1046emb2A-2BG1P2StatusValue OBJECT-TYPE
    SYNTAX     Enc1E101enumObj
    MAX-ACCESS read-only
    STATUS     current
    DESCRIPTION
    "Summary of embedded audio status."
::= { enc1P1046emb2A-2BG1P2StatusEntry 1 }

enc1P1047emb3A-3BG2P1StatusTable OBJECT-TYPE
    SYNTAX SEQUENCE OF Enc1P1047emb3A-3BG2P1StatusEntry
    MAX-ACCESS not-accessible
    STATUS     current
    DESCRIPTION
    "
    Name      : Emb 3A-3B (G2P1) Status
    Menu Path : /Audio/Input Status
    Details   : Summary of embedded audio status.
    "
::= { enc1Params 1047 }

enc1P1047emb3A-3BG2P1StatusEntry OBJECT-TYPE
    SYNTAX Enc1P1047emb3A-3BG2P1StatusEntry
    MAX-ACCESS not-accessible
    STATUS     current
    DESCRIPTION
    "Table Entry for Emb 3A-3B (G2P1) Status"
    INDEX { slotId }
::= { enc1P1047emb3A-3BG2P1StatusTable 1 }

Enc1P1047emb3A-3BG2P1StatusEntry ::= SEQUENCE {
    enc1P1047emb3A-3BG2P1StatusValue    Enc1E101enumObj
}

enc1P1047emb3A-3BG2P1StatusValue OBJECT-TYPE
    SYNTAX     Enc1E101enumObj
    MAX-ACCESS read-only
    STATUS     current
    DESCRIPTION
    "Summary of embedded audio status."
::= { enc1P1047emb3A-3BG2P1StatusEntry 1 }

enc1P1048emb4A-4BG2P2StatusTable OBJECT-TYPE
    SYNTAX SEQUENCE OF Enc1P1048emb4A-4BG2P2StatusEntry
    MAX-ACCESS not-accessible
    STATUS     current
    DESCRIPTION
    "
    Name      : Emb 4A-4B (G2P2) Status
    Menu Path : /Audio/Input Status
    Details   : Summary of embedded audio status.
    "
::= { enc1Params 1048 }

enc1P1048emb4A-4BG2P2StatusEntry OBJECT-TYPE
    SYNTAX Enc1P1048emb4A-4BG2P2StatusEntry
    MAX-ACCESS not-accessible
    STATUS     current
    DESCRIPTION
    "Table Entry for Emb 4A-4B (G2P2) Status"
    INDEX { slotId }
::= { enc1P1048emb4A-4BG2P2StatusTable 1 }

Enc1P1048emb4A-4BG2P2StatusEntry ::= SEQUENCE {
    enc1P1048emb4A-4BG2P2StatusValue    Enc1E101enumObj
}

enc1P1048emb4A-4BG2P2StatusValue OBJECT-TYPE
    SYNTAX     Enc1E101enumObj
    MAX-ACCESS read-only
    STATUS     current
    DESCRIPTION
    "Summary of embedded audio status."
::= { enc1P1048emb4A-4BG2P2StatusEntry 1 }

enc1P1049emb5A-5BG3P1StatusTable OBJECT-TYPE
    SYNTAX SEQUENCE OF Enc1P1049emb5A-5BG3P1StatusEntry
    MAX-ACCESS not-accessible
    STATUS     current
    DESCRIPTION
    "
    Name      : Emb 5A-5B (G3P1) Status
    Menu Path : /Audio/Input Status
    Details   : Summary of embedded audio status.
    "
::= { enc1Params 1049 }

enc1P1049emb5A-5BG3P1StatusEntry OBJECT-TYPE
    SYNTAX Enc1P1049emb5A-5BG3P1StatusEntry
    MAX-ACCESS not-accessible
    STATUS     current
    DESCRIPTION
    "Table Entry for Emb 5A-5B (G3P1) Status"
    INDEX { slotId }
::= { enc1P1049emb5A-5BG3P1StatusTable 1 }

Enc1P1049emb5A-5BG3P1StatusEntry ::= SEQUENCE {
    enc1P1049emb5A-5BG3P1StatusValue    Enc1E101enumObj
}

enc1P1049emb5A-5BG3P1StatusValue OBJECT-TYPE
    SYNTAX     Enc1E101enumObj
    MAX-ACCESS read-only
    STATUS     current
    DESCRIPTION
    "Summary of embedded audio status."
::= { enc1P1049emb5A-5BG3P1StatusEntry 1 }

enc1P1050emb6A-6BG3P2StatusTable OBJECT-TYPE
    SYNTAX SEQUENCE OF Enc1P1050emb6A-6BG3P2StatusEntry
    MAX-ACCESS not-accessible
    STATUS     current
    DESCRIPTION
    "
    Name      : Emb 6A-6B (G3P2) Status
    Menu Path : /Audio/Input Status
    Details   : Summary of embedded audio status.
    "
::= { enc1Params 1050 }

enc1P1050emb6A-6BG3P2StatusEntry OBJECT-TYPE
    SYNTAX Enc1P1050emb6A-6BG3P2StatusEntry
    MAX-ACCESS not-accessible
    STATUS     current
    DESCRIPTION
    "Table Entry for Emb 6A-6B (G3P2) Status"
    INDEX { slotId }
::= { enc1P1050emb6A-6BG3P2StatusTable 1 }

Enc1P1050emb6A-6BG3P2StatusEntry ::= SEQUENCE {
    enc1P1050emb6A-6BG3P2StatusValue    Enc1E101enumObj
}

enc1P1050emb6A-6BG3P2StatusValue OBJECT-TYPE
    SYNTAX     Enc1E101enumObj
    MAX-ACCESS read-only
    STATUS     current
    DESCRIPTION
    "Summary of embedded audio status."
::= { enc1P1050emb6A-6BG3P2StatusEntry 1 }

enc1P1051emb7A-7BG4P1StatusTable OBJECT-TYPE
    SYNTAX SEQUENCE OF Enc1P1051emb7A-7BG4P1StatusEntry
    MAX-ACCESS not-accessible
    STATUS     current
    DESCRIPTION
    "
    Name      : Emb 7A-7B (G4P1) Status
    Menu Path : /Audio/Input Status
    Details   : Summary of embedded audio status.
    "
::= { enc1Params 1051 }

enc1P1051emb7A-7BG4P1StatusEntry OBJECT-TYPE
    SYNTAX Enc1P1051emb7A-7BG4P1StatusEntry
    MAX-ACCESS not-accessible
    STATUS     current
    DESCRIPTION
    "Table Entry for Emb 7A-7B (G4P1) Status"
    INDEX { slotId }
::= { enc1P1051emb7A-7BG4P1StatusTable 1 }

Enc1P1051emb7A-7BG4P1StatusEntry ::= SEQUENCE {
    enc1P1051emb7A-7BG4P1StatusValue    Enc1E101enumObj
}

enc1P1051emb7A-7BG4P1StatusValue OBJECT-TYPE
    SYNTAX     Enc1E101enumObj
    MAX-ACCESS read-only
    STATUS     current
    DESCRIPTION
    "Summary of embedded audio status."
::= { enc1P1051emb7A-7BG4P1StatusEntry 1 }

enc1P1052emb8A-8BG4P2StatusTable OBJECT-TYPE
    SYNTAX SEQUENCE OF Enc1P1052emb8A-8BG4P2StatusEntry
    MAX-ACCESS not-accessible
    STATUS     current
    DESCRIPTION
    "
    Name      : Emb 8A-8B (G4P2) Status
    Menu Path : /Audio/Input Status
    Details   : Summary of embedded audio status.
    "
::= { enc1Params 1052 }

enc1P1052emb8A-8BG4P2StatusEntry OBJECT-TYPE
    SYNTAX Enc1P1052emb8A-8BG4P2StatusEntry
    MAX-ACCESS not-accessible
    STATUS     current
    DESCRIPTION
    "Table Entry for Emb 8A-8B (G4P2) Status"
    INDEX { slotId }
::= { enc1P1052emb8A-8BG4P2StatusTable 1 }

Enc1P1052emb8A-8BG4P2StatusEntry ::= SEQUENCE {
    enc1P1052emb8A-8BG4P2StatusValue    Enc1E101enumObj
}

enc1P1052emb8A-8BG4P2StatusValue OBJECT-TYPE
    SYNTAX     Enc1E101enumObj
    MAX-ACCESS read-only
    STATUS     current
    DESCRIPTION
    "Summary of embedded audio status."
::= { enc1P1052emb8A-8BG4P2StatusEntry 1 }

enc1P1053emb1A-1BG1P1SampleRateTable OBJECT-TYPE
    SYNTAX SEQUENCE OF Enc1P1053emb1A-1BG1P1SampleRateEntry
    MAX-ACCESS not-accessible
    STATUS     current
    DESCRIPTION
    "
    Name      : Emb 1A-1B (G1P1) Sample Rate
    Menu Path : /Audio/Input Status
    Details   : Sample rate specified in AES channel block of embedded audio.
    "
::= { enc1Params 1053 }

enc1P1053emb1A-1BG1P1SampleRateEntry OBJECT-TYPE
    SYNTAX Enc1P1053emb1A-1BG1P1SampleRateEntry
    MAX-ACCESS not-accessible
    STATUS     current
    DESCRIPTION
    "Table Entry for Emb 1A-1B (G1P1) Sample Rate"
    INDEX { slotId }
::= { enc1P1053emb1A-1BG1P1SampleRateTable 1 }

Enc1P1053emb1A-1BG1P1SampleRateEntry ::= SEQUENCE {
    enc1P1053emb1A-1BG1P1SampleRateValue    Enc1E102enumObj
}

enc1P1053emb1A-1BG1P1SampleRateValue OBJECT-TYPE
    SYNTAX     Enc1E102enumObj
    MAX-ACCESS read-only
    STATUS     current
    DESCRIPTION
    "Sample rate specified in AES channel block of embedded audio."
::= { enc1P1053emb1A-1BG1P1SampleRateEntry 1 }

enc1P1054emb2A-2BG1P2SampleRateTable OBJECT-TYPE
    SYNTAX SEQUENCE OF Enc1P1054emb2A-2BG1P2SampleRateEntry
    MAX-ACCESS not-accessible
    STATUS     current
    DESCRIPTION
    "
    Name      : Emb 2A-2B (G1P2) Sample Rate
    Menu Path : /Audio/Input Status
    Details   : Sample rate specified in AES channel block of embedded audio.
    "
::= { enc1Params 1054 }

enc1P1054emb2A-2BG1P2SampleRateEntry OBJECT-TYPE
    SYNTAX Enc1P1054emb2A-2BG1P2SampleRateEntry
    MAX-ACCESS not-accessible
    STATUS     current
    DESCRIPTION
    "Table Entry for Emb 2A-2B (G1P2) Sample Rate"
    INDEX { slotId }
::= { enc1P1054emb2A-2BG1P2SampleRateTable 1 }

Enc1P1054emb2A-2BG1P2SampleRateEntry ::= SEQUENCE {
    enc1P1054emb2A-2BG1P2SampleRateValue    Enc1E102enumObj
}

enc1P1054emb2A-2BG1P2SampleRateValue OBJECT-TYPE
    SYNTAX     Enc1E102enumObj
    MAX-ACCESS read-only
    STATUS     current
    DESCRIPTION
    "Sample rate specified in AES channel block of embedded audio."
::= { enc1P1054emb2A-2BG1P2SampleRateEntry 1 }

enc1P1055emb3A-3BG2P1SampleRateTable OBJECT-TYPE
    SYNTAX SEQUENCE OF Enc1P1055emb3A-3BG2P1SampleRateEntry
    MAX-ACCESS not-accessible
    STATUS     current
    DESCRIPTION
    "
    Name      : Emb 3A-3B (G2P1) Sample Rate
    Menu Path : /Audio/Input Status
    Details   : Sample rate specified in AES channel block of embedded audio.
    "
::= { enc1Params 1055 }

enc1P1055emb3A-3BG2P1SampleRateEntry OBJECT-TYPE
    SYNTAX Enc1P1055emb3A-3BG2P1SampleRateEntry
    MAX-ACCESS not-accessible
    STATUS     current
    DESCRIPTION
    "Table Entry for Emb 3A-3B (G2P1) Sample Rate"
    INDEX { slotId }
::= { enc1P1055emb3A-3BG2P1SampleRateTable 1 }

Enc1P1055emb3A-3BG2P1SampleRateEntry ::= SEQUENCE {
    enc1P1055emb3A-3BG2P1SampleRateValue    Enc1E102enumObj
}

enc1P1055emb3A-3BG2P1SampleRateValue OBJECT-TYPE
    SYNTAX     Enc1E102enumObj
    MAX-ACCESS read-only
    STATUS     current
    DESCRIPTION
    "Sample rate specified in AES channel block of embedded audio."
::= { enc1P1055emb3A-3BG2P1SampleRateEntry 1 }

enc1P1056emb4A-4BG2P2SampleRateTable OBJECT-TYPE
    SYNTAX SEQUENCE OF Enc1P1056emb4A-4BG2P2SampleRateEntry
    MAX-ACCESS not-accessible
    STATUS     current
    DESCRIPTION
    "
    Name      : Emb 4A-4B (G2P2) Sample Rate
    Menu Path : /Audio/Input Status
    Details   : Sample rate specified in AES channel block of embedded audio.
    "
::= { enc1Params 1056 }

enc1P1056emb4A-4BG2P2SampleRateEntry OBJECT-TYPE
    SYNTAX Enc1P1056emb4A-4BG2P2SampleRateEntry
    MAX-ACCESS not-accessible
    STATUS     current
    DESCRIPTION
    "Table Entry for Emb 4A-4B (G2P2) Sample Rate"
    INDEX { slotId }
::= { enc1P1056emb4A-4BG2P2SampleRateTable 1 }

Enc1P1056emb4A-4BG2P2SampleRateEntry ::= SEQUENCE {
    enc1P1056emb4A-4BG2P2SampleRateValue    Enc1E102enumObj
}

enc1P1056emb4A-4BG2P2SampleRateValue OBJECT-TYPE
    SYNTAX     Enc1E102enumObj
    MAX-ACCESS read-only
    STATUS     current
    DESCRIPTION
    "Sample rate specified in AES channel block of embedded audio."
::= { enc1P1056emb4A-4BG2P2SampleRateEntry 1 }

enc1P1057emb5A-5BG3P1SampleRateTable OBJECT-TYPE
    SYNTAX SEQUENCE OF Enc1P1057emb5A-5BG3P1SampleRateEntry
    MAX-ACCESS not-accessible
    STATUS     current
    DESCRIPTION
    "
    Name      : Emb 5A-5B (G3P1) Sample Rate
    Menu Path : /Audio/Input Status
    Details   : Sample rate specified in AES channel block of embedded audio.
    "
::= { enc1Params 1057 }

enc1P1057emb5A-5BG3P1SampleRateEntry OBJECT-TYPE
    SYNTAX Enc1P1057emb5A-5BG3P1SampleRateEntry
    MAX-ACCESS not-accessible
    STATUS     current
    DESCRIPTION
    "Table Entry for Emb 5A-5B (G3P1) Sample Rate"
    INDEX { slotId }
::= { enc1P1057emb5A-5BG3P1SampleRateTable 1 }

Enc1P1057emb5A-5BG3P1SampleRateEntry ::= SEQUENCE {
    enc1P1057emb5A-5BG3P1SampleRateValue    Enc1E102enumObj
}

enc1P1057emb5A-5BG3P1SampleRateValue OBJECT-TYPE
    SYNTAX     Enc1E102enumObj
    MAX-ACCESS read-only
    STATUS     current
    DESCRIPTION
    "Sample rate specified in AES channel block of embedded audio."
::= { enc1P1057emb5A-5BG3P1SampleRateEntry 1 }

enc1P1058emb6A-6BG3P2SampleRateTable OBJECT-TYPE
    SYNTAX SEQUENCE OF Enc1P1058emb6A-6BG3P2SampleRateEntry
    MAX-ACCESS not-accessible
    STATUS     current
    DESCRIPTION
    "
    Name      : Emb 6A-6B (G3P2) Sample Rate
    Menu Path : /Audio/Input Status
    Details   : Sample rate specified in AES channel block of embedded audio.
    "
::= { enc1Params 1058 }

enc1P1058emb6A-6BG3P2SampleRateEntry OBJECT-TYPE
    SYNTAX Enc1P1058emb6A-6BG3P2SampleRateEntry
    MAX-ACCESS not-accessible
    STATUS     current
    DESCRIPTION
    "Table Entry for Emb 6A-6B (G3P2) Sample Rate"
    INDEX { slotId }
::= { enc1P1058emb6A-6BG3P2SampleRateTable 1 }

Enc1P1058emb6A-6BG3P2SampleRateEntry ::= SEQUENCE {
    enc1P1058emb6A-6BG3P2SampleRateValue    Enc1E102enumObj
}

enc1P1058emb6A-6BG3P2SampleRateValue OBJECT-TYPE
    SYNTAX     Enc1E102enumObj
    MAX-ACCESS read-only
    STATUS     current
    DESCRIPTION
    "Sample rate specified in AES channel block of embedded audio."
::= { enc1P1058emb6A-6BG3P2SampleRateEntry 1 }

enc1P1059emb7A-7BG4P1SampleRateTable OBJECT-TYPE
    SYNTAX SEQUENCE OF Enc1P1059emb7A-7BG4P1SampleRateEntry
    MAX-ACCESS not-accessible
    STATUS     current
    DESCRIPTION
    "
    Name      : Emb 7A-7B (G4P1) Sample Rate
    Menu Path : /Audio/Input Status
    Details   : Sample rate specified in AES channel block of embedded audio.
    "
::= { enc1Params 1059 }

enc1P1059emb7A-7BG4P1SampleRateEntry OBJECT-TYPE
    SYNTAX Enc1P1059emb7A-7BG4P1SampleRateEntry
    MAX-ACCESS not-accessible
    STATUS     current
    DESCRIPTION
    "Table Entry for Emb 7A-7B (G4P1) Sample Rate"
    INDEX { slotId }
::= { enc1P1059emb7A-7BG4P1SampleRateTable 1 }

Enc1P1059emb7A-7BG4P1SampleRateEntry ::= SEQUENCE {
    enc1P1059emb7A-7BG4P1SampleRateValue    Enc1E102enumObj
}

enc1P1059emb7A-7BG4P1SampleRateValue OBJECT-TYPE
    SYNTAX     Enc1E102enumObj
    MAX-ACCESS read-only
    STATUS     current
    DESCRIPTION
    "Sample rate specified in AES channel block of embedded audio."
::= { enc1P1059emb7A-7BG4P1SampleRateEntry 1 }

enc1P1060emb8A-8BG4P2SampleRateTable OBJECT-TYPE
    SYNTAX SEQUENCE OF Enc1P1060emb8A-8BG4P2SampleRateEntry
    MAX-ACCESS not-accessible
    STATUS     current
    DESCRIPTION
    "
    Name      : Emb 8A-8B (G4P2) Sample Rate
    Menu Path : /Audio/Input Status
    Details   : Sample rate specified in AES channel block of embedded audio.
    "
::= { enc1Params 1060 }

enc1P1060emb8A-8BG4P2SampleRateEntry OBJECT-TYPE
    SYNTAX Enc1P1060emb8A-8BG4P2SampleRateEntry
    MAX-ACCESS not-accessible
    STATUS     current
    DESCRIPTION
    "Table Entry for Emb 8A-8B (G4P2) Sample Rate"
    INDEX { slotId }
::= { enc1P1060emb8A-8BG4P2SampleRateTable 1 }

Enc1P1060emb8A-8BG4P2SampleRateEntry ::= SEQUENCE {
    enc1P1060emb8A-8BG4P2SampleRateValue    Enc1E102enumObj
}

enc1P1060emb8A-8BG4P2SampleRateValue OBJECT-TYPE
    SYNTAX     Enc1E102enumObj
    MAX-ACCESS read-only
    STATUS     current
    DESCRIPTION
    "Sample rate specified in AES channel block of embedded audio."
::= { enc1P1060emb8A-8BG4P2SampleRateEntry 1 }

enc1P1061subtitleRateTable OBJECT-TYPE
    SYNTAX SEQUENCE OF Enc1P1061subtitleRateEntry
    MAX-ACCESS not-accessible
    STATUS     current
    DESCRIPTION
    "
    Name      : Subtitle Rate
    Menu Path : /Data/Status
    Units     : Mbits/sec
    Precision : 6
    Low Range : 0
    High Range: 5000000
    Details   : Shows the combined average bitrate for all Subtitle streams. (Units: Mbits/sec)

     NOTE: Precision/Units/Ranges represent the state of the
           parameter during the MIB generation, and does not
           neccessary reflect the current state of the parameter
    "
::= { enc1Params 1061 }

enc1P1061subtitleRateEntry OBJECT-TYPE
    SYNTAX Enc1P1061subtitleRateEntry
    MAX-ACCESS not-accessible
    STATUS     current
    DESCRIPTION
    "Table Entry for Subtitle Rate"
    INDEX { slotId }
::= { enc1P1061subtitleRateTable 1 }

Enc1P1061subtitleRateEntry ::= SEQUENCE {
    enc1P1061subtitleRateValue    INTEGER
}

enc1P1061subtitleRateValue OBJECT-TYPE
    SYNTAX     INTEGER
    MAX-ACCESS read-only
    STATUS     current
    DESCRIPTION
    "Shows the combined average bitrate for all Subtitle streams. (Units: Mbits/sec)"
::= { enc1P1061subtitleRateEntry 1 }

enc1P1062subtitleDropTable OBJECT-TYPE
    SYNTAX SEQUENCE OF Enc1P1062subtitleDropEntry
    MAX-ACCESS not-accessible
    STATUS     current
    DESCRIPTION
    "
    Name      : Subtitle Drop
    Menu Path : /Data/Status
    Units     : 
    Precision : 0
    Low Range : 0
    High Range: -1
    Details   : Shows the number of dropped Subtitle packets

     NOTE: Precision/Units/Ranges represent the state of the
           parameter during the MIB generation, and does not
           neccessary reflect the current state of the parameter
    "
::= { enc1Params 1062 }

enc1P1062subtitleDropEntry OBJECT-TYPE
    SYNTAX Enc1P1062subtitleDropEntry
    MAX-ACCESS not-accessible
    STATUS     current
    DESCRIPTION
    "Table Entry for Subtitle Drop"
    INDEX { slotId }
::= { enc1P1062subtitleDropTable 1 }

Enc1P1062subtitleDropEntry ::= SEQUENCE {
    enc1P1062subtitleDropValue    INTEGER
}

enc1P1062subtitleDropValue OBJECT-TYPE
    SYNTAX     INTEGER
    MAX-ACCESS read-only
    STATUS     current
    DESCRIPTION
    "Shows the number of dropped Subtitle packets"
::= { enc1P1062subtitleDropEntry 1 }

enc1P1063fecinterleaveTable OBJECT-TYPE
    SYNTAX SEQUENCE OF Enc1P1063fecinterleaveEntry
    MAX-ACCESS not-accessible
    STATUS     current
    DESCRIPTION
    "
    Name      : FEC Interleave
    Menu Path : /IP Encapsulation/Main Program IP
    Details   : Specifies the mode for FEC interleaving as described in Annex A (non block aligned) and Annex B (block aligned) of Pro-MPEG Code of Practice #3 release 2. July 2004
    "
::= { enc1Params 1063 }

enc1P1063fecinterleaveEntry OBJECT-TYPE
    SYNTAX Enc1P1063fecinterleaveEntry
    MAX-ACCESS not-accessible
    STATUS     current
    DESCRIPTION
    "Table Entry for FEC Interleave"
    INDEX { slotId }
::= { enc1P1063fecinterleaveTable 1 }

Enc1P1063fecinterleaveEntry ::= SEQUENCE {
    enc1P1063fecinterleaveValue    Enc1E141enumObj
}

enc1P1063fecinterleaveValue OBJECT-TYPE
    SYNTAX     Enc1E141enumObj
    MAX-ACCESS read-write
    STATUS     current
    DESCRIPTION
    "Specifies the mode for FEC interleaving as described in Annex A (non block aligned) and Annex B (block aligned) of Pro-MPEG Code of Practice #3 release 2. July 2004"
::= { enc1P1063fecinterleaveEntry 1 }

enc1P1064transmitInterfaceTable OBJECT-TYPE
    SYNTAX SEQUENCE OF Enc1P1064transmitInterfaceEntry
    MAX-ACCESS not-accessible
    STATUS     current
    DESCRIPTION
    "
    Name      : Transmit Interface
    Menu Path : /IP Encapsulation/Main Program IP
    Details   : Specifies whether IP output should be transmitted on both primary and secondary data interfaces or only one interface. If 'Both' is selected then the IP output will be sent on both the primary and secondary data ethernet interfaces. If 'Active Controller' is selected, then the IP output will be transmitted only on the primary data Ethernet interface when the primary controller is active or the secondary data Ehternet does not have a good link status. It will be sent only on the secondary data ethernet inteface if the secondary controller is active or the primary data ethernet does not have a good link status.
    "
::= { enc1Params 1064 }

enc1P1064transmitInterfaceEntry OBJECT-TYPE
    SYNTAX Enc1P1064transmitInterfaceEntry
    MAX-ACCESS not-accessible
    STATUS     current
    DESCRIPTION
    "Table Entry for Transmit Interface"
    INDEX { slotId }
::= { enc1P1064transmitInterfaceTable 1 }

Enc1P1064transmitInterfaceEntry ::= SEQUENCE {
    enc1P1064transmitInterfaceValue    Enc1E142enumObj
}

enc1P1064transmitInterfaceValue OBJECT-TYPE
    SYNTAX     Enc1E142enumObj
    MAX-ACCESS read-write
    STATUS     current
    DESCRIPTION
    "Specifies whether IP output should be transmitted on both primary and secondary data interfaces or only one interface. If 'Both' is selected then the IP output will be sent on both the primary and secondary data ethernet interfaces. If 'Active Controller' is selected, then the IP output will be transmitted only on the primary data Ethernet interface when the primary controller is active or the secondary data Ehternet does not have a good link status. It will be sent only on the secondary data ethernet inteface if the secondary controller is active or the primary data ethernet does not have a good link status."
::= { enc1P1064transmitInterfaceEntry 1 }

enc1P1065fecinterleaveTable OBJECT-TYPE
    SYNTAX SEQUENCE OF Enc1P1065fecinterleaveEntry
    MAX-ACCESS not-accessible
    STATUS     current
    DESCRIPTION
    "
    Name      : FEC Interleave
    Menu Path : /IP Encapsulation/Pip Program IP
    Details   : Specifies the mode for FEC interleaving as described in Annex A (non block aligned) and Annex B (block aligned) of Pro-MPEG Code of Practice #3 release 2. July 2004
    "
::= { enc1Params 1065 }

enc1P1065fecinterleaveEntry OBJECT-TYPE
    SYNTAX Enc1P1065fecinterleaveEntry
    MAX-ACCESS not-accessible
    STATUS     current
    DESCRIPTION
    "Table Entry for FEC Interleave"
    INDEX { slotId }
::= { enc1P1065fecinterleaveTable 1 }

Enc1P1065fecinterleaveEntry ::= SEQUENCE {
    enc1P1065fecinterleaveValue    Enc1E141enumObj
}

enc1P1065fecinterleaveValue OBJECT-TYPE
    SYNTAX     Enc1E141enumObj
    MAX-ACCESS read-write
    STATUS     current
    DESCRIPTION
    "Specifies the mode for FEC interleaving as described in Annex A (non block aligned) and Annex B (block aligned) of Pro-MPEG Code of Practice #3 release 2. July 2004"
::= { enc1P1065fecinterleaveEntry 1 }

enc1P1066transmitInterfaceTable OBJECT-TYPE
    SYNTAX SEQUENCE OF Enc1P1066transmitInterfaceEntry
    MAX-ACCESS not-accessible
    STATUS     current
    DESCRIPTION
    "
    Name      : Transmit Interface
    Menu Path : /IP Encapsulation/Pip Program IP
    Details   : Specifies whether IP output should be transmitted on both primary and secondary data interfaces or only on the active controller's interface.
    "
::= { enc1Params 1066 }

enc1P1066transmitInterfaceEntry OBJECT-TYPE
    SYNTAX Enc1P1066transmitInterfaceEntry
    MAX-ACCESS not-accessible
    STATUS     current
    DESCRIPTION
    "Table Entry for Transmit Interface"
    INDEX { slotId }
::= { enc1P1066transmitInterfaceTable 1 }

Enc1P1066transmitInterfaceEntry ::= SEQUENCE {
    enc1P1066transmitInterfaceValue    Enc1E143enumObj
}

enc1P1066transmitInterfaceValue OBJECT-TYPE
    SYNTAX     Enc1E143enumObj
    MAX-ACCESS read-write
    STATUS     current
    DESCRIPTION
    "Specifies whether IP output should be transmitted on both primary and secondary data interfaces or only on the active controller's interface."
::= { enc1P1066transmitInterfaceEntry 1 }

enc1P1070configurationErrorTable OBJECT-TYPE
    SYNTAX SEQUENCE OF Enc1P1070configurationErrorEntry
    MAX-ACCESS not-accessible
    STATUS     current
    DESCRIPTION
    "
    Name      : Configuration Error
    Menu Path : /Audio/Audio 1/Status
    Details   : Displays any current audio configuration error impacting this stream.
    "
::= { enc1Params 1070 }

enc1P1070configurationErrorEntry OBJECT-TYPE
    SYNTAX Enc1P1070configurationErrorEntry
    MAX-ACCESS not-accessible
    STATUS     current
    DESCRIPTION
    "Table Entry for Configuration Error"
    INDEX { slotId }
::= { enc1P1070configurationErrorTable 1 }

Enc1P1070configurationErrorEntry ::= SEQUENCE {
    enc1P1070configurationErrorValue    DisplayString
}

enc1P1070configurationErrorValue OBJECT-TYPE
    SYNTAX     DisplayString
    MAX-ACCESS read-only
    STATUS     current
    DESCRIPTION
    "Displays any current audio configuration error impacting this stream."
::= { enc1P1070configurationErrorEntry 1 }

enc1P1071configurationErrorTable OBJECT-TYPE
    SYNTAX SEQUENCE OF Enc1P1071configurationErrorEntry
    MAX-ACCESS not-accessible
    STATUS     current
    DESCRIPTION
    "
    Name      : Configuration Error
    Menu Path : /Audio/Audio 2/Status
    Details   : Displays any current audio configuration error impacting this stream.
    "
::= { enc1Params 1071 }

enc1P1071configurationErrorEntry OBJECT-TYPE
    SYNTAX Enc1P1071configurationErrorEntry
    MAX-ACCESS not-accessible
    STATUS     current
    DESCRIPTION
    "Table Entry for Configuration Error"
    INDEX { slotId }
::= { enc1P1071configurationErrorTable 1 }

Enc1P1071configurationErrorEntry ::= SEQUENCE {
    enc1P1071configurationErrorValue    DisplayString
}

enc1P1071configurationErrorValue OBJECT-TYPE
    SYNTAX     DisplayString
    MAX-ACCESS read-only
    STATUS     current
    DESCRIPTION
    "Displays any current audio configuration error impacting this stream."
::= { enc1P1071configurationErrorEntry 1 }

enc1P1072configurationErrorTable OBJECT-TYPE
    SYNTAX SEQUENCE OF Enc1P1072configurationErrorEntry
    MAX-ACCESS not-accessible
    STATUS     current
    DESCRIPTION
    "
    Name      : Configuration Error
    Menu Path : /Audio/Audio 3/Status
    Details   : Displays any current audio configuration error impacting this stream.
    "
::= { enc1Params 1072 }

enc1P1072configurationErrorEntry OBJECT-TYPE
    SYNTAX Enc1P1072configurationErrorEntry
    MAX-ACCESS not-accessible
    STATUS     current
    DESCRIPTION
    "Table Entry for Configuration Error"
    INDEX { slotId }
::= { enc1P1072configurationErrorTable 1 }

Enc1P1072configurationErrorEntry ::= SEQUENCE {
    enc1P1072configurationErrorValue    DisplayString
}

enc1P1072configurationErrorValue OBJECT-TYPE
    SYNTAX     DisplayString
    MAX-ACCESS read-only
    STATUS     current
    DESCRIPTION
    "Displays any current audio configuration error impacting this stream."
::= { enc1P1072configurationErrorEntry 1 }

enc1P1073configurationErrorTable OBJECT-TYPE
    SYNTAX SEQUENCE OF Enc1P1073configurationErrorEntry
    MAX-ACCESS not-accessible
    STATUS     current
    DESCRIPTION
    "
    Name      : Configuration Error
    Menu Path : /Audio/Audio 4/Status
    Details   : Displays any current audio configuration error impacting this stream.
    "
::= { enc1Params 1073 }

enc1P1073configurationErrorEntry OBJECT-TYPE
    SYNTAX Enc1P1073configurationErrorEntry
    MAX-ACCESS not-accessible
    STATUS     current
    DESCRIPTION
    "Table Entry for Configuration Error"
    INDEX { slotId }
::= { enc1P1073configurationErrorTable 1 }

Enc1P1073configurationErrorEntry ::= SEQUENCE {
    enc1P1073configurationErrorValue    DisplayString
}

enc1P1073configurationErrorValue OBJECT-TYPE
    SYNTAX     DisplayString
    MAX-ACCESS read-only
    STATUS     current
    DESCRIPTION
    "Displays any current audio configuration error impacting this stream."
::= { enc1P1073configurationErrorEntry 1 }

enc1P1074configurationErrorTable OBJECT-TYPE
    SYNTAX SEQUENCE OF Enc1P1074configurationErrorEntry
    MAX-ACCESS not-accessible
    STATUS     current
    DESCRIPTION
    "
    Name      : Configuration Error
    Menu Path : /Audio/Audio 5/Status
    Details   : Displays any current audio configuration error impacting this stream.
    "
::= { enc1Params 1074 }

enc1P1074configurationErrorEntry OBJECT-TYPE
    SYNTAX Enc1P1074configurationErrorEntry
    MAX-ACCESS not-accessible
    STATUS     current
    DESCRIPTION
    "Table Entry for Configuration Error"
    INDEX { slotId }
::= { enc1P1074configurationErrorTable 1 }

Enc1P1074configurationErrorEntry ::= SEQUENCE {
    enc1P1074configurationErrorValue    DisplayString
}

enc1P1074configurationErrorValue OBJECT-TYPE
    SYNTAX     DisplayString
    MAX-ACCESS read-only
    STATUS     current
    DESCRIPTION
    "Displays any current audio configuration error impacting this stream."
::= { enc1P1074configurationErrorEntry 1 }

enc1P1075configurationErrorTable OBJECT-TYPE
    SYNTAX SEQUENCE OF Enc1P1075configurationErrorEntry
    MAX-ACCESS not-accessible
    STATUS     current
    DESCRIPTION
    "
    Name      : Configuration Error
    Menu Path : /Audio/Audio 6/Status
    Details   : Displays any current audio configuration error impacting this stream.
    "
::= { enc1Params 1075 }

enc1P1075configurationErrorEntry OBJECT-TYPE
    SYNTAX Enc1P1075configurationErrorEntry
    MAX-ACCESS not-accessible
    STATUS     current
    DESCRIPTION
    "Table Entry for Configuration Error"
    INDEX { slotId }
::= { enc1P1075configurationErrorTable 1 }

Enc1P1075configurationErrorEntry ::= SEQUENCE {
    enc1P1075configurationErrorValue    DisplayString
}

enc1P1075configurationErrorValue OBJECT-TYPE
    SYNTAX     DisplayString
    MAX-ACCESS read-only
    STATUS     current
    DESCRIPTION
    "Displays any current audio configuration error impacting this stream."
::= { enc1P1075configurationErrorEntry 1 }

enc1P1076configurationErrorTable OBJECT-TYPE
    SYNTAX SEQUENCE OF Enc1P1076configurationErrorEntry
    MAX-ACCESS not-accessible
    STATUS     current
    DESCRIPTION
    "
    Name      : Configuration Error
    Menu Path : /Audio/Audio 7/Status
    Details   : Displays any current audio configuration error impacting this stream.
    "
::= { enc1Params 1076 }

enc1P1076configurationErrorEntry OBJECT-TYPE
    SYNTAX Enc1P1076configurationErrorEntry
    MAX-ACCESS not-accessible
    STATUS     current
    DESCRIPTION
    "Table Entry for Configuration Error"
    INDEX { slotId }
::= { enc1P1076configurationErrorTable 1 }

Enc1P1076configurationErrorEntry ::= SEQUENCE {
    enc1P1076configurationErrorValue    DisplayString
}

enc1P1076configurationErrorValue OBJECT-TYPE
    SYNTAX     DisplayString
    MAX-ACCESS read-only
    STATUS     current
    DESCRIPTION
    "Displays any current audio configuration error impacting this stream."
::= { enc1P1076configurationErrorEntry 1 }

enc1P1077configurationErrorTable OBJECT-TYPE
    SYNTAX SEQUENCE OF Enc1P1077configurationErrorEntry
    MAX-ACCESS not-accessible
    STATUS     current
    DESCRIPTION
    "
    Name      : Configuration Error
    Menu Path : /Audio/Audio 8/Status
    Details   : Displays any current audio configuration error impacting this stream.
    "
::= { enc1Params 1077 }

enc1P1077configurationErrorEntry OBJECT-TYPE
    SYNTAX Enc1P1077configurationErrorEntry
    MAX-ACCESS not-accessible
    STATUS     current
    DESCRIPTION
    "Table Entry for Configuration Error"
    INDEX { slotId }
::= { enc1P1077configurationErrorTable 1 }

Enc1P1077configurationErrorEntry ::= SEQUENCE {
    enc1P1077configurationErrorValue    DisplayString
}

enc1P1077configurationErrorValue OBJECT-TYPE
    SYNTAX     DisplayString
    MAX-ACCESS read-only
    STATUS     current
    DESCRIPTION
    "Displays any current audio configuration error impacting this stream."
::= { enc1P1077configurationErrorEntry 1 }

enc1P1078romversionTable OBJECT-TYPE
    SYNTAX SEQUENCE OF Enc1P1078romversionEntry
    MAX-ACCESS not-accessible
    STATUS     current
    DESCRIPTION
    "
    Name      : ROM Version
    Menu Path : /Misc
    Details   : Version of the ROM.
    "
::= { enc1Params 1078 }

enc1P1078romversionEntry OBJECT-TYPE
    SYNTAX Enc1P1078romversionEntry
    MAX-ACCESS not-accessible
    STATUS     current
    DESCRIPTION
    "Table Entry for ROM Version"
    INDEX { slotId }
::= { enc1P1078romversionTable 1 }

Enc1P1078romversionEntry ::= SEQUENCE {
    enc1P1078romversionValue    DisplayString
}

enc1P1078romversionValue OBJECT-TYPE
    SYNTAX     DisplayString
    MAX-ACCESS read-only
    STATUS     current
    DESCRIPTION
    "Version of the ROM."
::= { enc1P1078romversionEntry 1 }

enc1P1080metadataSourceInUseTable OBJECT-TYPE
    SYNTAX SEQUENCE OF Enc1P1080metadataSourceInUseEntry
    MAX-ACCESS not-accessible
    STATUS     current
    DESCRIPTION
    "
    Name      : Metadata Source In Use
    Menu Path : /Audio/Audio 1/Metadata
    Details   : Indicates current audio metadata source or reversion.
    "
::= { enc1Params 1080 }

enc1P1080metadataSourceInUseEntry OBJECT-TYPE
    SYNTAX Enc1P1080metadataSourceInUseEntry
    MAX-ACCESS not-accessible
    STATUS     current
    DESCRIPTION
    "Table Entry for Metadata Source In Use"
    INDEX { slotId }
::= { enc1P1080metadataSourceInUseTable 1 }

Enc1P1080metadataSourceInUseEntry ::= SEQUENCE {
    enc1P1080metadataSourceInUseValue    Enc1E103enumObj
}

enc1P1080metadataSourceInUseValue OBJECT-TYPE
    SYNTAX     Enc1E103enumObj
    MAX-ACCESS read-only
    STATUS     current
    DESCRIPTION
    "Indicates current audio metadata source or reversion."
::= { enc1P1080metadataSourceInUseEntry 1 }

enc1P1081externalMetadataErrorTable OBJECT-TYPE
    SYNTAX SEQUENCE OF Enc1P1081externalMetadataErrorEntry
    MAX-ACCESS not-accessible
    STATUS     current
    DESCRIPTION
    "
    Name      : External Metadata Error
    Menu Path : /Audio/Audio 1/Metadata
    Details   : Indicates any current error in external metadata.
    "
::= { enc1Params 1081 }

enc1P1081externalMetadataErrorEntry OBJECT-TYPE
    SYNTAX Enc1P1081externalMetadataErrorEntry
    MAX-ACCESS not-accessible
    STATUS     current
    DESCRIPTION
    "Table Entry for External Metadata Error"
    INDEX { slotId }
::= { enc1P1081externalMetadataErrorTable 1 }

Enc1P1081externalMetadataErrorEntry ::= SEQUENCE {
    enc1P1081externalMetadataErrorValue    Enc1E104enumObj
}

enc1P1081externalMetadataErrorValue OBJECT-TYPE
    SYNTAX     Enc1E104enumObj
    MAX-ACCESS read-only
    STATUS     current
    DESCRIPTION
    "Indicates any current error in external metadata."
::= { enc1P1081externalMetadataErrorEntry 1 }

enc1P1082metadataSourceInUseTable OBJECT-TYPE
    SYNTAX SEQUENCE OF Enc1P1082metadataSourceInUseEntry
    MAX-ACCESS not-accessible
    STATUS     current
    DESCRIPTION
    "
    Name      : Metadata Source In Use
    Menu Path : /Audio/Audio 2/Metadata
    Details   : Indicates current audio metadata source or reversion.
    "
::= { enc1Params 1082 }

enc1P1082metadataSourceInUseEntry OBJECT-TYPE
    SYNTAX Enc1P1082metadataSourceInUseEntry
    MAX-ACCESS not-accessible
    STATUS     current
    DESCRIPTION
    "Table Entry for Metadata Source In Use"
    INDEX { slotId }
::= { enc1P1082metadataSourceInUseTable 1 }

Enc1P1082metadataSourceInUseEntry ::= SEQUENCE {
    enc1P1082metadataSourceInUseValue    Enc1E103enumObj
}

enc1P1082metadataSourceInUseValue OBJECT-TYPE
    SYNTAX     Enc1E103enumObj
    MAX-ACCESS read-only
    STATUS     current
    DESCRIPTION
    "Indicates current audio metadata source or reversion."
::= { enc1P1082metadataSourceInUseEntry 1 }

enc1P1083externalMetadataErrorTable OBJECT-TYPE
    SYNTAX SEQUENCE OF Enc1P1083externalMetadataErrorEntry
    MAX-ACCESS not-accessible
    STATUS     current
    DESCRIPTION
    "
    Name      : External Metadata Error
    Menu Path : /Audio/Audio 2/Metadata
    Details   : Indicates any current error in external metadata.
    "
::= { enc1Params 1083 }

enc1P1083externalMetadataErrorEntry OBJECT-TYPE
    SYNTAX Enc1P1083externalMetadataErrorEntry
    MAX-ACCESS not-accessible
    STATUS     current
    DESCRIPTION
    "Table Entry for External Metadata Error"
    INDEX { slotId }
::= { enc1P1083externalMetadataErrorTable 1 }

Enc1P1083externalMetadataErrorEntry ::= SEQUENCE {
    enc1P1083externalMetadataErrorValue    Enc1E104enumObj
}

enc1P1083externalMetadataErrorValue OBJECT-TYPE
    SYNTAX     Enc1E104enumObj
    MAX-ACCESS read-only
    STATUS     current
    DESCRIPTION
    "Indicates any current error in external metadata."
::= { enc1P1083externalMetadataErrorEntry 1 }

enc1P1084metadataSourceInUseTable OBJECT-TYPE
    SYNTAX SEQUENCE OF Enc1P1084metadataSourceInUseEntry
    MAX-ACCESS not-accessible
    STATUS     current
    DESCRIPTION
    "
    Name      : Metadata Source In Use
    Menu Path : /Audio/Audio 3/Metadata
    Details   : Indicates current audio metadata source or reversion.
    "
::= { enc1Params 1084 }

enc1P1084metadataSourceInUseEntry OBJECT-TYPE
    SYNTAX Enc1P1084metadataSourceInUseEntry
    MAX-ACCESS not-accessible
    STATUS     current
    DESCRIPTION
    "Table Entry for Metadata Source In Use"
    INDEX { slotId }
::= { enc1P1084metadataSourceInUseTable 1 }

Enc1P1084metadataSourceInUseEntry ::= SEQUENCE {
    enc1P1084metadataSourceInUseValue    Enc1E103enumObj
}

enc1P1084metadataSourceInUseValue OBJECT-TYPE
    SYNTAX     Enc1E103enumObj
    MAX-ACCESS read-only
    STATUS     current
    DESCRIPTION
    "Indicates current audio metadata source or reversion."
::= { enc1P1084metadataSourceInUseEntry 1 }

enc1P1085externalMetadataErrorTable OBJECT-TYPE
    SYNTAX SEQUENCE OF Enc1P1085externalMetadataErrorEntry
    MAX-ACCESS not-accessible
    STATUS     current
    DESCRIPTION
    "
    Name      : External Metadata Error
    Menu Path : /Audio/Audio 3/Metadata
    Details   : Indicates any current error in external metadata.
    "
::= { enc1Params 1085 }

enc1P1085externalMetadataErrorEntry OBJECT-TYPE
    SYNTAX Enc1P1085externalMetadataErrorEntry
    MAX-ACCESS not-accessible
    STATUS     current
    DESCRIPTION
    "Table Entry for External Metadata Error"
    INDEX { slotId }
::= { enc1P1085externalMetadataErrorTable 1 }

Enc1P1085externalMetadataErrorEntry ::= SEQUENCE {
    enc1P1085externalMetadataErrorValue    Enc1E104enumObj
}

enc1P1085externalMetadataErrorValue OBJECT-TYPE
    SYNTAX     Enc1E104enumObj
    MAX-ACCESS read-only
    STATUS     current
    DESCRIPTION
    "Indicates any current error in external metadata."
::= { enc1P1085externalMetadataErrorEntry 1 }

enc1P1086metadataSourceInUseTable OBJECT-TYPE
    SYNTAX SEQUENCE OF Enc1P1086metadataSourceInUseEntry
    MAX-ACCESS not-accessible
    STATUS     current
    DESCRIPTION
    "
    Name      : Metadata Source In Use
    Menu Path : /Audio/Audio 4/Metadata
    Details   : Indicates current audio metadata source or reversion.
    "
::= { enc1Params 1086 }

enc1P1086metadataSourceInUseEntry OBJECT-TYPE
    SYNTAX Enc1P1086metadataSourceInUseEntry
    MAX-ACCESS not-accessible
    STATUS     current
    DESCRIPTION
    "Table Entry for Metadata Source In Use"
    INDEX { slotId }
::= { enc1P1086metadataSourceInUseTable 1 }

Enc1P1086metadataSourceInUseEntry ::= SEQUENCE {
    enc1P1086metadataSourceInUseValue    Enc1E103enumObj
}

enc1P1086metadataSourceInUseValue OBJECT-TYPE
    SYNTAX     Enc1E103enumObj
    MAX-ACCESS read-only
    STATUS     current
    DESCRIPTION
    "Indicates current audio metadata source or reversion."
::= { enc1P1086metadataSourceInUseEntry 1 }

enc1P1087externalMetadataErrorTable OBJECT-TYPE
    SYNTAX SEQUENCE OF Enc1P1087externalMetadataErrorEntry
    MAX-ACCESS not-accessible
    STATUS     current
    DESCRIPTION
    "
    Name      : External Metadata Error
    Menu Path : /Audio/Audio 4/Metadata
    Details   : Indicates any current error in external metadata.
    "
::= { enc1Params 1087 }

enc1P1087externalMetadataErrorEntry OBJECT-TYPE
    SYNTAX Enc1P1087externalMetadataErrorEntry
    MAX-ACCESS not-accessible
    STATUS     current
    DESCRIPTION
    "Table Entry for External Metadata Error"
    INDEX { slotId }
::= { enc1P1087externalMetadataErrorTable 1 }

Enc1P1087externalMetadataErrorEntry ::= SEQUENCE {
    enc1P1087externalMetadataErrorValue    Enc1E104enumObj
}

enc1P1087externalMetadataErrorValue OBJECT-TYPE
    SYNTAX     Enc1E104enumObj
    MAX-ACCESS read-only
    STATUS     current
    DESCRIPTION
    "Indicates any current error in external metadata."
::= { enc1P1087externalMetadataErrorEntry 1 }

enc1P1088metadataSourceInUseTable OBJECT-TYPE
    SYNTAX SEQUENCE OF Enc1P1088metadataSourceInUseEntry
    MAX-ACCESS not-accessible
    STATUS     current
    DESCRIPTION
    "
    Name      : Metadata Source In Use
    Menu Path : /Audio/Audio 5/Metadata
    Details   : Indicates current audio metadata source or reversion.
    "
::= { enc1Params 1088 }

enc1P1088metadataSourceInUseEntry OBJECT-TYPE
    SYNTAX Enc1P1088metadataSourceInUseEntry
    MAX-ACCESS not-accessible
    STATUS     current
    DESCRIPTION
    "Table Entry for Metadata Source In Use"
    INDEX { slotId }
::= { enc1P1088metadataSourceInUseTable 1 }

Enc1P1088metadataSourceInUseEntry ::= SEQUENCE {
    enc1P1088metadataSourceInUseValue    Enc1E103enumObj
}

enc1P1088metadataSourceInUseValue OBJECT-TYPE
    SYNTAX     Enc1E103enumObj
    MAX-ACCESS read-only
    STATUS     current
    DESCRIPTION
    "Indicates current audio metadata source or reversion."
::= { enc1P1088metadataSourceInUseEntry 1 }

enc1P1089externalMetadataErrorTable OBJECT-TYPE
    SYNTAX SEQUENCE OF Enc1P1089externalMetadataErrorEntry
    MAX-ACCESS not-accessible
    STATUS     current
    DESCRIPTION
    "
    Name      : External Metadata Error
    Menu Path : /Audio/Audio 5/Metadata
    Details   : Indicates any current error in external metadata.
    "
::= { enc1Params 1089 }

enc1P1089externalMetadataErrorEntry OBJECT-TYPE
    SYNTAX Enc1P1089externalMetadataErrorEntry
    MAX-ACCESS not-accessible
    STATUS     current
    DESCRIPTION
    "Table Entry for External Metadata Error"
    INDEX { slotId }
::= { enc1P1089externalMetadataErrorTable 1 }

Enc1P1089externalMetadataErrorEntry ::= SEQUENCE {
    enc1P1089externalMetadataErrorValue    Enc1E104enumObj
}

enc1P1089externalMetadataErrorValue OBJECT-TYPE
    SYNTAX     Enc1E104enumObj
    MAX-ACCESS read-only
    STATUS     current
    DESCRIPTION
    "Indicates any current error in external metadata."
::= { enc1P1089externalMetadataErrorEntry 1 }

enc1P1090metadataSourceInUseTable OBJECT-TYPE
    SYNTAX SEQUENCE OF Enc1P1090metadataSourceInUseEntry
    MAX-ACCESS not-accessible
    STATUS     current
    DESCRIPTION
    "
    Name      : Metadata Source In Use
    Menu Path : /Audio/Audio 6/Metadata
    Details   : Indicates current audio metadata source or reversion.
    "
::= { enc1Params 1090 }

enc1P1090metadataSourceInUseEntry OBJECT-TYPE
    SYNTAX Enc1P1090metadataSourceInUseEntry
    MAX-ACCESS not-accessible
    STATUS     current
    DESCRIPTION
    "Table Entry for Metadata Source In Use"
    INDEX { slotId }
::= { enc1P1090metadataSourceInUseTable 1 }

Enc1P1090metadataSourceInUseEntry ::= SEQUENCE {
    enc1P1090metadataSourceInUseValue    Enc1E103enumObj
}

enc1P1090metadataSourceInUseValue OBJECT-TYPE
    SYNTAX     Enc1E103enumObj
    MAX-ACCESS read-only
    STATUS     current
    DESCRIPTION
    "Indicates current audio metadata source or reversion."
::= { enc1P1090metadataSourceInUseEntry 1 }

enc1P1091externalMetadataErrorTable OBJECT-TYPE
    SYNTAX SEQUENCE OF Enc1P1091externalMetadataErrorEntry
    MAX-ACCESS not-accessible
    STATUS     current
    DESCRIPTION
    "
    Name      : External Metadata Error
    Menu Path : /Audio/Audio 6/Metadata
    Details   : Indicates any current error in external metadata.
    "
::= { enc1Params 1091 }

enc1P1091externalMetadataErrorEntry OBJECT-TYPE
    SYNTAX Enc1P1091externalMetadataErrorEntry
    MAX-ACCESS not-accessible
    STATUS     current
    DESCRIPTION
    "Table Entry for External Metadata Error"
    INDEX { slotId }
::= { enc1P1091externalMetadataErrorTable 1 }

Enc1P1091externalMetadataErrorEntry ::= SEQUENCE {
    enc1P1091externalMetadataErrorValue    Enc1E104enumObj
}

enc1P1091externalMetadataErrorValue OBJECT-TYPE
    SYNTAX     Enc1E104enumObj
    MAX-ACCESS read-only
    STATUS     current
    DESCRIPTION
    "Indicates any current error in external metadata."
::= { enc1P1091externalMetadataErrorEntry 1 }

enc1P1092metadataSourceInUseTable OBJECT-TYPE
    SYNTAX SEQUENCE OF Enc1P1092metadataSourceInUseEntry
    MAX-ACCESS not-accessible
    STATUS     current
    DESCRIPTION
    "
    Name      : Metadata Source In Use
    Menu Path : /Audio/Audio 7/Metadata
    Details   : Indicates current audio metadata source or reversion.
    "
::= { enc1Params 1092 }

enc1P1092metadataSourceInUseEntry OBJECT-TYPE
    SYNTAX Enc1P1092metadataSourceInUseEntry
    MAX-ACCESS not-accessible
    STATUS     current
    DESCRIPTION
    "Table Entry for Metadata Source In Use"
    INDEX { slotId }
::= { enc1P1092metadataSourceInUseTable 1 }

Enc1P1092metadataSourceInUseEntry ::= SEQUENCE {
    enc1P1092metadataSourceInUseValue    Enc1E103enumObj
}

enc1P1092metadataSourceInUseValue OBJECT-TYPE
    SYNTAX     Enc1E103enumObj
    MAX-ACCESS read-only
    STATUS     current
    DESCRIPTION
    "Indicates current audio metadata source or reversion."
::= { enc1P1092metadataSourceInUseEntry 1 }

enc1P1093externalMetadataErrorTable OBJECT-TYPE
    SYNTAX SEQUENCE OF Enc1P1093externalMetadataErrorEntry
    MAX-ACCESS not-accessible
    STATUS     current
    DESCRIPTION
    "
    Name      : External Metadata Error
    Menu Path : /Audio/Audio 7/Metadata
    Details   : Indicates any current error in external metadata.
    "
::= { enc1Params 1093 }

enc1P1093externalMetadataErrorEntry OBJECT-TYPE
    SYNTAX Enc1P1093externalMetadataErrorEntry
    MAX-ACCESS not-accessible
    STATUS     current
    DESCRIPTION
    "Table Entry for External Metadata Error"
    INDEX { slotId }
::= { enc1P1093externalMetadataErrorTable 1 }

Enc1P1093externalMetadataErrorEntry ::= SEQUENCE {
    enc1P1093externalMetadataErrorValue    Enc1E104enumObj
}

enc1P1093externalMetadataErrorValue OBJECT-TYPE
    SYNTAX     Enc1E104enumObj
    MAX-ACCESS read-only
    STATUS     current
    DESCRIPTION
    "Indicates any current error in external metadata."
::= { enc1P1093externalMetadataErrorEntry 1 }

enc1P1094metadataSourceInUseTable OBJECT-TYPE
    SYNTAX SEQUENCE OF Enc1P1094metadataSourceInUseEntry
    MAX-ACCESS not-accessible
    STATUS     current
    DESCRIPTION
    "
    Name      : Metadata Source In Use
    Menu Path : /Audio/Audio 8/Metadata
    Details   : Indicates current audio metadata source or reversion.
    "
::= { enc1Params 1094 }

enc1P1094metadataSourceInUseEntry OBJECT-TYPE
    SYNTAX Enc1P1094metadataSourceInUseEntry
    MAX-ACCESS not-accessible
    STATUS     current
    DESCRIPTION
    "Table Entry for Metadata Source In Use"
    INDEX { slotId }
::= { enc1P1094metadataSourceInUseTable 1 }

Enc1P1094metadataSourceInUseEntry ::= SEQUENCE {
    enc1P1094metadataSourceInUseValue    Enc1E103enumObj
}

enc1P1094metadataSourceInUseValue OBJECT-TYPE
    SYNTAX     Enc1E103enumObj
    MAX-ACCESS read-only
    STATUS     current
    DESCRIPTION
    "Indicates current audio metadata source or reversion."
::= { enc1P1094metadataSourceInUseEntry 1 }

enc1P1095externalMetadataErrorTable OBJECT-TYPE
    SYNTAX SEQUENCE OF Enc1P1095externalMetadataErrorEntry
    MAX-ACCESS not-accessible
    STATUS     current
    DESCRIPTION
    "
    Name      : External Metadata Error
    Menu Path : /Audio/Audio 8/Metadata
    Details   : Indicates any current error in external metadata.
    "
::= { enc1Params 1095 }

enc1P1095externalMetadataErrorEntry OBJECT-TYPE
    SYNTAX Enc1P1095externalMetadataErrorEntry
    MAX-ACCESS not-accessible
    STATUS     current
    DESCRIPTION
    "Table Entry for External Metadata Error"
    INDEX { slotId }
::= { enc1P1095externalMetadataErrorTable 1 }

Enc1P1095externalMetadataErrorEntry ::= SEQUENCE {
    enc1P1095externalMetadataErrorValue    Enc1E104enumObj
}

enc1P1095externalMetadataErrorValue OBJECT-TYPE
    SYNTAX     Enc1E104enumObj
    MAX-ACCESS read-only
    STATUS     current
    DESCRIPTION
    "Indicates any current error in external metadata."
::= { enc1P1095externalMetadataErrorEntry 1 }

enc1P1100pictureCodingModeTable OBJECT-TYPE
    SYNTAX SEQUENCE OF Enc1P1100pictureCodingModeEntry
    MAX-ACCESS not-accessible
    STATUS     current
    DESCRIPTION
    "
    Name      : Picture Coding Mode
    Menu Path : /Video/Compression
    Details   : Specifies the video coding mode.
    "
::= { enc1Params 1100 }

enc1P1100pictureCodingModeEntry OBJECT-TYPE
    SYNTAX Enc1P1100pictureCodingModeEntry
    MAX-ACCESS not-accessible
    STATUS     current
    DESCRIPTION
    "Table Entry for Picture Coding Mode"
    INDEX { slotId }
::= { enc1P1100pictureCodingModeTable 1 }

Enc1P1100pictureCodingModeEntry ::= SEQUENCE {
    enc1P1100pictureCodingModeValue    Enc1E47enumObj
}

enc1P1100pictureCodingModeValue OBJECT-TYPE
    SYNTAX     Enc1E47enumObj
    MAX-ACCESS read-write
    STATUS     current
    DESCRIPTION
    "Specifies the video coding mode."
::= { enc1P1100pictureCodingModeEntry 1 }

enc1P1101serviceTypeTable OBJECT-TYPE
    SYNTAX SEQUENCE OF Enc1P1101serviceTypeEntry
    MAX-ACCESS not-accessible
    STATUS     current
    DESCRIPTION
    "
    Name      : Service Type
    Menu Path : /TS Mux/SI Parameters
    Units     : 
    Precision : 0
    Low Range : 0
    High Range: 127
    Details   : Specifies service type for program. It is used in the service descriptor of the SDT table. A value of zero means that internal defaults are used. The user can override them by specifying a non-zero value.

     NOTE: Precision/Units/Ranges represent the state of the
           parameter during the MIB generation, and does not
           neccessary reflect the current state of the parameter
    "
::= { enc1Params 1101 }

enc1P1101serviceTypeEntry OBJECT-TYPE
    SYNTAX Enc1P1101serviceTypeEntry
    MAX-ACCESS not-accessible
    STATUS     current
    DESCRIPTION
    "Table Entry for Service Type"
    INDEX { slotId }
::= { enc1P1101serviceTypeTable 1 }

Enc1P1101serviceTypeEntry ::= SEQUENCE {
    enc1P1101serviceTypeValue    INTEGER
}

enc1P1101serviceTypeValue OBJECT-TYPE
    SYNTAX     INTEGER
    MAX-ACCESS read-write
    STATUS     current
    DESCRIPTION
    "Specifies service type for program. It is used in the service descriptor of the SDT table. A value of zero means that internal defaults are used. The user can override them by specifying a non-zero value."
::= { enc1P1101serviceTypeEntry 1 }

enc1P1102codingStandardTable OBJECT-TYPE
    SYNTAX SEQUENCE OF Enc1P1102codingStandardEntry
    MAX-ACCESS not-accessible
    STATUS     current
    DESCRIPTION
    "
    Name      : Coding Standard
    Menu Path : /Video/Compression
    Details   : Specifies the video coding standard.
    "
::= { enc1Params 1102 }

enc1P1102codingStandardEntry OBJECT-TYPE
    SYNTAX Enc1P1102codingStandardEntry
    MAX-ACCESS not-accessible
    STATUS     current
    DESCRIPTION
    "Table Entry for Coding Standard"
    INDEX { slotId }
::= { enc1P1102codingStandardTable 1 }

Enc1P1102codingStandardEntry ::= SEQUENCE {
    enc1P1102codingStandardValue    Enc1E46enumObj
}

enc1P1102codingStandardValue OBJECT-TYPE
    SYNTAX     Enc1E46enumObj
    MAX-ACCESS read-write
    STATUS     current
    DESCRIPTION
    "Specifies the video coding standard."
::= { enc1P1102codingStandardEntry 1 }

enc1P1104videoScanTypeTable OBJECT-TYPE
    SYNTAX SEQUENCE OF Enc1P1104videoScanTypeEntry
    MAX-ACCESS not-accessible
    STATUS     current
    DESCRIPTION
    "
    Name      : Video Scan Type
    Menu Path : /Video/Compression
    Details   : Specifies scan (progressive/interlaced) for input video.
    "
::= { enc1Params 1104 }

enc1P1104videoScanTypeEntry OBJECT-TYPE
    SYNTAX Enc1P1104videoScanTypeEntry
    MAX-ACCESS not-accessible
    STATUS     current
    DESCRIPTION
    "Table Entry for Video Scan Type"
    INDEX { slotId }
::= { enc1P1104videoScanTypeTable 1 }

Enc1P1104videoScanTypeEntry ::= SEQUENCE {
    enc1P1104videoScanTypeValue    Enc1E39enumObj
}

enc1P1104videoScanTypeValue OBJECT-TYPE
    SYNTAX     Enc1E39enumObj
    MAX-ACCESS read-write
    STATUS     current
    DESCRIPTION
    "Specifies scan (progressive/interlaced) for input video."
::= { enc1P1104videoScanTypeEntry 1 }

enc1P1105klvsourceTable OBJECT-TYPE
    SYNTAX SEQUENCE OF Enc1P1105klvsourceEntry
    MAX-ACCESS not-accessible
    STATUS     current
    DESCRIPTION
    "
    Name      : KLV Source
    Menu Path : /Data/KLV
    Details   : Specifies source for KLV data input.
    "
::= { enc1Params 1105 }

enc1P1105klvsourceEntry OBJECT-TYPE
    SYNTAX Enc1P1105klvsourceEntry
    MAX-ACCESS not-accessible
    STATUS     current
    DESCRIPTION
    "Table Entry for KLV Source"
    INDEX { slotId }
::= { enc1P1105klvsourceTable 1 }

Enc1P1105klvsourceEntry ::= SEQUENCE {
    enc1P1105klvsourceValue    Enc1E116enumObj
}

enc1P1105klvsourceValue OBJECT-TYPE
    SYNTAX     Enc1E116enumObj
    MAX-ACCESS read-write
    STATUS     current
    DESCRIPTION
    "Specifies source for KLV data input."
::= { enc1P1105klvsourceEntry 1 }

enc1P1106spliceEventCountTable OBJECT-TYPE
    SYNTAX SEQUENCE OF Enc1P1106spliceEventCountEntry
    MAX-ACCESS not-accessible
    STATUS     current
    DESCRIPTION
    "
    Name      : Splice Event Count
    Menu Path : /Data/Status
    Units     : 
    Precision : 0
    Low Range : 0
    High Range: -1
    Details   : Shows the count of splice point events.

     NOTE: Precision/Units/Ranges represent the state of the
           parameter during the MIB generation, and does not
           neccessary reflect the current state of the parameter
    "
::= { enc1Params 1106 }

enc1P1106spliceEventCountEntry OBJECT-TYPE
    SYNTAX Enc1P1106spliceEventCountEntry
    MAX-ACCESS not-accessible
    STATUS     current
    DESCRIPTION
    "Table Entry for Splice Event Count"
    INDEX { slotId }
::= { enc1P1106spliceEventCountTable 1 }

Enc1P1106spliceEventCountEntry ::= SEQUENCE {
    enc1P1106spliceEventCountValue    INTEGER
}

enc1P1106spliceEventCountValue OBJECT-TYPE
    SYNTAX     INTEGER
    MAX-ACCESS read-only
    STATUS     current
    DESCRIPTION
    "Shows the count of splice point events."
::= { enc1P1106spliceEventCountEntry 1 }

enc1P1107alternateSourceTable OBJECT-TYPE
    SYNTAX SEQUENCE OF Enc1P1107alternateSourceEntry
    MAX-ACCESS not-accessible
    STATUS     current
    DESCRIPTION
    "
    Name      : Alternate Source
    Menu Path : /Video/Input
    Details   : Selects alternate video input source for encoding.
    "
::= { enc1Params 1107 }

enc1P1107alternateSourceEntry OBJECT-TYPE
    SYNTAX Enc1P1107alternateSourceEntry
    MAX-ACCESS not-accessible
    STATUS     current
    DESCRIPTION
    "Table Entry for Alternate Source"
    INDEX { slotId }
::= { enc1P1107alternateSourceTable 1 }

Enc1P1107alternateSourceEntry ::= SEQUENCE {
    enc1P1107alternateSourceValue    Enc1E36enumObj
}

enc1P1107alternateSourceValue OBJECT-TYPE
    SYNTAX     Enc1E36enumObj
    MAX-ACCESS read-write
    STATUS     current
    DESCRIPTION
    "Selects alternate video input source for encoding."
::= { enc1P1107alternateSourceEntry 1 }

enc1P1108sourceSelectionTable OBJECT-TYPE
    SYNTAX SEQUENCE OF Enc1P1108sourceSelectionEntry
    MAX-ACCESS not-accessible
    STATUS     current
    DESCRIPTION
    "
    Name      : Source Selection
    Menu Path : /Video/Input
    Details   : Selects video source redundancy type.
    "
::= { enc1Params 1108 }

enc1P1108sourceSelectionEntry OBJECT-TYPE
    SYNTAX Enc1P1108sourceSelectionEntry
    MAX-ACCESS not-accessible
    STATUS     current
    DESCRIPTION
    "Table Entry for Source Selection"
    INDEX { slotId }
::= { enc1P1108sourceSelectionTable 1 }

Enc1P1108sourceSelectionEntry ::= SEQUENCE {
    enc1P1108sourceSelectionValue    Enc1E38enumObj
}

enc1P1108sourceSelectionValue OBJECT-TYPE
    SYNTAX     Enc1E38enumObj
    MAX-ACCESS read-write
    STATUS     current
    DESCRIPTION
    "Selects video source redundancy type."
::= { enc1P1108sourceSelectionEntry 1 }

enc1P1109currentVideoSourceTable OBJECT-TYPE
    SYNTAX SEQUENCE OF Enc1P1109currentVideoSourceEntry
    MAX-ACCESS not-accessible
    STATUS     current
    DESCRIPTION
    "
    Name      : Current Video Source
    Menu Path : /Video/Input/Status
    Details   : Shows the current selected video input source.
    "
::= { enc1Params 1109 }

enc1P1109currentVideoSourceEntry OBJECT-TYPE
    SYNTAX Enc1P1109currentVideoSourceEntry
    MAX-ACCESS not-accessible
    STATUS     current
    DESCRIPTION
    "Table Entry for Current Video Source"
    INDEX { slotId }
::= { enc1P1109currentVideoSourceTable 1 }

Enc1P1109currentVideoSourceEntry ::= SEQUENCE {
    enc1P1109currentVideoSourceValue    Enc1E35enumObj
}

enc1P1109currentVideoSourceValue OBJECT-TYPE
    SYNTAX     Enc1E35enumObj
    MAX-ACCESS read-only
    STATUS     current
    DESCRIPTION
    "Shows the current selected video input source."
::= { enc1P1109currentVideoSourceEntry 1 }

enc1P1115pespackingTable OBJECT-TYPE
    SYNTAX SEQUENCE OF Enc1P1115pespackingEntry
    MAX-ACCESS not-accessible
    STATUS     current
    DESCRIPTION
    "
    Name      : PES Packing
    Menu Path : /Audio/Audio 1/AAC
    Details   : Specifies AAC frame alignment in the PES.
    "
::= { enc1Params 1115 }

enc1P1115pespackingEntry OBJECT-TYPE
    SYNTAX Enc1P1115pespackingEntry
    MAX-ACCESS not-accessible
    STATUS     current
    DESCRIPTION
    "Table Entry for PES Packing"
    INDEX { slotId }
::= { enc1P1115pespackingTable 1 }

Enc1P1115pespackingEntry ::= SEQUENCE {
    enc1P1115pespackingValue    Enc1E181enumObj
}

enc1P1115pespackingValue OBJECT-TYPE
    SYNTAX     Enc1E181enumObj
    MAX-ACCESS read-write
    STATUS     current
    DESCRIPTION
    "Specifies AAC frame alignment in the PES."
::= { enc1P1115pespackingEntry 1 }

enc1P1116pespackingTable OBJECT-TYPE
    SYNTAX SEQUENCE OF Enc1P1116pespackingEntry
    MAX-ACCESS not-accessible
    STATUS     current
    DESCRIPTION
    "
    Name      : PES Packing
    Menu Path : /Audio/Audio 2/AAC
    Details   : Specifies AAC frame alignment in the PES.
    "
::= { enc1Params 1116 }

enc1P1116pespackingEntry OBJECT-TYPE
    SYNTAX Enc1P1116pespackingEntry
    MAX-ACCESS not-accessible
    STATUS     current
    DESCRIPTION
    "Table Entry for PES Packing"
    INDEX { slotId }
::= { enc1P1116pespackingTable 1 }

Enc1P1116pespackingEntry ::= SEQUENCE {
    enc1P1116pespackingValue    Enc1E184enumObj
}

enc1P1116pespackingValue OBJECT-TYPE
    SYNTAX     Enc1E184enumObj
    MAX-ACCESS read-write
    STATUS     current
    DESCRIPTION
    "Specifies AAC frame alignment in the PES."
::= { enc1P1116pespackingEntry 1 }

enc1P1117pespackingTable OBJECT-TYPE
    SYNTAX SEQUENCE OF Enc1P1117pespackingEntry
    MAX-ACCESS not-accessible
    STATUS     current
    DESCRIPTION
    "
    Name      : PES Packing
    Menu Path : /Audio/Audio 3/AAC
    Details   : Specifies AAC frame alignment in the PES.
    "
::= { enc1Params 1117 }

enc1P1117pespackingEntry OBJECT-TYPE
    SYNTAX Enc1P1117pespackingEntry
    MAX-ACCESS not-accessible
    STATUS     current
    DESCRIPTION
    "Table Entry for PES Packing"
    INDEX { slotId }
::= { enc1P1117pespackingTable 1 }

Enc1P1117pespackingEntry ::= SEQUENCE {
    enc1P1117pespackingValue    Enc1E187enumObj
}

enc1P1117pespackingValue OBJECT-TYPE
    SYNTAX     Enc1E187enumObj
    MAX-ACCESS read-write
    STATUS     current
    DESCRIPTION
    "Specifies AAC frame alignment in the PES."
::= { enc1P1117pespackingEntry 1 }

enc1P1118pespackingTable OBJECT-TYPE
    SYNTAX SEQUENCE OF Enc1P1118pespackingEntry
    MAX-ACCESS not-accessible
    STATUS     current
    DESCRIPTION
    "
    Name      : PES Packing
    Menu Path : /Audio/Audio 4/AAC
    Details   : Specifies AAC frame alignment in the PES.
    "
::= { enc1Params 1118 }

enc1P1118pespackingEntry OBJECT-TYPE
    SYNTAX Enc1P1118pespackingEntry
    MAX-ACCESS not-accessible
    STATUS     current
    DESCRIPTION
    "Table Entry for PES Packing"
    INDEX { slotId }
::= { enc1P1118pespackingTable 1 }

Enc1P1118pespackingEntry ::= SEQUENCE {
    enc1P1118pespackingValue    Enc1E190enumObj
}

enc1P1118pespackingValue OBJECT-TYPE
    SYNTAX     Enc1E190enumObj
    MAX-ACCESS read-write
    STATUS     current
    DESCRIPTION
    "Specifies AAC frame alignment in the PES."
::= { enc1P1118pespackingEntry 1 }

enc1P1119pespackingTable OBJECT-TYPE
    SYNTAX SEQUENCE OF Enc1P1119pespackingEntry
    MAX-ACCESS not-accessible
    STATUS     current
    DESCRIPTION
    "
    Name      : PES Packing
    Menu Path : /Audio/Audio 5/AAC
    Details   : Specifies AAC frame alignment in the PES.
    "
::= { enc1Params 1119 }

enc1P1119pespackingEntry OBJECT-TYPE
    SYNTAX Enc1P1119pespackingEntry
    MAX-ACCESS not-accessible
    STATUS     current
    DESCRIPTION
    "Table Entry for PES Packing"
    INDEX { slotId }
::= { enc1P1119pespackingTable 1 }

Enc1P1119pespackingEntry ::= SEQUENCE {
    enc1P1119pespackingValue    Enc1E193enumObj
}

enc1P1119pespackingValue OBJECT-TYPE
    SYNTAX     Enc1E193enumObj
    MAX-ACCESS read-write
    STATUS     current
    DESCRIPTION
    "Specifies AAC frame alignment in the PES."
::= { enc1P1119pespackingEntry 1 }

enc1P1120pespackingTable OBJECT-TYPE
    SYNTAX SEQUENCE OF Enc1P1120pespackingEntry
    MAX-ACCESS not-accessible
    STATUS     current
    DESCRIPTION
    "
    Name      : PES Packing
    Menu Path : /Audio/Audio 6/AAC
    Details   : Specifies AAC frame alignment in the PES.
    "
::= { enc1Params 1120 }

enc1P1120pespackingEntry OBJECT-TYPE
    SYNTAX Enc1P1120pespackingEntry
    MAX-ACCESS not-accessible
    STATUS     current
    DESCRIPTION
    "Table Entry for PES Packing"
    INDEX { slotId }
::= { enc1P1120pespackingTable 1 }

Enc1P1120pespackingEntry ::= SEQUENCE {
    enc1P1120pespackingValue    Enc1E196enumObj
}

enc1P1120pespackingValue OBJECT-TYPE
    SYNTAX     Enc1E196enumObj
    MAX-ACCESS read-write
    STATUS     current
    DESCRIPTION
    "Specifies AAC frame alignment in the PES."
::= { enc1P1120pespackingEntry 1 }

enc1P1121pespackingTable OBJECT-TYPE
    SYNTAX SEQUENCE OF Enc1P1121pespackingEntry
    MAX-ACCESS not-accessible
    STATUS     current
    DESCRIPTION
    "
    Name      : PES Packing
    Menu Path : /Audio/Audio 7/AAC
    Details   : Specifies AAC frame alignment in the PES.
    "
::= { enc1Params 1121 }

enc1P1121pespackingEntry OBJECT-TYPE
    SYNTAX Enc1P1121pespackingEntry
    MAX-ACCESS not-accessible
    STATUS     current
    DESCRIPTION
    "Table Entry for PES Packing"
    INDEX { slotId }
::= { enc1P1121pespackingTable 1 }

Enc1P1121pespackingEntry ::= SEQUENCE {
    enc1P1121pespackingValue    Enc1E199enumObj
}

enc1P1121pespackingValue OBJECT-TYPE
    SYNTAX     Enc1E199enumObj
    MAX-ACCESS read-write
    STATUS     current
    DESCRIPTION
    "Specifies AAC frame alignment in the PES."
::= { enc1P1121pespackingEntry 1 }

enc1P1122pespackingTable OBJECT-TYPE
    SYNTAX SEQUENCE OF Enc1P1122pespackingEntry
    MAX-ACCESS not-accessible
    STATUS     current
    DESCRIPTION
    "
    Name      : PES Packing
    Menu Path : /Audio/Audio 8/AAC
    Details   : Specifies AAC frame alignment in the PES.
    "
::= { enc1Params 1122 }

enc1P1122pespackingEntry OBJECT-TYPE
    SYNTAX Enc1P1122pespackingEntry
    MAX-ACCESS not-accessible
    STATUS     current
    DESCRIPTION
    "Table Entry for PES Packing"
    INDEX { slotId }
::= { enc1P1122pespackingTable 1 }

Enc1P1122pespackingEntry ::= SEQUENCE {
    enc1P1122pespackingValue    Enc1E202enumObj
}

enc1P1122pespackingValue OBJECT-TYPE
    SYNTAX     Enc1E202enumObj
    MAX-ACCESS read-write
    STATUS     current
    DESCRIPTION
    "Specifies AAC frame alignment in the PES."
::= { enc1P1122pespackingEntry 1 }

enc1P1123codecSampleRateTable OBJECT-TYPE
    SYNTAX SEQUENCE OF Enc1P1123codecSampleRateEntry
    MAX-ACCESS not-accessible
    STATUS     current
    DESCRIPTION
    "
    Name      : Codec Sample Rate
    Menu Path : /Audio/Audio 1
    Details   : Specifies audio sample rate signaled by codec.
    "
::= { enc1Params 1123 }

enc1P1123codecSampleRateEntry OBJECT-TYPE
    SYNTAX Enc1P1123codecSampleRateEntry
    MAX-ACCESS not-accessible
    STATUS     current
    DESCRIPTION
    "Table Entry for Codec Sample Rate"
    INDEX { slotId }
::= { enc1P1123codecSampleRateTable 1 }

Enc1P1123codecSampleRateEntry ::= SEQUENCE {
    enc1P1123codecSampleRateValue    Enc1E105enumObj
}

enc1P1123codecSampleRateValue OBJECT-TYPE
    SYNTAX     Enc1E105enumObj
    MAX-ACCESS read-write
    STATUS     current
    DESCRIPTION
    "Specifies audio sample rate signaled by codec."
::= { enc1P1123codecSampleRateEntry 1 }

enc1P1124codecSampleRateTable OBJECT-TYPE
    SYNTAX SEQUENCE OF Enc1P1124codecSampleRateEntry
    MAX-ACCESS not-accessible
    STATUS     current
    DESCRIPTION
    "
    Name      : Codec Sample Rate
    Menu Path : /Audio/Audio 2
    Details   : Specifies audio sample rate signaled by codec.
    "
::= { enc1Params 1124 }

enc1P1124codecSampleRateEntry OBJECT-TYPE
    SYNTAX Enc1P1124codecSampleRateEntry
    MAX-ACCESS not-accessible
    STATUS     current
    DESCRIPTION
    "Table Entry for Codec Sample Rate"
    INDEX { slotId }
::= { enc1P1124codecSampleRateTable 1 }

Enc1P1124codecSampleRateEntry ::= SEQUENCE {
    enc1P1124codecSampleRateValue    Enc1E105enumObj
}

enc1P1124codecSampleRateValue OBJECT-TYPE
    SYNTAX     Enc1E105enumObj
    MAX-ACCESS read-write
    STATUS     current
    DESCRIPTION
    "Specifies audio sample rate signaled by codec."
::= { enc1P1124codecSampleRateEntry 1 }

enc1P1125codecSampleRateTable OBJECT-TYPE
    SYNTAX SEQUENCE OF Enc1P1125codecSampleRateEntry
    MAX-ACCESS not-accessible
    STATUS     current
    DESCRIPTION
    "
    Name      : Codec Sample Rate
    Menu Path : /Audio/Audio 3
    Details   : Specifies audio sample rate signaled by codec.
    "
::= { enc1Params 1125 }

enc1P1125codecSampleRateEntry OBJECT-TYPE
    SYNTAX Enc1P1125codecSampleRateEntry
    MAX-ACCESS not-accessible
    STATUS     current
    DESCRIPTION
    "Table Entry for Codec Sample Rate"
    INDEX { slotId }
::= { enc1P1125codecSampleRateTable 1 }

Enc1P1125codecSampleRateEntry ::= SEQUENCE {
    enc1P1125codecSampleRateValue    Enc1E105enumObj
}

enc1P1125codecSampleRateValue OBJECT-TYPE
    SYNTAX     Enc1E105enumObj
    MAX-ACCESS read-write
    STATUS     current
    DESCRIPTION
    "Specifies audio sample rate signaled by codec."
::= { enc1P1125codecSampleRateEntry 1 }

enc1P1126codecSampleRateTable OBJECT-TYPE
    SYNTAX SEQUENCE OF Enc1P1126codecSampleRateEntry
    MAX-ACCESS not-accessible
    STATUS     current
    DESCRIPTION
    "
    Name      : Codec Sample Rate
    Menu Path : /Audio/Audio 4
    Details   : Specifies audio sample rate signaled by codec.
    "
::= { enc1Params 1126 }

enc1P1126codecSampleRateEntry OBJECT-TYPE
    SYNTAX Enc1P1126codecSampleRateEntry
    MAX-ACCESS not-accessible
    STATUS     current
    DESCRIPTION
    "Table Entry for Codec Sample Rate"
    INDEX { slotId }
::= { enc1P1126codecSampleRateTable 1 }

Enc1P1126codecSampleRateEntry ::= SEQUENCE {
    enc1P1126codecSampleRateValue    Enc1E105enumObj
}

enc1P1126codecSampleRateValue OBJECT-TYPE
    SYNTAX     Enc1E105enumObj
    MAX-ACCESS read-write
    STATUS     current
    DESCRIPTION
    "Specifies audio sample rate signaled by codec."
::= { enc1P1126codecSampleRateEntry 1 }

enc1P1127codecSampleRateTable OBJECT-TYPE
    SYNTAX SEQUENCE OF Enc1P1127codecSampleRateEntry
    MAX-ACCESS not-accessible
    STATUS     current
    DESCRIPTION
    "
    Name      : Codec Sample Rate
    Menu Path : /Audio/Audio 5
    Details   : Specifies audio sample rate signaled by codec.
    "
::= { enc1Params 1127 }

enc1P1127codecSampleRateEntry OBJECT-TYPE
    SYNTAX Enc1P1127codecSampleRateEntry
    MAX-ACCESS not-accessible
    STATUS     current
    DESCRIPTION
    "Table Entry for Codec Sample Rate"
    INDEX { slotId }
::= { enc1P1127codecSampleRateTable 1 }

Enc1P1127codecSampleRateEntry ::= SEQUENCE {
    enc1P1127codecSampleRateValue    Enc1E105enumObj
}

enc1P1127codecSampleRateValue OBJECT-TYPE
    SYNTAX     Enc1E105enumObj
    MAX-ACCESS read-write
    STATUS     current
    DESCRIPTION
    "Specifies audio sample rate signaled by codec."
::= { enc1P1127codecSampleRateEntry 1 }

enc1P1128codecSampleRateTable OBJECT-TYPE
    SYNTAX SEQUENCE OF Enc1P1128codecSampleRateEntry
    MAX-ACCESS not-accessible
    STATUS     current
    DESCRIPTION
    "
    Name      : Codec Sample Rate
    Menu Path : /Audio/Audio 6
    Details   : Specifies audio sample rate signaled by codec.
    "
::= { enc1Params 1128 }

enc1P1128codecSampleRateEntry OBJECT-TYPE
    SYNTAX Enc1P1128codecSampleRateEntry
    MAX-ACCESS not-accessible
    STATUS     current
    DESCRIPTION
    "Table Entry for Codec Sample Rate"
    INDEX { slotId }
::= { enc1P1128codecSampleRateTable 1 }

Enc1P1128codecSampleRateEntry ::= SEQUENCE {
    enc1P1128codecSampleRateValue    Enc1E105enumObj
}

enc1P1128codecSampleRateValue OBJECT-TYPE
    SYNTAX     Enc1E105enumObj
    MAX-ACCESS read-write
    STATUS     current
    DESCRIPTION
    "Specifies audio sample rate signaled by codec."
::= { enc1P1128codecSampleRateEntry 1 }

enc1P1129codecSampleRateTable OBJECT-TYPE
    SYNTAX SEQUENCE OF Enc1P1129codecSampleRateEntry
    MAX-ACCESS not-accessible
    STATUS     current
    DESCRIPTION
    "
    Name      : Codec Sample Rate
    Menu Path : /Audio/Audio 7
    Details   : Specifies audio sample rate signaled by codec.
    "
::= { enc1Params 1129 }

enc1P1129codecSampleRateEntry OBJECT-TYPE
    SYNTAX Enc1P1129codecSampleRateEntry
    MAX-ACCESS not-accessible
    STATUS     current
    DESCRIPTION
    "Table Entry for Codec Sample Rate"
    INDEX { slotId }
::= { enc1P1129codecSampleRateTable 1 }

Enc1P1129codecSampleRateEntry ::= SEQUENCE {
    enc1P1129codecSampleRateValue    Enc1E105enumObj
}

enc1P1129codecSampleRateValue OBJECT-TYPE
    SYNTAX     Enc1E105enumObj
    MAX-ACCESS read-write
    STATUS     current
    DESCRIPTION
    "Specifies audio sample rate signaled by codec."
::= { enc1P1129codecSampleRateEntry 1 }

enc1P1130codecSampleRateTable OBJECT-TYPE
    SYNTAX SEQUENCE OF Enc1P1130codecSampleRateEntry
    MAX-ACCESS not-accessible
    STATUS     current
    DESCRIPTION
    "
    Name      : Codec Sample Rate
    Menu Path : /Audio/Audio 8
    Details   : Specifies audio sample rate signaled by codec.
    "
::= { enc1Params 1130 }

enc1P1130codecSampleRateEntry OBJECT-TYPE
    SYNTAX Enc1P1130codecSampleRateEntry
    MAX-ACCESS not-accessible
    STATUS     current
    DESCRIPTION
    "Table Entry for Codec Sample Rate"
    INDEX { slotId }
::= { enc1P1130codecSampleRateTable 1 }

Enc1P1130codecSampleRateEntry ::= SEQUENCE {
    enc1P1130codecSampleRateValue    Enc1E105enumObj
}

enc1P1130codecSampleRateValue OBJECT-TYPE
    SYNTAX     Enc1E105enumObj
    MAX-ACCESS read-write
    STATUS     current
    DESCRIPTION
    "Specifies audio sample rate signaled by codec."
::= { enc1P1130codecSampleRateEntry 1 }

enc1P1131cctranslationTable OBJECT-TYPE
    SYNTAX SEQUENCE OF Enc1P1131cctranslationEntry
    MAX-ACCESS not-accessible
    STATUS     current
    DESCRIPTION
    "
    Name      : CC Translation
    Menu Path : /Data/Status
    Details   : Shows whether 608->708 translation is happening or not.
    "
::= { enc1Params 1131 }

enc1P1131cctranslationEntry OBJECT-TYPE
    SYNTAX Enc1P1131cctranslationEntry
    MAX-ACCESS not-accessible
    STATUS     current
    DESCRIPTION
    "Table Entry for CC Translation"
    INDEX { slotId }
::= { enc1P1131cctranslationTable 1 }

Enc1P1131cctranslationEntry ::= SEQUENCE {
    enc1P1131cctranslationValue    Enc1E1enumObj
}

enc1P1131cctranslationValue OBJECT-TYPE
    SYNTAX     Enc1E1enumObj
    MAX-ACCESS read-only
    STATUS     current
    DESCRIPTION
    "Shows whether 608->708 translation is happening or not."
::= { enc1P1131cctranslationEntry 1 }

enc1P1132presetCompletionIndicatorTable OBJECT-TYPE
    SYNTAX SEQUENCE OF Enc1P1132presetCompletionIndicatorEntry
    MAX-ACCESS not-accessible
    STATUS     current
    DESCRIPTION
    "
    Name      : Preset Completion Indicator
    Menu Path : /Preset Indicator
    Details   : Indicates completion of preset loading.
    "
::= { enc1Params 1132 }

enc1P1132presetCompletionIndicatorEntry OBJECT-TYPE
    SYNTAX Enc1P1132presetCompletionIndicatorEntry
    MAX-ACCESS not-accessible
    STATUS     current
    DESCRIPTION
    "Table Entry for Preset Completion Indicator"
    INDEX { slotId }
::= { enc1P1132presetCompletionIndicatorTable 1 }

Enc1P1132presetCompletionIndicatorEntry ::= SEQUENCE {
    enc1P1132presetCompletionIndicatorValue    DisplayString
}

enc1P1132presetCompletionIndicatorValue OBJECT-TYPE
    SYNTAX     DisplayString
    MAX-ACCESS read-write
    STATUS     current
    DESCRIPTION
    "Indicates completion of preset loading."
::= { enc1P1132presetCompletionIndicatorEntry 1 }

enc1P1133extDolbyHeadphoneEncodingTable OBJECT-TYPE
    SYNTAX SEQUENCE OF Enc1P1133extDolbyHeadphoneEncodingEntry
    MAX-ACCESS not-accessible
    STATUS     current
    DESCRIPTION
    "
    Name      : Ext: Dolby Headphone Encoding
    Menu Path : /Audio/Metadata Generator 1
    Details   : Indicates the presence of Dolby Headphone Encoding.
    "
::= { enc1Params 1133 }

enc1P1133extDolbyHeadphoneEncodingEntry OBJECT-TYPE
    SYNTAX Enc1P1133extDolbyHeadphoneEncodingEntry
    MAX-ACCESS not-accessible
    STATUS     current
    DESCRIPTION
    "Table Entry for Ext: Dolby Headphone Encoding"
    INDEX { slotId }
::= { enc1P1133extDolbyHeadphoneEncodingTable 1 }

Enc1P1133extDolbyHeadphoneEncodingEntry ::= SEQUENCE {
    enc1P1133extDolbyHeadphoneEncodingValue    Enc1E94enumObj
}

enc1P1133extDolbyHeadphoneEncodingValue OBJECT-TYPE
    SYNTAX     Enc1E94enumObj
    MAX-ACCESS read-write
    STATUS     current
    DESCRIPTION
    "Indicates the presence of Dolby Headphone Encoding."
::= { enc1P1133extDolbyHeadphoneEncodingEntry 1 }

enc1P1134extDolbyHeadphoneEncodingTable OBJECT-TYPE
    SYNTAX SEQUENCE OF Enc1P1134extDolbyHeadphoneEncodingEntry
    MAX-ACCESS not-accessible
    STATUS     current
    DESCRIPTION
    "
    Name      : Ext Dolby Headphone Encoding
    Menu Path : /Audio/Metadata Generator 2
    Details   : Indicates the presence of Dolby Headphone Encoding.
    "
::= { enc1Params 1134 }

enc1P1134extDolbyHeadphoneEncodingEntry OBJECT-TYPE
    SYNTAX Enc1P1134extDolbyHeadphoneEncodingEntry
    MAX-ACCESS not-accessible
    STATUS     current
    DESCRIPTION
    "Table Entry for Ext Dolby Headphone Encoding"
    INDEX { slotId }
::= { enc1P1134extDolbyHeadphoneEncodingTable 1 }

Enc1P1134extDolbyHeadphoneEncodingEntry ::= SEQUENCE {
    enc1P1134extDolbyHeadphoneEncodingValue    Enc1E94enumObj
}

enc1P1134extDolbyHeadphoneEncodingValue OBJECT-TYPE
    SYNTAX     Enc1E94enumObj
    MAX-ACCESS read-write
    STATUS     current
    DESCRIPTION
    "Indicates the presence of Dolby Headphone Encoding."
::= { enc1P1134extDolbyHeadphoneEncodingEntry 1 }

enc1P1135primaryAudioIPPacketsTable OBJECT-TYPE
    SYNTAX SEQUENCE OF Enc1P1135primaryAudioIPPacketsEntry
    MAX-ACCESS not-accessible
    STATUS     current
    DESCRIPTION
    "
    Name      : Primary Audio IP Packets
    Menu Path : /IP Encapsulation/Main Program IP Status
    Units     : 
    Precision : 0
    Low Range : 0
    High Range: -1
    Details   : Shows the count of transmitted audio IP packets on this program.

     NOTE: Precision/Units/Ranges represent the state of the
           parameter during the MIB generation, and does not
           neccessary reflect the current state of the parameter
    "
::= { enc1Params 1135 }

enc1P1135primaryAudioIPPacketsEntry OBJECT-TYPE
    SYNTAX Enc1P1135primaryAudioIPPacketsEntry
    MAX-ACCESS not-accessible
    STATUS     current
    DESCRIPTION
    "Table Entry for Primary Audio IP Packets"
    INDEX { slotId }
::= { enc1P1135primaryAudioIPPacketsTable 1 }

Enc1P1135primaryAudioIPPacketsEntry ::= SEQUENCE {
    enc1P1135primaryAudioIPPacketsValue    INTEGER
}

enc1P1135primaryAudioIPPacketsValue OBJECT-TYPE
    SYNTAX     INTEGER
    MAX-ACCESS read-only
    STATUS     current
    DESCRIPTION
    "Shows the count of transmitted audio IP packets on this program."
::= { enc1P1135primaryAudioIPPacketsEntry 1 }

enc1P1136outputThreadRestartsTable OBJECT-TYPE
    SYNTAX SEQUENCE OF Enc1P1136outputThreadRestartsEntry
    MAX-ACCESS not-accessible
    STATUS     current
    DESCRIPTION
    "
    Name      : Output Thread Restarts
    Menu Path : /IP Encapsulation/Main Program IP Status
    Units     : 
    Precision : 0
    Low Range : 0
    High Range: -1
    Details   : Shows the count of restarts of output thread due to loss of audio.

     NOTE: Precision/Units/Ranges represent the state of the
           parameter during the MIB generation, and does not
           neccessary reflect the current state of the parameter
    "
::= { enc1Params 1136 }

enc1P1136outputThreadRestartsEntry OBJECT-TYPE
    SYNTAX Enc1P1136outputThreadRestartsEntry
    MAX-ACCESS not-accessible
    STATUS     current
    DESCRIPTION
    "Table Entry for Output Thread Restarts"
    INDEX { slotId }
::= { enc1P1136outputThreadRestartsTable 1 }

Enc1P1136outputThreadRestartsEntry ::= SEQUENCE {
    enc1P1136outputThreadRestartsValue    INTEGER
}

enc1P1136outputThreadRestartsValue OBJECT-TYPE
    SYNTAX     INTEGER
    MAX-ACCESS read-only
    STATUS     current
    DESCRIPTION
    "Shows the count of restarts of output thread due to loss of audio."
::= { enc1P1136outputThreadRestartsEntry 1 }

enc1P1137serviceFaultAlarmPriorityTable OBJECT-TYPE
    SYNTAX SEQUENCE OF Enc1P1137serviceFaultAlarmPriorityEntry
    MAX-ACCESS not-accessible
    STATUS     current
    DESCRIPTION
    "
    Name      : Service Fault Alarm Priority
    Menu Path : /Misc
    Details   : Set service fault priority threshold.
    "
::= { enc1Params 1137 }

enc1P1137serviceFaultAlarmPriorityEntry OBJECT-TYPE
    SYNTAX Enc1P1137serviceFaultAlarmPriorityEntry
    MAX-ACCESS not-accessible
    STATUS     current
    DESCRIPTION
    "Table Entry for Service Fault Alarm Priority"
    INDEX { slotId }
::= { enc1P1137serviceFaultAlarmPriorityTable 1 }

Enc1P1137serviceFaultAlarmPriorityEntry ::= SEQUENCE {
    enc1P1137serviceFaultAlarmPriorityValue    Enc1E25enumObj
}

enc1P1137serviceFaultAlarmPriorityValue OBJECT-TYPE
    SYNTAX     Enc1E25enumObj
    MAX-ACCESS read-write
    STATUS     current
    DESCRIPTION
    "Set service fault priority threshold."
::= { enc1P1137serviceFaultAlarmPriorityEntry 1 }

enc1P1201extCompressedSubstreamIDTable OBJECT-TYPE
    SYNTAX SEQUENCE OF Enc1P1201extCompressedSubstreamIDEntry
    MAX-ACCESS not-accessible
    STATUS     current
    DESCRIPTION
    "
    Name      : Ext. Compressed Substream ID
    Menu Path : /Audio/Audio 1
    Units     : 
    Precision : 0
    Low Range : 0
    High Range: 6
    Details   : Specifies substream ID of externally compressed audio source

     NOTE: Precision/Units/Ranges represent the state of the
           parameter during the MIB generation, and does not
           neccessary reflect the current state of the parameter
    "
::= { enc1Params 1201 }

enc1P1201extCompressedSubstreamIDEntry OBJECT-TYPE
    SYNTAX Enc1P1201extCompressedSubstreamIDEntry
    MAX-ACCESS not-accessible
    STATUS     current
    DESCRIPTION
    "Table Entry for Ext. Compressed Substream ID"
    INDEX { slotId }
::= { enc1P1201extCompressedSubstreamIDTable 1 }

Enc1P1201extCompressedSubstreamIDEntry ::= SEQUENCE {
    enc1P1201extCompressedSubstreamIDValue    INTEGER
}

enc1P1201extCompressedSubstreamIDValue OBJECT-TYPE
    SYNTAX     INTEGER
    MAX-ACCESS read-write
    STATUS     current
    DESCRIPTION
    "Specifies substream ID of externally compressed audio source"
::= { enc1P1201extCompressedSubstreamIDEntry 1 }

enc1P1202extCompressedSubstreamIDTable OBJECT-TYPE
    SYNTAX SEQUENCE OF Enc1P1202extCompressedSubstreamIDEntry
    MAX-ACCESS not-accessible
    STATUS     current
    DESCRIPTION
    "
    Name      : Ext. Compressed Substream ID
    Menu Path : /Audio/Audio 2
    Units     : 
    Precision : 0
    Low Range : 0
    High Range: 6
    Details   : Specifies substream ID of externally compressed audio source

     NOTE: Precision/Units/Ranges represent the state of the
           parameter during the MIB generation, and does not
           neccessary reflect the current state of the parameter
    "
::= { enc1Params 1202 }

enc1P1202extCompressedSubstreamIDEntry OBJECT-TYPE
    SYNTAX Enc1P1202extCompressedSubstreamIDEntry
    MAX-ACCESS not-accessible
    STATUS     current
    DESCRIPTION
    "Table Entry for Ext. Compressed Substream ID"
    INDEX { slotId }
::= { enc1P1202extCompressedSubstreamIDTable 1 }

Enc1P1202extCompressedSubstreamIDEntry ::= SEQUENCE {
    enc1P1202extCompressedSubstreamIDValue    INTEGER
}

enc1P1202extCompressedSubstreamIDValue OBJECT-TYPE
    SYNTAX     INTEGER
    MAX-ACCESS read-write
    STATUS     current
    DESCRIPTION
    "Specifies substream ID of externally compressed audio source"
::= { enc1P1202extCompressedSubstreamIDEntry 1 }

enc1P1203extCompressedSubstreamIDTable OBJECT-TYPE
    SYNTAX SEQUENCE OF Enc1P1203extCompressedSubstreamIDEntry
    MAX-ACCESS not-accessible
    STATUS     current
    DESCRIPTION
    "
    Name      : Ext. Compressed Substream ID
    Menu Path : /Audio/Audio 3
    Units     : 
    Precision : 0
    Low Range : 0
    High Range: 6
    Details   : Specifies substream ID of externally compressed audio source

     NOTE: Precision/Units/Ranges represent the state of the
           parameter during the MIB generation, and does not
           neccessary reflect the current state of the parameter
    "
::= { enc1Params 1203 }

enc1P1203extCompressedSubstreamIDEntry OBJECT-TYPE
    SYNTAX Enc1P1203extCompressedSubstreamIDEntry
    MAX-ACCESS not-accessible
    STATUS     current
    DESCRIPTION
    "Table Entry for Ext. Compressed Substream ID"
    INDEX { slotId }
::= { enc1P1203extCompressedSubstreamIDTable 1 }

Enc1P1203extCompressedSubstreamIDEntry ::= SEQUENCE {
    enc1P1203extCompressedSubstreamIDValue    INTEGER
}

enc1P1203extCompressedSubstreamIDValue OBJECT-TYPE
    SYNTAX     INTEGER
    MAX-ACCESS read-write
    STATUS     current
    DESCRIPTION
    "Specifies substream ID of externally compressed audio source"
::= { enc1P1203extCompressedSubstreamIDEntry 1 }

enc1P1204extCompressedSubstreamIDTable OBJECT-TYPE
    SYNTAX SEQUENCE OF Enc1P1204extCompressedSubstreamIDEntry
    MAX-ACCESS not-accessible
    STATUS     current
    DESCRIPTION
    "
    Name      : Ext. Compressed Substream ID
    Menu Path : /Audio/Audio 4
    Units     : 
    Precision : 0
    Low Range : 0
    High Range: 6
    Details   : Specifies substream ID of externally compressed audio source

     NOTE: Precision/Units/Ranges represent the state of the
           parameter during the MIB generation, and does not
           neccessary reflect the current state of the parameter
    "
::= { enc1Params 1204 }

enc1P1204extCompressedSubstreamIDEntry OBJECT-TYPE
    SYNTAX Enc1P1204extCompressedSubstreamIDEntry
    MAX-ACCESS not-accessible
    STATUS     current
    DESCRIPTION
    "Table Entry for Ext. Compressed Substream ID"
    INDEX { slotId }
::= { enc1P1204extCompressedSubstreamIDTable 1 }

Enc1P1204extCompressedSubstreamIDEntry ::= SEQUENCE {
    enc1P1204extCompressedSubstreamIDValue    INTEGER
}

enc1P1204extCompressedSubstreamIDValue OBJECT-TYPE
    SYNTAX     INTEGER
    MAX-ACCESS read-write
    STATUS     current
    DESCRIPTION
    "Specifies substream ID of externally compressed audio source"
::= { enc1P1204extCompressedSubstreamIDEntry 1 }

enc1P1205extCompressedSubstreamIDTable OBJECT-TYPE
    SYNTAX SEQUENCE OF Enc1P1205extCompressedSubstreamIDEntry
    MAX-ACCESS not-accessible
    STATUS     current
    DESCRIPTION
    "
    Name      : Ext. Compressed Substream ID
    Menu Path : /Audio/Audio 5
    Units     : 
    Precision : 0
    Low Range : 0
    High Range: 6
    Details   : Specifies substream ID of externally compressed audio source

     NOTE: Precision/Units/Ranges represent the state of the
           parameter during the MIB generation, and does not
           neccessary reflect the current state of the parameter
    "
::= { enc1Params 1205 }

enc1P1205extCompressedSubstreamIDEntry OBJECT-TYPE
    SYNTAX Enc1P1205extCompressedSubstreamIDEntry
    MAX-ACCESS not-accessible
    STATUS     current
    DESCRIPTION
    "Table Entry for Ext. Compressed Substream ID"
    INDEX { slotId }
::= { enc1P1205extCompressedSubstreamIDTable 1 }

Enc1P1205extCompressedSubstreamIDEntry ::= SEQUENCE {
    enc1P1205extCompressedSubstreamIDValue    INTEGER
}

enc1P1205extCompressedSubstreamIDValue OBJECT-TYPE
    SYNTAX     INTEGER
    MAX-ACCESS read-write
    STATUS     current
    DESCRIPTION
    "Specifies substream ID of externally compressed audio source"
::= { enc1P1205extCompressedSubstreamIDEntry 1 }

enc1P1206extCompressedSubstreamIDTable OBJECT-TYPE
    SYNTAX SEQUENCE OF Enc1P1206extCompressedSubstreamIDEntry
    MAX-ACCESS not-accessible
    STATUS     current
    DESCRIPTION
    "
    Name      : Ext. Compressed Substream ID
    Menu Path : /Audio/Audio 6
    Units     : 
    Precision : 0
    Low Range : 0
    High Range: 6
    Details   : Specifies substream ID of externally compressed audio source

     NOTE: Precision/Units/Ranges represent the state of the
           parameter during the MIB generation, and does not
           neccessary reflect the current state of the parameter
    "
::= { enc1Params 1206 }

enc1P1206extCompressedSubstreamIDEntry OBJECT-TYPE
    SYNTAX Enc1P1206extCompressedSubstreamIDEntry
    MAX-ACCESS not-accessible
    STATUS     current
    DESCRIPTION
    "Table Entry for Ext. Compressed Substream ID"
    INDEX { slotId }
::= { enc1P1206extCompressedSubstreamIDTable 1 }

Enc1P1206extCompressedSubstreamIDEntry ::= SEQUENCE {
    enc1P1206extCompressedSubstreamIDValue    INTEGER
}

enc1P1206extCompressedSubstreamIDValue OBJECT-TYPE
    SYNTAX     INTEGER
    MAX-ACCESS read-write
    STATUS     current
    DESCRIPTION
    "Specifies substream ID of externally compressed audio source"
::= { enc1P1206extCompressedSubstreamIDEntry 1 }

enc1P1207extCompressedSubstreamIDTable OBJECT-TYPE
    SYNTAX SEQUENCE OF Enc1P1207extCompressedSubstreamIDEntry
    MAX-ACCESS not-accessible
    STATUS     current
    DESCRIPTION
    "
    Name      : Ext. Compressed Substream ID
    Menu Path : /Audio/Audio 7
    Units     : 
    Precision : 0
    Low Range : 0
    High Range: 6
    Details   : Specifies substream ID of externally compressed audio source

     NOTE: Precision/Units/Ranges represent the state of the
           parameter during the MIB generation, and does not
           neccessary reflect the current state of the parameter
    "
::= { enc1Params 1207 }

enc1P1207extCompressedSubstreamIDEntry OBJECT-TYPE
    SYNTAX Enc1P1207extCompressedSubstreamIDEntry
    MAX-ACCESS not-accessible
    STATUS     current
    DESCRIPTION
    "Table Entry for Ext. Compressed Substream ID"
    INDEX { slotId }
::= { enc1P1207extCompressedSubstreamIDTable 1 }

Enc1P1207extCompressedSubstreamIDEntry ::= SEQUENCE {
    enc1P1207extCompressedSubstreamIDValue    INTEGER
}

enc1P1207extCompressedSubstreamIDValue OBJECT-TYPE
    SYNTAX     INTEGER
    MAX-ACCESS read-write
    STATUS     current
    DESCRIPTION
    "Specifies substream ID of externally compressed audio source"
::= { enc1P1207extCompressedSubstreamIDEntry 1 }

enc1P1208extCompressedSubstreamIDTable OBJECT-TYPE
    SYNTAX SEQUENCE OF Enc1P1208extCompressedSubstreamIDEntry
    MAX-ACCESS not-accessible
    STATUS     current
    DESCRIPTION
    "
    Name      : Ext. Compressed Substream ID
    Menu Path : /Audio/Audio 8
    Units     : 
    Precision : 0
    Low Range : 0
    High Range: 6
    Details   : Specifies substream ID of externally compressed audio source

     NOTE: Precision/Units/Ranges represent the state of the
           parameter during the MIB generation, and does not
           neccessary reflect the current state of the parameter
    "
::= { enc1Params 1208 }

enc1P1208extCompressedSubstreamIDEntry OBJECT-TYPE
    SYNTAX Enc1P1208extCompressedSubstreamIDEntry
    MAX-ACCESS not-accessible
    STATUS     current
    DESCRIPTION
    "Table Entry for Ext. Compressed Substream ID"
    INDEX { slotId }
::= { enc1P1208extCompressedSubstreamIDTable 1 }

Enc1P1208extCompressedSubstreamIDEntry ::= SEQUENCE {
    enc1P1208extCompressedSubstreamIDValue    INTEGER
}

enc1P1208extCompressedSubstreamIDValue OBJECT-TYPE
    SYNTAX     INTEGER
    MAX-ACCESS read-write
    STATUS     current
    DESCRIPTION
    "Specifies substream ID of externally compressed audio source"
::= { enc1P1208extCompressedSubstreamIDEntry 1 }

enc1P1209switchingDelayTable OBJECT-TYPE
    SYNTAX SEQUENCE OF Enc1P1209switchingDelayEntry
    MAX-ACCESS not-accessible
    STATUS     current
    DESCRIPTION
    "
    Name      : Switching Delay
    Menu Path : /Video/Input
    Units     : sec
    Precision : 1
    Low Range : 0
    High Range: 100
    Details   : Specifies the switching delay used for video source redundancy.

     NOTE: Precision/Units/Ranges represent the state of the
           parameter during the MIB generation, and does not
           neccessary reflect the current state of the parameter
    "
::= { enc1Params 1209 }

enc1P1209switchingDelayEntry OBJECT-TYPE
    SYNTAX Enc1P1209switchingDelayEntry
    MAX-ACCESS not-accessible
    STATUS     current
    DESCRIPTION
    "Table Entry for Switching Delay"
    INDEX { slotId }
::= { enc1P1209switchingDelayTable 1 }

Enc1P1209switchingDelayEntry ::= SEQUENCE {
    enc1P1209switchingDelayValue    INTEGER
}

enc1P1209switchingDelayValue OBJECT-TYPE
    SYNTAX     INTEGER
    MAX-ACCESS read-write
    STATUS     current
    DESCRIPTION
    "Specifies the switching delay used for video source redundancy."
::= { enc1P1209switchingDelayEntry 1 }

enc1P1210losimageSizeTable OBJECT-TYPE
    SYNTAX SEQUENCE OF Enc1P1210losimageSizeEntry
    MAX-ACCESS not-accessible
    STATUS     current
    DESCRIPTION
    "
    Name      : LOS Image Size
    Menu Path : /Video/Input/LOS Image
    Details   : Specifies the size of the LOS image being configured (Units: Lines).
    "
::= { enc1Params 1210 }

enc1P1210losimageSizeEntry OBJECT-TYPE
    SYNTAX Enc1P1210losimageSizeEntry
    MAX-ACCESS not-accessible
    STATUS     current
    DESCRIPTION
    "Table Entry for LOS Image Size"
    INDEX { slotId }
::= { enc1P1210losimageSizeTable 1 }

Enc1P1210losimageSizeEntry ::= SEQUENCE {
    enc1P1210losimageSizeValue    Enc1E68enumObj
}

enc1P1210losimageSizeValue OBJECT-TYPE
    SYNTAX     Enc1E68enumObj
    MAX-ACCESS read-write
    STATUS     current
    DESCRIPTION
    "Specifies the size of the LOS image being configured (Units: Lines)."
::= { enc1P1210losimageSizeEntry 1 }

enc1P1211selectedLOSImageTable OBJECT-TYPE
    SYNTAX SEQUENCE OF Enc1P1211selectedLOSImageEntry
    MAX-ACCESS not-accessible
    STATUS     current
    DESCRIPTION
    "
    Name      : Selected LOS Image
    Menu Path : /Video/Input/LOS Image
    Details   : Specifies the image to be displayed when there is a video LOS fault and the loss of input behavior is set to 'Image'.
    "
::= { enc1Params 1211 }

enc1P1211selectedLOSImageEntry OBJECT-TYPE
    SYNTAX Enc1P1211selectedLOSImageEntry
    MAX-ACCESS not-accessible
    STATUS     current
    DESCRIPTION
    "Table Entry for Selected LOS Image"
    INDEX { slotId }
::= { enc1P1211selectedLOSImageTable 1 }

Enc1P1211selectedLOSImageEntry ::= SEQUENCE {
    enc1P1211selectedLOSImageValue    DisplayString
}

enc1P1211selectedLOSImageValue OBJECT-TYPE
    SYNTAX     DisplayString
    MAX-ACCESS read-write
    STATUS     current
    DESCRIPTION
    "Specifies the image to be displayed when there is a video LOS fault and the loss of input behavior is set to 'Image'."
::= { enc1P1211selectedLOSImageEntry 1 }

enc1P1212losimageStatusTable OBJECT-TYPE
    SYNTAX SEQUENCE OF Enc1P1212losimageStatusEntry
    MAX-ACCESS not-accessible
    STATUS     current
    DESCRIPTION
    "
    Name      : LOS Image Status
    Menu Path : /Video/Input/LOS Image
    Details   : Specifies the video LOS image loading status.
    "
::= { enc1Params 1212 }

enc1P1212losimageStatusEntry OBJECT-TYPE
    SYNTAX Enc1P1212losimageStatusEntry
    MAX-ACCESS not-accessible
    STATUS     current
    DESCRIPTION
    "Table Entry for LOS Image Status"
    INDEX { slotId }
::= { enc1P1212losimageStatusTable 1 }

Enc1P1212losimageStatusEntry ::= SEQUENCE {
    enc1P1212losimageStatusValue    Enc1E69enumObj
}

enc1P1212losimageStatusValue OBJECT-TYPE
    SYNTAX     Enc1E69enumObj
    MAX-ACCESS read-only
    STATUS     current
    DESCRIPTION
    "Specifies the video LOS image loading status."
::= { enc1P1212losimageStatusEntry 1 }

enc1P1213displayPreviousFileTable OBJECT-TYPE
    SYNTAX SEQUENCE OF Enc1P1213displayPreviousFileEntry
    MAX-ACCESS not-accessible
    STATUS     current
    DESCRIPTION
    "
    Name      : Display Previous File
    Menu Path : /Video/Input/LOS Image
    Details   : Display the previous available image file.
    "
::= { enc1Params 1213 }

enc1P1213displayPreviousFileEntry OBJECT-TYPE
    SYNTAX Enc1P1213displayPreviousFileEntry
    MAX-ACCESS not-accessible
    STATUS     current
    DESCRIPTION
    "Table Entry for Display Previous File"
    INDEX { slotId }
::= { enc1P1213displayPreviousFileTable 1 }

Enc1P1213displayPreviousFileEntry ::= SEQUENCE {
    enc1P1213displayPreviousFileValue    Enc1E22enumObj
}

enc1P1213displayPreviousFileValue OBJECT-TYPE
    SYNTAX     Enc1E22enumObj
    MAX-ACCESS read-write
    STATUS     current
    DESCRIPTION
    "Display the previous available image file."
::= { enc1P1213displayPreviousFileEntry 1 }

enc1P1214imageFileTable OBJECT-TYPE
    SYNTAX SEQUENCE OF Enc1P1214imageFileEntry
    MAX-ACCESS not-accessible
    STATUS     current
    DESCRIPTION
    "
    Name      : Image File
    Menu Path : /Video/Input/LOS Image
    Details   : Indicates an available image file.
    "
::= { enc1Params 1214 }

enc1P1214imageFileEntry OBJECT-TYPE
    SYNTAX Enc1P1214imageFileEntry
    MAX-ACCESS not-accessible
    STATUS     current
    DESCRIPTION
    "Table Entry for Image File"
    INDEX { slotId }
::= { enc1P1214imageFileTable 1 }

Enc1P1214imageFileEntry ::= SEQUENCE {
    enc1P1214imageFileValue    DisplayString
}

enc1P1214imageFileValue OBJECT-TYPE
    SYNTAX     DisplayString
    MAX-ACCESS read-only
    STATUS     current
    DESCRIPTION
    "Indicates an available image file."
::= { enc1P1214imageFileEntry 1 }

enc1P1215displayNextFileTable OBJECT-TYPE
    SYNTAX SEQUENCE OF Enc1P1215displayNextFileEntry
    MAX-ACCESS not-accessible
    STATUS     current
    DESCRIPTION
    "
    Name      : Display Next File
    Menu Path : /Video/Input/LOS Image
    Details   : Display the next available image file.
    "
::= { enc1Params 1215 }

enc1P1215displayNextFileEntry OBJECT-TYPE
    SYNTAX Enc1P1215displayNextFileEntry
    MAX-ACCESS not-accessible
    STATUS     current
    DESCRIPTION
    "Table Entry for Display Next File"
    INDEX { slotId }
::= { enc1P1215displayNextFileTable 1 }

Enc1P1215displayNextFileEntry ::= SEQUENCE {
    enc1P1215displayNextFileValue    Enc1E23enumObj
}

enc1P1215displayNextFileValue OBJECT-TYPE
    SYNTAX     Enc1E23enumObj
    MAX-ACCESS read-write
    STATUS     current
    DESCRIPTION
    "Display the next available image file."
::= { enc1P1215displayNextFileEntry 1 }

enc1P1216selectImageFileTable OBJECT-TYPE
    SYNTAX SEQUENCE OF Enc1P1216selectImageFileEntry
    MAX-ACCESS not-accessible
    STATUS     current
    DESCRIPTION
    "
    Name      : Select Image File
    Menu Path : /Video/Input/LOS Image
    Details   : Select the currently displayed image file as the LOS image file.
    "
::= { enc1Params 1216 }

enc1P1216selectImageFileEntry OBJECT-TYPE
    SYNTAX Enc1P1216selectImageFileEntry
    MAX-ACCESS not-accessible
    STATUS     current
    DESCRIPTION
    "Table Entry for Select Image File"
    INDEX { slotId }
::= { enc1P1216selectImageFileTable 1 }

Enc1P1216selectImageFileEntry ::= SEQUENCE {
    enc1P1216selectImageFileValue    Enc1E24enumObj
}

enc1P1216selectImageFileValue OBJECT-TYPE
    SYNTAX     Enc1E24enumObj
    MAX-ACCESS read-write
    STATUS     current
    DESCRIPTION
    "Select the currently displayed image file as the LOS image file."
::= { enc1P1216selectImageFileEntry 1 }

enc1P1217lossofSignalTable OBJECT-TYPE
    SYNTAX SEQUENCE OF Enc1P1217lossofSignalEntry
    MAX-ACCESS not-accessible
    STATUS     current
    DESCRIPTION
    "
    Name      : Loss of Signal
    Menu Path : /Video/Input/Status/Ext SDI 1
    Details   : Indicates the SDI 1 loss of signal fault.
    "
::= { enc1Params 1217 }

enc1P1217lossofSignalEntry OBJECT-TYPE
    SYNTAX Enc1P1217lossofSignalEntry
    MAX-ACCESS not-accessible
    STATUS     current
    DESCRIPTION
    "Table Entry for Loss of Signal"
    INDEX { slotId }
::= { enc1P1217lossofSignalTable 1 }

Enc1P1217lossofSignalEntry ::= SEQUENCE {
    enc1P1217lossofSignalValue    Enc1E5enumObj
}

enc1P1217lossofSignalValue OBJECT-TYPE
    SYNTAX     Enc1E5enumObj
    MAX-ACCESS read-only
    STATUS     current
    DESCRIPTION
    "Indicates the SDI 1 loss of signal fault."
::= { enc1P1217lossofSignalEntry 1 }

enc1P1218inputStandardTable OBJECT-TYPE
    SYNTAX SEQUENCE OF Enc1P1218inputStandardEntry
    MAX-ACCESS not-accessible
    STATUS     current
    DESCRIPTION
    "
    Name      : Input Standard
    Menu Path : /Video/Input/Status/Ext SDI 1
    Details   : Shows the current video standard on the SDI 1 video.
    "
::= { enc1Params 1218 }

enc1P1218inputStandardEntry OBJECT-TYPE
    SYNTAX Enc1P1218inputStandardEntry
    MAX-ACCESS not-accessible
    STATUS     current
    DESCRIPTION
    "Table Entry for Input Standard"
    INDEX { slotId }
::= { enc1P1218inputStandardTable 1 }

Enc1P1218inputStandardEntry ::= SEQUENCE {
    enc1P1218inputStandardValue    Enc1E61enumObj
}

enc1P1218inputStandardValue OBJECT-TYPE
    SYNTAX     Enc1E61enumObj
    MAX-ACCESS read-only
    STATUS     current
    DESCRIPTION
    "Shows the current video standard on the SDI 1 video."
::= { enc1P1218inputStandardEntry 1 }

enc1P1219syncErrorTable OBJECT-TYPE
    SYNTAX SEQUENCE OF Enc1P1219syncErrorEntry
    MAX-ACCESS not-accessible
    STATUS     current
    DESCRIPTION
    "
    Name      : Sync Error
    Menu Path : /Video/Input/Status/Ext SDI 1
    Units     : 
    Precision : 0
    Low Range : 0
    High Range: -1
    Details   : Indicates the SDI 1 sync error count.

     NOTE: Precision/Units/Ranges represent the state of the
           parameter during the MIB generation, and does not
           neccessary reflect the current state of the parameter
    "
::= { enc1Params 1219 }

enc1P1219syncErrorEntry OBJECT-TYPE
    SYNTAX Enc1P1219syncErrorEntry
    MAX-ACCESS not-accessible
    STATUS     current
    DESCRIPTION
    "Table Entry for Sync Error"
    INDEX { slotId }
::= { enc1P1219syncErrorTable 1 }

Enc1P1219syncErrorEntry ::= SEQUENCE {
    enc1P1219syncErrorValue    INTEGER
}

enc1P1219syncErrorValue OBJECT-TYPE
    SYNTAX     INTEGER
    MAX-ACCESS read-only
    STATUS     current
    DESCRIPTION
    "Indicates the SDI 1 sync error count."
::= { enc1P1219syncErrorEntry 1 }

enc1P1220crcerrorTable OBJECT-TYPE
    SYNTAX SEQUENCE OF Enc1P1220crcerrorEntry
    MAX-ACCESS not-accessible
    STATUS     current
    DESCRIPTION
    "
    Name      : CRC Error
    Menu Path : /Video/Input/Status/Ext SDI 1
    Units     : 
    Precision : 0
    Low Range : 0
    High Range: -1
    Details   : Indicates the SDI 1 CRC error count (HD)

     NOTE: Precision/Units/Ranges represent the state of the
           parameter during the MIB generation, and does not
           neccessary reflect the current state of the parameter
    "
::= { enc1Params 1220 }

enc1P1220crcerrorEntry OBJECT-TYPE
    SYNTAX Enc1P1220crcerrorEntry
    MAX-ACCESS not-accessible
    STATUS     current
    DESCRIPTION
    "Table Entry for CRC Error"
    INDEX { slotId }
::= { enc1P1220crcerrorTable 1 }

Enc1P1220crcerrorEntry ::= SEQUENCE {
    enc1P1220crcerrorValue    INTEGER
}

enc1P1220crcerrorValue OBJECT-TYPE
    SYNTAX     INTEGER
    MAX-ACCESS read-only
    STATUS     current
    DESCRIPTION
    "Indicates the SDI 1 CRC error count (HD)"
::= { enc1P1220crcerrorEntry 1 }

enc1P1221edherrorTable OBJECT-TYPE
    SYNTAX SEQUENCE OF Enc1P1221edherrorEntry
    MAX-ACCESS not-accessible
    STATUS     current
    DESCRIPTION
    "
    Name      : EDH Error
    Menu Path : /Video/Input/Status/Ext SDI 1
    Units     : 
    Precision : 0
    Low Range : 0
    High Range: -1
    Details   : Indicates the SDI 1 EDH error count.

     NOTE: Precision/Units/Ranges represent the state of the
           parameter during the MIB generation, and does not
           neccessary reflect the current state of the parameter
    "
::= { enc1Params 1221 }

enc1P1221edherrorEntry OBJECT-TYPE
    SYNTAX Enc1P1221edherrorEntry
    MAX-ACCESS not-accessible
    STATUS     current
    DESCRIPTION
    "Table Entry for EDH Error"
    INDEX { slotId }
::= { enc1P1221edherrorTable 1 }

Enc1P1221edherrorEntry ::= SEQUENCE {
    enc1P1221edherrorValue    INTEGER
}

enc1P1221edherrorValue OBJECT-TYPE
    SYNTAX     INTEGER
    MAX-ACCESS read-only
    STATUS     current
    DESCRIPTION
    "Indicates the SDI 1 EDH error count."
::= { enc1P1221edherrorEntry 1 }

enc1P1222edhpresentTable OBJECT-TYPE
    SYNTAX SEQUENCE OF Enc1P1222edhpresentEntry
    MAX-ACCESS not-accessible
    STATUS     current
    DESCRIPTION
    "
    Name      : EDH Present
    Menu Path : /Video/Input/Status/Ext SDI 1
    Details   : Indicates whether SDI 1 EDH check bytes are present.
    "
::= { enc1Params 1222 }

enc1P1222edhpresentEntry OBJECT-TYPE
    SYNTAX Enc1P1222edhpresentEntry
    MAX-ACCESS not-accessible
    STATUS     current
    DESCRIPTION
    "Table Entry for EDH Present"
    INDEX { slotId }
::= { enc1P1222edhpresentTable 1 }

Enc1P1222edhpresentEntry ::= SEQUENCE {
    enc1P1222edhpresentValue    Enc1E9enumObj
}

enc1P1222edhpresentValue OBJECT-TYPE
    SYNTAX     Enc1E9enumObj
    MAX-ACCESS read-only
    STATUS     current
    DESCRIPTION
    "Indicates whether SDI 1 EDH check bytes are present."
::= { enc1P1222edhpresentEntry 1 }

enc1P1223clearEXTSDI1StatusTable OBJECT-TYPE
    SYNTAX SEQUENCE OF Enc1P1223clearEXTSDI1StatusEntry
    MAX-ACCESS not-accessible
    STATUS     current
    DESCRIPTION
    "
    Name      : Clear EXT SDI 1 Status
    Menu Path : /Video/Input/Status/Ext SDI 1
    Details   : Clear EXT SDI 1 status counters
    "
::= { enc1Params 1223 }

enc1P1223clearEXTSDI1StatusEntry OBJECT-TYPE
    SYNTAX Enc1P1223clearEXTSDI1StatusEntry
    MAX-ACCESS not-accessible
    STATUS     current
    DESCRIPTION
    "Table Entry for Clear EXT SDI 1 Status"
    INDEX { slotId }
::= { enc1P1223clearEXTSDI1StatusTable 1 }

Enc1P1223clearEXTSDI1StatusEntry ::= SEQUENCE {
    enc1P1223clearEXTSDI1StatusValue    Enc1E20enumObj
}

enc1P1223clearEXTSDI1StatusValue OBJECT-TYPE
    SYNTAX     Enc1E20enumObj
    MAX-ACCESS read-write
    STATUS     current
    DESCRIPTION
    "Clear EXT SDI 1 status counters"
::= { enc1P1223clearEXTSDI1StatusEntry 1 }

enc1P1224lossofSignalTable OBJECT-TYPE
    SYNTAX SEQUENCE OF Enc1P1224lossofSignalEntry
    MAX-ACCESS not-accessible
    STATUS     current
    DESCRIPTION
    "
    Name      : Loss of Signal
    Menu Path : /Video/Input/Status/Ext SDI 2
    Details   : Indicates the SDI 2 loss of signal fault.
    "
::= { enc1Params 1224 }

enc1P1224lossofSignalEntry OBJECT-TYPE
    SYNTAX Enc1P1224lossofSignalEntry
    MAX-ACCESS not-accessible
    STATUS     current
    DESCRIPTION
    "Table Entry for Loss of Signal"
    INDEX { slotId }
::= { enc1P1224lossofSignalTable 1 }

Enc1P1224lossofSignalEntry ::= SEQUENCE {
    enc1P1224lossofSignalValue    Enc1E5enumObj
}

enc1P1224lossofSignalValue OBJECT-TYPE
    SYNTAX     Enc1E5enumObj
    MAX-ACCESS read-only
    STATUS     current
    DESCRIPTION
    "Indicates the SDI 2 loss of signal fault."
::= { enc1P1224lossofSignalEntry 1 }

enc1P1225inputStandardTable OBJECT-TYPE
    SYNTAX SEQUENCE OF Enc1P1225inputStandardEntry
    MAX-ACCESS not-accessible
    STATUS     current
    DESCRIPTION
    "
    Name      : Input Standard
    Menu Path : /Video/Input/Status/Ext SDI 2
    Details   : Shows the current video standard on the SDI 2 video.
    "
::= { enc1Params 1225 }

enc1P1225inputStandardEntry OBJECT-TYPE
    SYNTAX Enc1P1225inputStandardEntry
    MAX-ACCESS not-accessible
    STATUS     current
    DESCRIPTION
    "Table Entry for Input Standard"
    INDEX { slotId }
::= { enc1P1225inputStandardTable 1 }

Enc1P1225inputStandardEntry ::= SEQUENCE {
    enc1P1225inputStandardValue    Enc1E61enumObj
}

enc1P1225inputStandardValue OBJECT-TYPE
    SYNTAX     Enc1E61enumObj
    MAX-ACCESS read-only
    STATUS     current
    DESCRIPTION
    "Shows the current video standard on the SDI 2 video."
::= { enc1P1225inputStandardEntry 1 }

enc1P1226syncErrorTable OBJECT-TYPE
    SYNTAX SEQUENCE OF Enc1P1226syncErrorEntry
    MAX-ACCESS not-accessible
    STATUS     current
    DESCRIPTION
    "
    Name      : Sync Error
    Menu Path : /Video/Input/Status/Ext SDI 2
    Units     : 
    Precision : 0
    Low Range : 0
    High Range: -1
    Details   : Indicates the SDI 2 sync error count.

     NOTE: Precision/Units/Ranges represent the state of the
           parameter during the MIB generation, and does not
           neccessary reflect the current state of the parameter
    "
::= { enc1Params 1226 }

enc1P1226syncErrorEntry OBJECT-TYPE
    SYNTAX Enc1P1226syncErrorEntry
    MAX-ACCESS not-accessible
    STATUS     current
    DESCRIPTION
    "Table Entry for Sync Error"
    INDEX { slotId }
::= { enc1P1226syncErrorTable 1 }

Enc1P1226syncErrorEntry ::= SEQUENCE {
    enc1P1226syncErrorValue    INTEGER
}

enc1P1226syncErrorValue OBJECT-TYPE
    SYNTAX     INTEGER
    MAX-ACCESS read-only
    STATUS     current
    DESCRIPTION
    "Indicates the SDI 2 sync error count."
::= { enc1P1226syncErrorEntry 1 }

enc1P1227crcerrorTable OBJECT-TYPE
    SYNTAX SEQUENCE OF Enc1P1227crcerrorEntry
    MAX-ACCESS not-accessible
    STATUS     current
    DESCRIPTION
    "
    Name      : CRC Error
    Menu Path : /Video/Input/Status/Ext SDI 2
    Units     : 
    Precision : 0
    Low Range : 0
    High Range: -1
    Details   : Indicates the SDI 2 CRC error count (HD)

     NOTE: Precision/Units/Ranges represent the state of the
           parameter during the MIB generation, and does not
           neccessary reflect the current state of the parameter
    "
::= { enc1Params 1227 }

enc1P1227crcerrorEntry OBJECT-TYPE
    SYNTAX Enc1P1227crcerrorEntry
    MAX-ACCESS not-accessible
    STATUS     current
    DESCRIPTION
    "Table Entry for CRC Error"
    INDEX { slotId }
::= { enc1P1227crcerrorTable 1 }

Enc1P1227crcerrorEntry ::= SEQUENCE {
    enc1P1227crcerrorValue    INTEGER
}

enc1P1227crcerrorValue OBJECT-TYPE
    SYNTAX     INTEGER
    MAX-ACCESS read-only
    STATUS     current
    DESCRIPTION
    "Indicates the SDI 2 CRC error count (HD)"
::= { enc1P1227crcerrorEntry 1 }

enc1P1228edherrorTable OBJECT-TYPE
    SYNTAX SEQUENCE OF Enc1P1228edherrorEntry
    MAX-ACCESS not-accessible
    STATUS     current
    DESCRIPTION
    "
    Name      : EDH Error
    Menu Path : /Video/Input/Status/Ext SDI 2
    Units     : 
    Precision : 0
    Low Range : 0
    High Range: -1
    Details   : Indicates the SDI 2 EDH error count.

     NOTE: Precision/Units/Ranges represent the state of the
           parameter during the MIB generation, and does not
           neccessary reflect the current state of the parameter
    "
::= { enc1Params 1228 }

enc1P1228edherrorEntry OBJECT-TYPE
    SYNTAX Enc1P1228edherrorEntry
    MAX-ACCESS not-accessible
    STATUS     current
    DESCRIPTION
    "Table Entry for EDH Error"
    INDEX { slotId }
::= { enc1P1228edherrorTable 1 }

Enc1P1228edherrorEntry ::= SEQUENCE {
    enc1P1228edherrorValue    INTEGER
}

enc1P1228edherrorValue OBJECT-TYPE
    SYNTAX     INTEGER
    MAX-ACCESS read-only
    STATUS     current
    DESCRIPTION
    "Indicates the SDI 2 EDH error count."
::= { enc1P1228edherrorEntry 1 }

enc1P1229edhpresentTable OBJECT-TYPE
    SYNTAX SEQUENCE OF Enc1P1229edhpresentEntry
    MAX-ACCESS not-accessible
    STATUS     current
    DESCRIPTION
    "
    Name      : EDH Present
    Menu Path : /Video/Input/Status/Ext SDI 2
    Details   : Indicates whether SDI 2 EDH check bytes are present.
    "
::= { enc1Params 1229 }

enc1P1229edhpresentEntry OBJECT-TYPE
    SYNTAX Enc1P1229edhpresentEntry
    MAX-ACCESS not-accessible
    STATUS     current
    DESCRIPTION
    "Table Entry for EDH Present"
    INDEX { slotId }
::= { enc1P1229edhpresentTable 1 }

Enc1P1229edhpresentEntry ::= SEQUENCE {
    enc1P1229edhpresentValue    Enc1E9enumObj
}

enc1P1229edhpresentValue OBJECT-TYPE
    SYNTAX     Enc1E9enumObj
    MAX-ACCESS read-only
    STATUS     current
    DESCRIPTION
    "Indicates whether SDI 2 EDH check bytes are present."
::= { enc1P1229edhpresentEntry 1 }

enc1P1230clearEXTSDI2StatusTable OBJECT-TYPE
    SYNTAX SEQUENCE OF Enc1P1230clearEXTSDI2StatusEntry
    MAX-ACCESS not-accessible
    STATUS     current
    DESCRIPTION
    "
    Name      : Clear EXT SDI 2 Status
    Menu Path : /Video/Input/Status/Ext SDI 2
    Details   : Clear EXT SDI 2 status counters
    "
::= { enc1Params 1230 }

enc1P1230clearEXTSDI2StatusEntry OBJECT-TYPE
    SYNTAX Enc1P1230clearEXTSDI2StatusEntry
    MAX-ACCESS not-accessible
    STATUS     current
    DESCRIPTION
    "Table Entry for Clear EXT SDI 2 Status"
    INDEX { slotId }
::= { enc1P1230clearEXTSDI2StatusTable 1 }

Enc1P1230clearEXTSDI2StatusEntry ::= SEQUENCE {
    enc1P1230clearEXTSDI2StatusValue    Enc1E20enumObj
}

enc1P1230clearEXTSDI2StatusValue OBJECT-TYPE
    SYNTAX     Enc1E20enumObj
    MAX-ACCESS read-write
    STATUS     current
    DESCRIPTION
    "Clear EXT SDI 2 status counters"
::= { enc1P1230clearEXTSDI2StatusEntry 1 }

enc1P1231lossofSignalTable OBJECT-TYPE
    SYNTAX SEQUENCE OF Enc1P1231lossofSignalEntry
    MAX-ACCESS not-accessible
    STATUS     current
    DESCRIPTION
    "
    Name      : Loss of Signal
    Menu Path : /Video/Input/Status/CTR SDI
    Details   : Indicates the CTR SDI loss of signal fault.
    "
::= { enc1Params 1231 }

enc1P1231lossofSignalEntry OBJECT-TYPE
    SYNTAX Enc1P1231lossofSignalEntry
    MAX-ACCESS not-accessible
    STATUS     current
    DESCRIPTION
    "Table Entry for Loss of Signal"
    INDEX { slotId }
::= { enc1P1231lossofSignalTable 1 }

Enc1P1231lossofSignalEntry ::= SEQUENCE {
    enc1P1231lossofSignalValue    Enc1E5enumObj
}

enc1P1231lossofSignalValue OBJECT-TYPE
    SYNTAX     Enc1E5enumObj
    MAX-ACCESS read-only
    STATUS     current
    DESCRIPTION
    "Indicates the CTR SDI loss of signal fault."
::= { enc1P1231lossofSignalEntry 1 }

enc1P1232inputStandardTable OBJECT-TYPE
    SYNTAX SEQUENCE OF Enc1P1232inputStandardEntry
    MAX-ACCESS not-accessible
    STATUS     current
    DESCRIPTION
    "
    Name      : Input Standard
    Menu Path : /Video/Input/Status/CTR SDI
    Details   : Shows the current video standard on the CTR SDI video.
    "
::= { enc1Params 1232 }

enc1P1232inputStandardEntry OBJECT-TYPE
    SYNTAX Enc1P1232inputStandardEntry
    MAX-ACCESS not-accessible
    STATUS     current
    DESCRIPTION
    "Table Entry for Input Standard"
    INDEX { slotId }
::= { enc1P1232inputStandardTable 1 }

Enc1P1232inputStandardEntry ::= SEQUENCE {
    enc1P1232inputStandardValue    Enc1E61enumObj
}

enc1P1232inputStandardValue OBJECT-TYPE
    SYNTAX     Enc1E61enumObj
    MAX-ACCESS read-only
    STATUS     current
    DESCRIPTION
    "Shows the current video standard on the CTR SDI video."
::= { enc1P1232inputStandardEntry 1 }

enc1P1233syncErrorTable OBJECT-TYPE
    SYNTAX SEQUENCE OF Enc1P1233syncErrorEntry
    MAX-ACCESS not-accessible
    STATUS     current
    DESCRIPTION
    "
    Name      : Sync Error
    Menu Path : /Video/Input/Status/CTR SDI
    Units     : 
    Precision : 0
    Low Range : 0
    High Range: -1
    Details   : Indicates the CTR SDI sync error count.

     NOTE: Precision/Units/Ranges represent the state of the
           parameter during the MIB generation, and does not
           neccessary reflect the current state of the parameter
    "
::= { enc1Params 1233 }

enc1P1233syncErrorEntry OBJECT-TYPE
    SYNTAX Enc1P1233syncErrorEntry
    MAX-ACCESS not-accessible
    STATUS     current
    DESCRIPTION
    "Table Entry for Sync Error"
    INDEX { slotId }
::= { enc1P1233syncErrorTable 1 }

Enc1P1233syncErrorEntry ::= SEQUENCE {
    enc1P1233syncErrorValue    INTEGER
}

enc1P1233syncErrorValue OBJECT-TYPE
    SYNTAX     INTEGER
    MAX-ACCESS read-only
    STATUS     current
    DESCRIPTION
    "Indicates the CTR SDI sync error count."
::= { enc1P1233syncErrorEntry 1 }

enc1P1234crcerrorTable OBJECT-TYPE
    SYNTAX SEQUENCE OF Enc1P1234crcerrorEntry
    MAX-ACCESS not-accessible
    STATUS     current
    DESCRIPTION
    "
    Name      : CRC Error
    Menu Path : /Video/Input/Status/CTR SDI
    Units     : 
    Precision : 0
    Low Range : 0
    High Range: -1
    Details   : Indicates the CTR SDI CRC error count (HD)

     NOTE: Precision/Units/Ranges represent the state of the
           parameter during the MIB generation, and does not
           neccessary reflect the current state of the parameter
    "
::= { enc1Params 1234 }

enc1P1234crcerrorEntry OBJECT-TYPE
    SYNTAX Enc1P1234crcerrorEntry
    MAX-ACCESS not-accessible
    STATUS     current
    DESCRIPTION
    "Table Entry for CRC Error"
    INDEX { slotId }
::= { enc1P1234crcerrorTable 1 }

Enc1P1234crcerrorEntry ::= SEQUENCE {
    enc1P1234crcerrorValue    INTEGER
}

enc1P1234crcerrorValue OBJECT-TYPE
    SYNTAX     INTEGER
    MAX-ACCESS read-only
    STATUS     current
    DESCRIPTION
    "Indicates the CTR SDI CRC error count (HD)"
::= { enc1P1234crcerrorEntry 1 }

enc1P1235edherrorTable OBJECT-TYPE
    SYNTAX SEQUENCE OF Enc1P1235edherrorEntry
    MAX-ACCESS not-accessible
    STATUS     current
    DESCRIPTION
    "
    Name      : EDH Error
    Menu Path : /Video/Input/Status/CTR SDI
    Units     : 
    Precision : 0
    Low Range : 0
    High Range: -1
    Details   : Indicates the CTR SDI EDH error count.

     NOTE: Precision/Units/Ranges represent the state of the
           parameter during the MIB generation, and does not
           neccessary reflect the current state of the parameter
    "
::= { enc1Params 1235 }

enc1P1235edherrorEntry OBJECT-TYPE
    SYNTAX Enc1P1235edherrorEntry
    MAX-ACCESS not-accessible
    STATUS     current
    DESCRIPTION
    "Table Entry for EDH Error"
    INDEX { slotId }
::= { enc1P1235edherrorTable 1 }

Enc1P1235edherrorEntry ::= SEQUENCE {
    enc1P1235edherrorValue    INTEGER
}

enc1P1235edherrorValue OBJECT-TYPE
    SYNTAX     INTEGER
    MAX-ACCESS read-only
    STATUS     current
    DESCRIPTION
    "Indicates the CTR SDI EDH error count."
::= { enc1P1235edherrorEntry 1 }

enc1P1236edhpresentTable OBJECT-TYPE
    SYNTAX SEQUENCE OF Enc1P1236edhpresentEntry
    MAX-ACCESS not-accessible
    STATUS     current
    DESCRIPTION
    "
    Name      : EDH Present
    Menu Path : /Video/Input/Status/CTR SDI
    Details   : Indicates whether CTR SDI EDH check bytes are present.
    "
::= { enc1Params 1236 }

enc1P1236edhpresentEntry OBJECT-TYPE
    SYNTAX Enc1P1236edhpresentEntry
    MAX-ACCESS not-accessible
    STATUS     current
    DESCRIPTION
    "Table Entry for EDH Present"
    INDEX { slotId }
::= { enc1P1236edhpresentTable 1 }

Enc1P1236edhpresentEntry ::= SEQUENCE {
    enc1P1236edhpresentValue    Enc1E9enumObj
}

enc1P1236edhpresentValue OBJECT-TYPE
    SYNTAX     Enc1E9enumObj
    MAX-ACCESS read-only
    STATUS     current
    DESCRIPTION
    "Indicates whether CTR SDI EDH check bytes are present."
::= { enc1P1236edhpresentEntry 1 }

enc1P1237clearCTRSDIStatusTable OBJECT-TYPE
    SYNTAX SEQUENCE OF Enc1P1237clearCTRSDIStatusEntry
    MAX-ACCESS not-accessible
    STATUS     current
    DESCRIPTION
    "
    Name      : Clear CTR SDI Status
    Menu Path : /Video/Input/Status/CTR SDI
    Details   : Clear CTR SDI status counters
    "
::= { enc1Params 1237 }

enc1P1237clearCTRSDIStatusEntry OBJECT-TYPE
    SYNTAX Enc1P1237clearCTRSDIStatusEntry
    MAX-ACCESS not-accessible
    STATUS     current
    DESCRIPTION
    "Table Entry for Clear CTR SDI Status"
    INDEX { slotId }
::= { enc1P1237clearCTRSDIStatusTable 1 }

Enc1P1237clearCTRSDIStatusEntry ::= SEQUENCE {
    enc1P1237clearCTRSDIStatusValue    Enc1E20enumObj
}

enc1P1237clearCTRSDIStatusValue OBJECT-TYPE
    SYNTAX     Enc1E20enumObj
    MAX-ACCESS read-write
    STATUS     current
    DESCRIPTION
    "Clear CTR SDI status counters"
::= { enc1P1237clearCTRSDIStatusEntry 1 }

enc1P1238videoBitrateModeTable OBJECT-TYPE
    SYNTAX SEQUENCE OF Enc1P1238videoBitrateModeEntry
    MAX-ACCESS not-accessible
    STATUS     current
    DESCRIPTION
    "
    Name      : Video Bitrate Mode
    Menu Path : /Video/Compression
    Details   : Select between automatic computation of video rate from TS rate, or manuall specify the video rate for encoding.
    "
::= { enc1Params 1238 }

enc1P1238videoBitrateModeEntry OBJECT-TYPE
    SYNTAX Enc1P1238videoBitrateModeEntry
    MAX-ACCESS not-accessible
    STATUS     current
    DESCRIPTION
    "Table Entry for Video Bitrate Mode"
    INDEX { slotId }
::= { enc1P1238videoBitrateModeTable 1 }

Enc1P1238videoBitrateModeEntry ::= SEQUENCE {
    enc1P1238videoBitrateModeValue    Enc1E30enumObj
}

enc1P1238videoBitrateModeValue OBJECT-TYPE
    SYNTAX     Enc1E30enumObj
    MAX-ACCESS read-write
    STATUS     current
    DESCRIPTION
    "Select between automatic computation of video rate from TS rate, or manuall specify the video rate for encoding."
::= { enc1P1238videoBitrateModeEntry 1 }

enc1P1239videoBitrateTable OBJECT-TYPE
    SYNTAX SEQUENCE OF Enc1P1239videoBitrateEntry
    MAX-ACCESS not-accessible
    STATUS     current
    DESCRIPTION
    "
    Name      : Video Bitrate
    Menu Path : /Video/Compression
    Units     : Mbits/sec
    Precision : 6
    Low Range : 0
    High Range: 60000000
    Details   : Specifies the manual video bitrate.

     NOTE: Precision/Units/Ranges represent the state of the
           parameter during the MIB generation, and does not
           neccessary reflect the current state of the parameter
    "
::= { enc1Params 1239 }

enc1P1239videoBitrateEntry OBJECT-TYPE
    SYNTAX Enc1P1239videoBitrateEntry
    MAX-ACCESS not-accessible
    STATUS     current
    DESCRIPTION
    "Table Entry for Video Bitrate"
    INDEX { slotId }
::= { enc1P1239videoBitrateTable 1 }

Enc1P1239videoBitrateEntry ::= SEQUENCE {
    enc1P1239videoBitrateValue    INTEGER
}

enc1P1239videoBitrateValue OBJECT-TYPE
    SYNTAX     INTEGER
    MAX-ACCESS read-write
    STATUS     current
    DESCRIPTION
    "Specifies the manual video bitrate."
::= { enc1P1239videoBitrateEntry 1 }

enc1P1240pipVideoBitrateModeTable OBJECT-TYPE
    SYNTAX SEQUENCE OF Enc1P1240pipVideoBitrateModeEntry
    MAX-ACCESS not-accessible
    STATUS     current
    DESCRIPTION
    "
    Name      : Pip Video Bitrate Mode
    Menu Path : /Video/Pip
    Details   : Specifies whether to automatically compute video rate for PIP program or to allow user to manually specify the video rate for the PIP program.
    "
::= { enc1Params 1240 }

enc1P1240pipVideoBitrateModeEntry OBJECT-TYPE
    SYNTAX Enc1P1240pipVideoBitrateModeEntry
    MAX-ACCESS not-accessible
    STATUS     current
    DESCRIPTION
    "Table Entry for Pip Video Bitrate Mode"
    INDEX { slotId }
::= { enc1P1240pipVideoBitrateModeTable 1 }

Enc1P1240pipVideoBitrateModeEntry ::= SEQUENCE {
    enc1P1240pipVideoBitrateModeValue    Enc1E30enumObj
}

enc1P1240pipVideoBitrateModeValue OBJECT-TYPE
    SYNTAX     Enc1E30enumObj
    MAX-ACCESS read-write
    STATUS     current
    DESCRIPTION
    "Specifies whether to automatically compute video rate for PIP program or to allow user to manually specify the video rate for the PIP program."
::= { enc1P1240pipVideoBitrateModeEntry 1 }

enc1P1241pipVideoBitrateTable OBJECT-TYPE
    SYNTAX SEQUENCE OF Enc1P1241pipVideoBitrateEntry
    MAX-ACCESS not-accessible
    STATUS     current
    DESCRIPTION
    "
    Name      : Pip Video Bitrate
    Menu Path : /Video/Pip
    Units     : Mbits/sec
    Precision : 6
    Low Range : 100000
    High Range: 1000000
    Details   : Specifies the video bitrate for the PIP program.

     NOTE: Precision/Units/Ranges represent the state of the
           parameter during the MIB generation, and does not
           neccessary reflect the current state of the parameter
    "
::= { enc1Params 1241 }

enc1P1241pipVideoBitrateEntry OBJECT-TYPE
    SYNTAX Enc1P1241pipVideoBitrateEntry
    MAX-ACCESS not-accessible
    STATUS     current
    DESCRIPTION
    "Table Entry for Pip Video Bitrate"
    INDEX { slotId }
::= { enc1P1241pipVideoBitrateTable 1 }

Enc1P1241pipVideoBitrateEntry ::= SEQUENCE {
    enc1P1241pipVideoBitrateValue    INTEGER
}

enc1P1241pipVideoBitrateValue OBJECT-TYPE
    SYNTAX     INTEGER
    MAX-ACCESS read-write
    STATUS     current
    DESCRIPTION
    "Specifies the video bitrate for the PIP program."
::= { enc1P1241pipVideoBitrateEntry 1 }

enc1P1242responsetoLossOfInputTable OBJECT-TYPE
    SYNTAX SEQUENCE OF Enc1P1242responsetoLossOfInputEntry
    MAX-ACCESS not-accessible
    STATUS     current
    DESCRIPTION
    "
    Name      : Response to Loss Of Input
    Menu Path : /Audio/Audio 1
    Details   : Specifies which action to perform when an input source is not present.
    "
::= { enc1Params 1242 }

enc1P1242responsetoLossOfInputEntry OBJECT-TYPE
    SYNTAX Enc1P1242responsetoLossOfInputEntry
    MAX-ACCESS not-accessible
    STATUS     current
    DESCRIPTION
    "Table Entry for Response to Loss Of Input"
    INDEX { slotId }
::= { enc1P1242responsetoLossOfInputTable 1 }

Enc1P1242responsetoLossOfInputEntry ::= SEQUENCE {
    enc1P1242responsetoLossOfInputValue    Enc1E80enumObj
}

enc1P1242responsetoLossOfInputValue OBJECT-TYPE
    SYNTAX     Enc1E80enumObj
    MAX-ACCESS read-write
    STATUS     current
    DESCRIPTION
    "Specifies which action to perform when an input source is not present."
::= { enc1P1242responsetoLossOfInputEntry 1 }

enc1P1243responsetoLossOfInputTable OBJECT-TYPE
    SYNTAX SEQUENCE OF Enc1P1243responsetoLossOfInputEntry
    MAX-ACCESS not-accessible
    STATUS     current
    DESCRIPTION
    "
    Name      : Response to Loss Of Input
    Menu Path : /Audio/Audio 2
    Details   : Specifies which action to perform when an input source is not present.
    "
::= { enc1Params 1243 }

enc1P1243responsetoLossOfInputEntry OBJECT-TYPE
    SYNTAX Enc1P1243responsetoLossOfInputEntry
    MAX-ACCESS not-accessible
    STATUS     current
    DESCRIPTION
    "Table Entry for Response to Loss Of Input"
    INDEX { slotId }
::= { enc1P1243responsetoLossOfInputTable 1 }

Enc1P1243responsetoLossOfInputEntry ::= SEQUENCE {
    enc1P1243responsetoLossOfInputValue    Enc1E80enumObj
}

enc1P1243responsetoLossOfInputValue OBJECT-TYPE
    SYNTAX     Enc1E80enumObj
    MAX-ACCESS read-write
    STATUS     current
    DESCRIPTION
    "Specifies which action to perform when an input source is not present."
::= { enc1P1243responsetoLossOfInputEntry 1 }

enc1P1244responsetoLossOfInputTable OBJECT-TYPE
    SYNTAX SEQUENCE OF Enc1P1244responsetoLossOfInputEntry
    MAX-ACCESS not-accessible
    STATUS     current
    DESCRIPTION
    "
    Name      : Response to Loss Of Input
    Menu Path : /Audio/Audio 3
    Details   : Specifies which action to perform when an input source is not present.
    "
::= { enc1Params 1244 }

enc1P1244responsetoLossOfInputEntry OBJECT-TYPE
    SYNTAX Enc1P1244responsetoLossOfInputEntry
    MAX-ACCESS not-accessible
    STATUS     current
    DESCRIPTION
    "Table Entry for Response to Loss Of Input"
    INDEX { slotId }
::= { enc1P1244responsetoLossOfInputTable 1 }

Enc1P1244responsetoLossOfInputEntry ::= SEQUENCE {
    enc1P1244responsetoLossOfInputValue    Enc1E80enumObj
}

enc1P1244responsetoLossOfInputValue OBJECT-TYPE
    SYNTAX     Enc1E80enumObj
    MAX-ACCESS read-write
    STATUS     current
    DESCRIPTION
    "Specifies which action to perform when an input source is not present."
::= { enc1P1244responsetoLossOfInputEntry 1 }

enc1P1245responsetoLossOfInputTable OBJECT-TYPE
    SYNTAX SEQUENCE OF Enc1P1245responsetoLossOfInputEntry
    MAX-ACCESS not-accessible
    STATUS     current
    DESCRIPTION
    "
    Name      : Response to Loss Of Input
    Menu Path : /Audio/Audio 4
    Details   : Specifies which action to perform when an input source is not present.
    "
::= { enc1Params 1245 }

enc1P1245responsetoLossOfInputEntry OBJECT-TYPE
    SYNTAX Enc1P1245responsetoLossOfInputEntry
    MAX-ACCESS not-accessible
    STATUS     current
    DESCRIPTION
    "Table Entry for Response to Loss Of Input"
    INDEX { slotId }
::= { enc1P1245responsetoLossOfInputTable 1 }

Enc1P1245responsetoLossOfInputEntry ::= SEQUENCE {
    enc1P1245responsetoLossOfInputValue    Enc1E80enumObj
}

enc1P1245responsetoLossOfInputValue OBJECT-TYPE
    SYNTAX     Enc1E80enumObj
    MAX-ACCESS read-write
    STATUS     current
    DESCRIPTION
    "Specifies which action to perform when an input source is not present."
::= { enc1P1245responsetoLossOfInputEntry 1 }

enc1P1246responsetoLossOfInputTable OBJECT-TYPE
    SYNTAX SEQUENCE OF Enc1P1246responsetoLossOfInputEntry
    MAX-ACCESS not-accessible
    STATUS     current
    DESCRIPTION
    "
    Name      : Response to Loss Of Input
    Menu Path : /Audio/Audio 5
    Details   : Specifies which action to perform when an input source is not present.
    "
::= { enc1Params 1246 }

enc1P1246responsetoLossOfInputEntry OBJECT-TYPE
    SYNTAX Enc1P1246responsetoLossOfInputEntry
    MAX-ACCESS not-accessible
    STATUS     current
    DESCRIPTION
    "Table Entry for Response to Loss Of Input"
    INDEX { slotId }
::= { enc1P1246responsetoLossOfInputTable 1 }

Enc1P1246responsetoLossOfInputEntry ::= SEQUENCE {
    enc1P1246responsetoLossOfInputValue    Enc1E80enumObj
}

enc1P1246responsetoLossOfInputValue OBJECT-TYPE
    SYNTAX     Enc1E80enumObj
    MAX-ACCESS read-write
    STATUS     current
    DESCRIPTION
    "Specifies which action to perform when an input source is not present."
::= { enc1P1246responsetoLossOfInputEntry 1 }

enc1P1247responsetoLossOfInputTable OBJECT-TYPE
    SYNTAX SEQUENCE OF Enc1P1247responsetoLossOfInputEntry
    MAX-ACCESS not-accessible
    STATUS     current
    DESCRIPTION
    "
    Name      : Response to Loss Of Input
    Menu Path : /Audio/Audio 6
    Details   : Specifies which action to perform when an input source is not present.
    "
::= { enc1Params 1247 }

enc1P1247responsetoLossOfInputEntry OBJECT-TYPE
    SYNTAX Enc1P1247responsetoLossOfInputEntry
    MAX-ACCESS not-accessible
    STATUS     current
    DESCRIPTION
    "Table Entry for Response to Loss Of Input"
    INDEX { slotId }
::= { enc1P1247responsetoLossOfInputTable 1 }

Enc1P1247responsetoLossOfInputEntry ::= SEQUENCE {
    enc1P1247responsetoLossOfInputValue    Enc1E80enumObj
}

enc1P1247responsetoLossOfInputValue OBJECT-TYPE
    SYNTAX     Enc1E80enumObj
    MAX-ACCESS read-write
    STATUS     current
    DESCRIPTION
    "Specifies which action to perform when an input source is not present."
::= { enc1P1247responsetoLossOfInputEntry 1 }

enc1P1248responsetoLossOfInputTable OBJECT-TYPE
    SYNTAX SEQUENCE OF Enc1P1248responsetoLossOfInputEntry
    MAX-ACCESS not-accessible
    STATUS     current
    DESCRIPTION
    "
    Name      : Response to Loss Of Input
    Menu Path : /Audio/Audio 7
    Details   : Specifies which action to perform when an input source is not present.
    "
::= { enc1Params 1248 }

enc1P1248responsetoLossOfInputEntry OBJECT-TYPE
    SYNTAX Enc1P1248responsetoLossOfInputEntry
    MAX-ACCESS not-accessible
    STATUS     current
    DESCRIPTION
    "Table Entry for Response to Loss Of Input"
    INDEX { slotId }
::= { enc1P1248responsetoLossOfInputTable 1 }

Enc1P1248responsetoLossOfInputEntry ::= SEQUENCE {
    enc1P1248responsetoLossOfInputValue    Enc1E80enumObj
}

enc1P1248responsetoLossOfInputValue OBJECT-TYPE
    SYNTAX     Enc1E80enumObj
    MAX-ACCESS read-write
    STATUS     current
    DESCRIPTION
    "Specifies which action to perform when an input source is not present."
::= { enc1P1248responsetoLossOfInputEntry 1 }

enc1P1249responsetoLossOfInputTable OBJECT-TYPE
    SYNTAX SEQUENCE OF Enc1P1249responsetoLossOfInputEntry
    MAX-ACCESS not-accessible
    STATUS     current
    DESCRIPTION
    "
    Name      : Response to Loss Of Input
    Menu Path : /Audio/Audio 8
    Details   : Specifies which action to perform when an input source is not present.
    "
::= { enc1Params 1249 }

enc1P1249responsetoLossOfInputEntry OBJECT-TYPE
    SYNTAX Enc1P1249responsetoLossOfInputEntry
    MAX-ACCESS not-accessible
    STATUS     current
    DESCRIPTION
    "Table Entry for Response to Loss Of Input"
    INDEX { slotId }
::= { enc1P1249responsetoLossOfInputTable 1 }

Enc1P1249responsetoLossOfInputEntry ::= SEQUENCE {
    enc1P1249responsetoLossOfInputValue    Enc1E80enumObj
}

enc1P1249responsetoLossOfInputValue OBJECT-TYPE
    SYNTAX     Enc1E80enumObj
    MAX-ACCESS read-write
    STATUS     current
    DESCRIPTION
    "Specifies which action to perform when an input source is not present."
::= { enc1P1249responsetoLossOfInputEntry 1 }

enc1P1250programIDTable OBJECT-TYPE
    SYNTAX SEQUENCE OF Enc1P1250programIDEntry
    MAX-ACCESS not-accessible
    STATUS     current
    DESCRIPTION
    "
    Name      : Program ID
    Menu Path : /Audio/Metadata Generator 1
    Details   : Indicates current audio metadata program being displayed.
    "
::= { enc1Params 1250 }

enc1P1250programIDEntry OBJECT-TYPE
    SYNTAX Enc1P1250programIDEntry
    MAX-ACCESS not-accessible
    STATUS     current
    DESCRIPTION
    "Table Entry for Program ID"
    INDEX { slotId }
::= { enc1P1250programIDTable 1 }

Enc1P1250programIDEntry ::= SEQUENCE {
    enc1P1250programIDValue    Enc1E97enumObj
}

enc1P1250programIDValue OBJECT-TYPE
    SYNTAX     Enc1E97enumObj
    MAX-ACCESS read-only
    STATUS     current
    DESCRIPTION
    "Indicates current audio metadata program being displayed."
::= { enc1P1250programIDEntry 1 }

enc1P1251programIDTable OBJECT-TYPE
    SYNTAX SEQUENCE OF Enc1P1251programIDEntry
    MAX-ACCESS not-accessible
    STATUS     current
    DESCRIPTION
    "
    Name      : Program ID
    Menu Path : /Audio/Metadata Generator 2
    Details   : Indicates current audio metadata program being displayed.
    "
::= { enc1Params 1251 }

enc1P1251programIDEntry OBJECT-TYPE
    SYNTAX Enc1P1251programIDEntry
    MAX-ACCESS not-accessible
    STATUS     current
    DESCRIPTION
    "Table Entry for Program ID"
    INDEX { slotId }
::= { enc1P1251programIDTable 1 }

Enc1P1251programIDEntry ::= SEQUENCE {
    enc1P1251programIDValue    Enc1E97enumObj
}

enc1P1251programIDValue OBJECT-TYPE
    SYNTAX     Enc1E97enumObj
    MAX-ACCESS read-only
    STATUS     current
    DESCRIPTION
    "Indicates current audio metadata program being displayed."
::= { enc1P1251programIDEntry 1 }

enc1P1252injectedIdentifierTable OBJECT-TYPE
    SYNTAX SEQUENCE OF Enc1P1252injectedIdentifierEntry
    MAX-ACCESS not-accessible
    STATUS     current
    DESCRIPTION
    "
    Name      : Injected Identifier
    Menu Path : /TS Mux/BISS
    Details   : Specifies BISS Injected ID for the program. Enter as a 14 digit hexadecimal string.
    "
::= { enc1Params 1252 }

enc1P1252injectedIdentifierEntry OBJECT-TYPE
    SYNTAX Enc1P1252injectedIdentifierEntry
    MAX-ACCESS not-accessible
    STATUS     current
    DESCRIPTION
    "Table Entry for Injected Identifier"
    INDEX { slotId }
::= { enc1P1252injectedIdentifierTable 1 }

Enc1P1252injectedIdentifierEntry ::= SEQUENCE {
    enc1P1252injectedIdentifierValue    DisplayString
}

enc1P1252injectedIdentifierValue OBJECT-TYPE
    SYNTAX     DisplayString
    MAX-ACCESS read-write
    STATUS     current
    DESCRIPTION
    "Specifies BISS Injected ID for the program. Enter as a 14 digit hexadecimal string."
::= { enc1P1252injectedIdentifierEntry 1 }

enc1P1253encryptedSessionWordTable OBJECT-TYPE
    SYNTAX SEQUENCE OF Enc1P1253encryptedSessionWordEntry
    MAX-ACCESS not-accessible
    STATUS     current
    DESCRIPTION
    "
    Name      : Encrypted Session Word
    Menu Path : /TS Mux/BISS
    Details   : Show the 16-digit hexadecimal BISS Encrypted Session Word for the program.
    "
::= { enc1Params 1253 }

enc1P1253encryptedSessionWordEntry OBJECT-TYPE
    SYNTAX Enc1P1253encryptedSessionWordEntry
    MAX-ACCESS not-accessible
    STATUS     current
    DESCRIPTION
    "Table Entry for Encrypted Session Word"
    INDEX { slotId }
::= { enc1P1253encryptedSessionWordTable 1 }

Enc1P1253encryptedSessionWordEntry ::= SEQUENCE {
    enc1P1253encryptedSessionWordValue    DisplayString
}

enc1P1253encryptedSessionWordValue OBJECT-TYPE
    SYNTAX     DisplayString
    MAX-ACCESS read-only
    STATUS     current
    DESCRIPTION
    "Show the 16-digit hexadecimal BISS Encrypted Session Word for the program."
::= { enc1P1253encryptedSessionWordEntry 1 }

enc1P1254ch51DolbyDigitalPlusProfessionalEncoderTable OBJECT-TYPE
    SYNTAX SEQUENCE OF Enc1P1254ch51DolbyDigitalPlusProfessionalEncoderEntry
    MAX-ACCESS not-accessible
    STATUS     current
    DESCRIPTION
    "
    Name      : 5.1ch Dolby Digital Plus Professional Encoder.
    Menu Path : /Misc
    Details   : Dolby Digital Plus version info
    "
::= { enc1Params 1254 }

enc1P1254ch51DolbyDigitalPlusProfessionalEncoderEntry OBJECT-TYPE
    SYNTAX Enc1P1254ch51DolbyDigitalPlusProfessionalEncoderEntry
    MAX-ACCESS not-accessible
    STATUS     current
    DESCRIPTION
    "Table Entry for 5.1ch Dolby Digital Plus Professional Encoder."
    INDEX { slotId }
::= { enc1P1254ch51DolbyDigitalPlusProfessionalEncoderTable 1 }

Enc1P1254ch51DolbyDigitalPlusProfessionalEncoderEntry ::= SEQUENCE {
    enc1P1254ch51DolbyDigitalPlusProfessionalEncoderValue    Enc1E106enumObj
}

enc1P1254ch51DolbyDigitalPlusProfessionalEncoderValue OBJECT-TYPE
    SYNTAX     Enc1E106enumObj
    MAX-ACCESS read-only
    STATUS     current
    DESCRIPTION
    "Dolby Digital Plus version info"
::= { enc1P1254ch51DolbyDigitalPlusProfessionalEncoderEntry 1 }

enc1P1255moduleFaultAlarmPriorityTable OBJECT-TYPE
    SYNTAX SEQUENCE OF Enc1P1255moduleFaultAlarmPriorityEntry
    MAX-ACCESS not-accessible
    STATUS     current
    DESCRIPTION
    "
    Name      : Module Fault Alarm Priority
    Menu Path : /Misc
    Details   : Set module fault priority threshold.
    "
::= { enc1Params 1255 }

enc1P1255moduleFaultAlarmPriorityEntry OBJECT-TYPE
    SYNTAX Enc1P1255moduleFaultAlarmPriorityEntry
    MAX-ACCESS not-accessible
    STATUS     current
    DESCRIPTION
    "Table Entry for Module Fault Alarm Priority"
    INDEX { slotId }
::= { enc1P1255moduleFaultAlarmPriorityTable 1 }

Enc1P1255moduleFaultAlarmPriorityEntry ::= SEQUENCE {
    enc1P1255moduleFaultAlarmPriorityValue    Enc1E25enumObj
}

enc1P1255moduleFaultAlarmPriorityValue OBJECT-TYPE
    SYNTAX     Enc1E25enumObj
    MAX-ACCESS read-write
    STATUS     current
    DESCRIPTION
    "Set module fault priority threshold."
::= { enc1P1255moduleFaultAlarmPriorityEntry 1 }

enc1P1256genlockTable OBJECT-TYPE
    SYNTAX SEQUENCE OF Enc1P1256genlockEntry
    MAX-ACCESS not-accessible
    STATUS     current
    DESCRIPTION
    "
    Name      : Genlock
    Menu Path : /Video/Input
    Details   : Disable/Enable Genlock.
    "
::= { enc1Params 1256 }

enc1P1256genlockEntry OBJECT-TYPE
    SYNTAX Enc1P1256genlockEntry
    MAX-ACCESS not-accessible
    STATUS     current
    DESCRIPTION
    "Table Entry for Genlock"
    INDEX { slotId }
::= { enc1P1256genlockTable 1 }

Enc1P1256genlockEntry ::= SEQUENCE {
    enc1P1256genlockValue    Enc1E54enumObj
}

enc1P1256genlockValue OBJECT-TYPE
    SYNTAX     Enc1E54enumObj
    MAX-ACCESS read-write
    STATUS     current
    DESCRIPTION
    "Disable/Enable Genlock."
::= { enc1P1256genlockEntry 1 }

enc1P1257referenceSelectTable OBJECT-TYPE
    SYNTAX SEQUENCE OF Enc1P1257referenceSelectEntry
    MAX-ACCESS not-accessible
    STATUS     current
    DESCRIPTION
    "
    Name      : Reference Select
    Menu Path : /Video/Input
    Details   : Select reference clock used for Genlock.
    "
::= { enc1Params 1257 }

enc1P1257referenceSelectEntry OBJECT-TYPE
    SYNTAX Enc1P1257referenceSelectEntry
    MAX-ACCESS not-accessible
    STATUS     current
    DESCRIPTION
    "Table Entry for Reference Select"
    INDEX { slotId }
::= { enc1P1257referenceSelectTable 1 }

Enc1P1257referenceSelectEntry ::= SEQUENCE {
    enc1P1257referenceSelectValue    Enc1E55enumObj
}

enc1P1257referenceSelectValue OBJECT-TYPE
    SYNTAX     Enc1E55enumObj
    MAX-ACCESS read-write
    STATUS     current
    DESCRIPTION
    "Select reference clock used for Genlock."
::= { enc1P1257referenceSelectEntry 1 }

enc1P1261processingModeTable OBJECT-TYPE
    SYNTAX SEQUENCE OF Enc1P1261processingModeEntry
    MAX-ACCESS not-accessible
    STATUS     current
    DESCRIPTION
    "
    Name      : Processing Mode
    Menu Path : /Audio/AAP 1 Configuration/General
    Details   : Advanced Audio Processor configuration select.
    "
::= { enc1Params 1261 }

enc1P1261processingModeEntry OBJECT-TYPE
    SYNTAX Enc1P1261processingModeEntry
    MAX-ACCESS not-accessible
    STATUS     current
    DESCRIPTION
    "Table Entry for Processing Mode"
    INDEX { slotId }
::= { enc1P1261processingModeTable 1 }

Enc1P1261processingModeEntry ::= SEQUENCE {
    enc1P1261processingModeValue    Enc1E144enumObj
}

enc1P1261processingModeValue OBJECT-TYPE
    SYNTAX     Enc1E144enumObj
    MAX-ACCESS read-write
    STATUS     current
    DESCRIPTION
    "Advanced Audio Processor configuration select."
::= { enc1P1261processingModeEntry 1 }

enc1P1262processingDelayTable OBJECT-TYPE
    SYNTAX SEQUENCE OF Enc1P1262processingDelayEntry
    MAX-ACCESS not-accessible
    STATUS     current
    DESCRIPTION
    "
    Name      : Processing Delay
    Menu Path : /Audio/AAP 1 Configuration/General
    Units     : ms
    Precision : 2
    Low Range : 0
    High Range: -1
    Details   : Informational - automatically included in lipsync adjustment.

     NOTE: Precision/Units/Ranges represent the state of the
           parameter during the MIB generation, and does not
           neccessary reflect the current state of the parameter
    "
::= { enc1Params 1262 }

enc1P1262processingDelayEntry OBJECT-TYPE
    SYNTAX Enc1P1262processingDelayEntry
    MAX-ACCESS not-accessible
    STATUS     current
    DESCRIPTION
    "Table Entry for Processing Delay"
    INDEX { slotId }
::= { enc1P1262processingDelayTable 1 }

Enc1P1262processingDelayEntry ::= SEQUENCE {
    enc1P1262processingDelayValue    INTEGER
}

enc1P1262processingDelayValue OBJECT-TYPE
    SYNTAX     INTEGER
    MAX-ACCESS read-only
    STATUS     current
    DESCRIPTION
    "Informational - automatically included in lipsync adjustment."
::= { enc1P1262processingDelayEntry 1 }

enc1P1263costDolbyEDecoderDEDTable OBJECT-TYPE
    SYNTAX SEQUENCE OF Enc1P1263costDolbyEDecoderDEDEntry
    MAX-ACCESS not-accessible
    STATUS     current
    DESCRIPTION
    "
    Name      : Cost, Dolby E Decoder (DED)
    Menu Path : Not Applicable
    Details   : Reports number of Dolby E decoder licensed required for the selected function
    "
::= { enc1Params 1263 }

enc1P1263costDolbyEDecoderDEDEntry OBJECT-TYPE
    SYNTAX Enc1P1263costDolbyEDecoderDEDEntry
    MAX-ACCESS not-accessible
    STATUS     current
    DESCRIPTION
    "Table Entry for Cost, Dolby E Decoder (DED)"
    INDEX { slotId }
::= { enc1P1263costDolbyEDecoderDEDTable 1 }

Enc1P1263costDolbyEDecoderDEDEntry ::= SEQUENCE {
    enc1P1263costDolbyEDecoderDEDValue    Enc1E146enumObj
}

enc1P1263costDolbyEDecoderDEDValue OBJECT-TYPE
    SYNTAX     Enc1E146enumObj
    MAX-ACCESS read-only
    STATUS     current
    DESCRIPTION
    "Reports number of Dolby E decoder licensed required for the selected function"
::= { enc1P1263costDolbyEDecoderDEDEntry 1 }

enc1P1264costDTSNeuralTable OBJECT-TYPE
    SYNTAX SEQUENCE OF Enc1P1264costDTSNeuralEntry
    MAX-ACCESS not-accessible
    STATUS     current
    DESCRIPTION
    "
    Name      : Cost, DTS Neural
    Menu Path : Not Applicable
    Details   : Reports number of DTS Neural credits required for the selected function
    "
::= { enc1Params 1264 }

enc1P1264costDTSNeuralEntry OBJECT-TYPE
    SYNTAX Enc1P1264costDTSNeuralEntry
    MAX-ACCESS not-accessible
    STATUS     current
    DESCRIPTION
    "Table Entry for Cost, DTS Neural"
    INDEX { slotId }
::= { enc1P1264costDTSNeuralTable 1 }

Enc1P1264costDTSNeuralEntry ::= SEQUENCE {
    enc1P1264costDTSNeuralValue    Enc1E149enumObj
}

enc1P1264costDTSNeuralValue OBJECT-TYPE
    SYNTAX     Enc1E149enumObj
    MAX-ACCESS read-only
    STATUS     current
    DESCRIPTION
    "Reports number of DTS Neural credits required for the selected function"
::= { enc1P1264costDTSNeuralEntry 1 }

enc1P1265loudnessControlPresetSelectTable OBJECT-TYPE
    SYNTAX SEQUENCE OF Enc1P1265loudnessControlPresetSelectEntry
    MAX-ACCESS not-accessible
    STATUS     current
    DESCRIPTION
    "
    Name      : Loudness Control Preset Select
    Menu Path : /Audio/AAP 1 Configuration/General
    Details   : Selects a loudness control preset.
    "
::= { enc1Params 1265 }

enc1P1265loudnessControlPresetSelectEntry OBJECT-TYPE
    SYNTAX Enc1P1265loudnessControlPresetSelectEntry
    MAX-ACCESS not-accessible
    STATUS     current
    DESCRIPTION
    "Table Entry for Loudness Control Preset Select"
    INDEX { slotId }
::= { enc1P1265loudnessControlPresetSelectTable 1 }

Enc1P1265loudnessControlPresetSelectEntry ::= SEQUENCE {
    enc1P1265loudnessControlPresetSelectValue    Enc1E173enumObj
}

enc1P1265loudnessControlPresetSelectValue OBJECT-TYPE
    SYNTAX     Enc1E173enumObj
    MAX-ACCESS read-write
    STATUS     current
    DESCRIPTION
    "Selects a loudness control preset."
::= { enc1P1265loudnessControlPresetSelectEntry 1 }

enc1P1266mcpsusageTable OBJECT-TYPE
    SYNTAX SEQUENCE OF Enc1P1266mcpsusageEntry
    MAX-ACCESS not-accessible
    STATUS     current
    DESCRIPTION
    "
    Name      : MCPS Usage
    Menu Path : Not Applicable
    Details   : Reports the MCPS usage for the selected function.
    "
::= { enc1Params 1266 }

enc1P1266mcpsusageEntry OBJECT-TYPE
    SYNTAX Enc1P1266mcpsusageEntry
    MAX-ACCESS not-accessible
    STATUS     current
    DESCRIPTION
    "Table Entry for MCPS Usage"
    INDEX { slotId }
::= { enc1P1266mcpsusageTable 1 }

Enc1P1266mcpsusageEntry ::= SEQUENCE {
    enc1P1266mcpsusageValue    Enc1E150enumObj
}

enc1P1266mcpsusageValue OBJECT-TYPE
    SYNTAX     Enc1E150enumObj
    MAX-ACCESS read-only
    STATUS     current
    DESCRIPTION
    "Reports the MCPS usage for the selected function."
::= { enc1P1266mcpsusageEntry 1 }

enc1P1267selectionStatusTable OBJECT-TYPE
    SYNTAX SEQUENCE OF Enc1P1267selectionStatusEntry
    MAX-ACCESS not-accessible
    STATUS     current
    DESCRIPTION
    "
    Name      : Selection Status
    Menu Path : Not Applicable
    Details   : Indicates the recent selection status
    "
::= { enc1Params 1267 }

enc1P1267selectionStatusEntry OBJECT-TYPE
    SYNTAX Enc1P1267selectionStatusEntry
    MAX-ACCESS not-accessible
    STATUS     current
    DESCRIPTION
    "Table Entry for Selection Status"
    INDEX { slotId }
::= { enc1P1267selectionStatusTable 1 }

Enc1P1267selectionStatusEntry ::= SEQUENCE {
    enc1P1267selectionStatusValue    Enc1E165enumObj
}

enc1P1267selectionStatusValue OBJECT-TYPE
    SYNTAX     Enc1E165enumObj
    MAX-ACCESS read-only
    STATUS     current
    DESCRIPTION
    "Indicates the recent selection status"
::= { enc1P1267selectionStatusEntry 1 }

enc1P1268aap1StatusTable OBJECT-TYPE
    SYNTAX SEQUENCE OF Enc1P1268aap1StatusEntry
    MAX-ACCESS not-accessible
    STATUS     current
    DESCRIPTION
    "
    Name      : AAP 1 Status
    Menu Path : /Audio/AAP 1 Configuration/General
    Details   : Indicates the overall state of the Advanced Audio Processor.
    "
::= { enc1Params 1268 }

enc1P1268aap1StatusEntry OBJECT-TYPE
    SYNTAX Enc1P1268aap1StatusEntry
    MAX-ACCESS not-accessible
    STATUS     current
    DESCRIPTION
    "Table Entry for AAP 1 Status"
    INDEX { slotId }
::= { enc1P1268aap1StatusTable 1 }

Enc1P1268aap1StatusEntry ::= SEQUENCE {
    enc1P1268aap1StatusValue    Enc1E203enumObj
}

enc1P1268aap1StatusValue OBJECT-TYPE
    SYNTAX     Enc1E203enumObj
    MAX-ACCESS read-only
    STATUS     current
    DESCRIPTION
    "Indicates the overall state of the Advanced Audio Processor."
::= { enc1P1268aap1StatusEntry 1 }

enc1P1269loudnessControlFunctionTable OBJECT-TYPE
    SYNTAX SEQUENCE OF Enc1P1269loudnessControlFunctionEntry
    MAX-ACCESS not-accessible
    STATUS     current
    DESCRIPTION
    "
    Name      : Loudness Control Function
    Menu Path : /Audio/AAP 1 Configuration/DTS Neural Loudness Ctrl 1
    Details   : Bypasses the loudness control circuit.
    "
::= { enc1Params 1269 }

enc1P1269loudnessControlFunctionEntry OBJECT-TYPE
    SYNTAX Enc1P1269loudnessControlFunctionEntry
    MAX-ACCESS not-accessible
    STATUS     current
    DESCRIPTION
    "Table Entry for Loudness Control Function"
    INDEX { slotId }
::= { enc1P1269loudnessControlFunctionTable 1 }

Enc1P1269loudnessControlFunctionEntry ::= SEQUENCE {
    enc1P1269loudnessControlFunctionValue    Enc1E174enumObj
}

enc1P1269loudnessControlFunctionValue OBJECT-TYPE
    SYNTAX     Enc1E174enumObj
    MAX-ACCESS read-write
    STATUS     current
    DESCRIPTION
    "Bypasses the loudness control circuit."
::= { enc1P1269loudnessControlFunctionEntry 1 }

enc1P1270loudnessControlStatusTable OBJECT-TYPE
    SYNTAX SEQUENCE OF Enc1P1270loudnessControlStatusEntry
    MAX-ACCESS not-accessible
    STATUS     current
    DESCRIPTION
    "
    Name      : Loudness Control Status
    Menu Path : /Audio/AAP 1 Configuration/DTS Neural Loudness Ctrl 1
    Details   : Indicates the state of loudness control processing.
    "
::= { enc1Params 1270 }

enc1P1270loudnessControlStatusEntry OBJECT-TYPE
    SYNTAX Enc1P1270loudnessControlStatusEntry
    MAX-ACCESS not-accessible
    STATUS     current
    DESCRIPTION
    "Table Entry for Loudness Control Status"
    INDEX { slotId }
::= { enc1P1270loudnessControlStatusTable 1 }

Enc1P1270loudnessControlStatusEntry ::= SEQUENCE {
    enc1P1270loudnessControlStatusValue    Enc1E172enumObj
}

enc1P1270loudnessControlStatusValue OBJECT-TYPE
    SYNTAX     Enc1E172enumObj
    MAX-ACCESS read-only
    STATUS     current
    DESCRIPTION
    "Indicates the state of loudness control processing."
::= { enc1P1270loudnessControlStatusEntry 1 }

enc1P1271loudnessMeasurementTypeTable OBJECT-TYPE
    SYNTAX SEQUENCE OF Enc1P1271loudnessMeasurementTypeEntry
    MAX-ACCESS not-accessible
    STATUS     current
    DESCRIPTION
    "
    Name      : Loudness Measurement Type
    Menu Path : /Audio/AAP 1 Configuration/DTS Neural Loudness Ctrl 1
    Details   : Specifies the type of loudness measurement to make prior to performing loudness control.
    "
::= { enc1Params 1271 }

enc1P1271loudnessMeasurementTypeEntry OBJECT-TYPE
    SYNTAX Enc1P1271loudnessMeasurementTypeEntry
    MAX-ACCESS not-accessible
    STATUS     current
    DESCRIPTION
    "Table Entry for Loudness Measurement Type"
    INDEX { slotId }
::= { enc1P1271loudnessMeasurementTypeTable 1 }

Enc1P1271loudnessMeasurementTypeEntry ::= SEQUENCE {
    enc1P1271loudnessMeasurementTypeValue    Enc1E175enumObj
}

enc1P1271loudnessMeasurementTypeValue OBJECT-TYPE
    SYNTAX     Enc1E175enumObj
    MAX-ACCESS read-write
    STATUS     current
    DESCRIPTION
    "Specifies the type of loudness measurement to make prior to performing loudness control."
::= { enc1P1271loudnessMeasurementTypeEntry 1 }

enc1P1272targetLoudnessLevelTable OBJECT-TYPE
    SYNTAX SEQUENCE OF Enc1P1272targetLoudnessLevelEntry
    MAX-ACCESS not-accessible
    STATUS     current
    DESCRIPTION
    "
    Name      : Target Loudness Level
    Menu Path : /Audio/AAP 1 Configuration/DTS Neural Loudness Ctrl 1
    Units     : dBEq/LKFS
    Precision : 0
    Low Range : -40
    High Range: 0
    Details   : Specifies the loudness level that will be targeted.

     NOTE: Precision/Units/Ranges represent the state of the
           parameter during the MIB generation, and does not
           neccessary reflect the current state of the parameter
    "
::= { enc1Params 1272 }

enc1P1272targetLoudnessLevelEntry OBJECT-TYPE
    SYNTAX Enc1P1272targetLoudnessLevelEntry
    MAX-ACCESS not-accessible
    STATUS     current
    DESCRIPTION
    "Table Entry for Target Loudness Level"
    INDEX { slotId }
::= { enc1P1272targetLoudnessLevelTable 1 }

Enc1P1272targetLoudnessLevelEntry ::= SEQUENCE {
    enc1P1272targetLoudnessLevelValue    INTEGER
}

enc1P1272targetLoudnessLevelValue OBJECT-TYPE
    SYNTAX     INTEGER
    MAX-ACCESS read-write
    STATUS     current
    DESCRIPTION
    "Specifies the loudness level that will be targeted."
::= { enc1P1272targetLoudnessLevelEntry 1 }

enc1P1273lcratioTable OBJECT-TYPE
    SYNTAX SEQUENCE OF Enc1P1273lcratioEntry
    MAX-ACCESS not-accessible
    STATUS     current
    DESCRIPTION
    "
    Name      : LC Ratio
    Menu Path : /Audio/AAP 1 Configuration/DTS Neural Loudness Ctrl 1
    Units     : 
    Precision : 2
    Low Range : 0
    High Range: 100
    Details   : Controls the amount of gain or attenuation that is applied when loudness differences are measured.

     NOTE: Precision/Units/Ranges represent the state of the
           parameter during the MIB generation, and does not
           neccessary reflect the current state of the parameter
    "
::= { enc1Params 1273 }

enc1P1273lcratioEntry OBJECT-TYPE
    SYNTAX Enc1P1273lcratioEntry
    MAX-ACCESS not-accessible
    STATUS     current
    DESCRIPTION
    "Table Entry for LC Ratio"
    INDEX { slotId }
::= { enc1P1273lcratioTable 1 }

Enc1P1273lcratioEntry ::= SEQUENCE {
    enc1P1273lcratioValue    INTEGER
}

enc1P1273lcratioValue OBJECT-TYPE
    SYNTAX     INTEGER
    MAX-ACCESS read-write
    STATUS     current
    DESCRIPTION
    "Controls the amount of gain or attenuation that is applied when loudness differences are measured."
::= { enc1P1273lcratioEntry 1 }

enc1P1274upperThresholdTable OBJECT-TYPE
    SYNTAX SEQUENCE OF Enc1P1274upperThresholdEntry
    MAX-ACCESS not-accessible
    STATUS     current
    DESCRIPTION
    "
    Name      : Upper Threshold
    Menu Path : /Audio/AAP 1 Configuration/DTS Neural Loudness Ctrl 1
    Units     : dB
    Precision : 0
    Low Range : 0
    High Range: 20
    Details   : Specifies the highest measured loudness of the input that will be permitted before attenuation is applied.

     NOTE: Precision/Units/Ranges represent the state of the
           parameter during the MIB generation, and does not
           neccessary reflect the current state of the parameter
    "
::= { enc1Params 1274 }

enc1P1274upperThresholdEntry OBJECT-TYPE
    SYNTAX Enc1P1274upperThresholdEntry
    MAX-ACCESS not-accessible
    STATUS     current
    DESCRIPTION
    "Table Entry for Upper Threshold"
    INDEX { slotId }
::= { enc1P1274upperThresholdTable 1 }

Enc1P1274upperThresholdEntry ::= SEQUENCE {
    enc1P1274upperThresholdValue    INTEGER
}

enc1P1274upperThresholdValue OBJECT-TYPE
    SYNTAX     INTEGER
    MAX-ACCESS read-write
    STATUS     current
    DESCRIPTION
    "Specifies the highest measured loudness of the input that will be permitted before attenuation is applied."
::= { enc1P1274upperThresholdEntry 1 }

enc1P1275lowerThresholdTable OBJECT-TYPE
    SYNTAX SEQUENCE OF Enc1P1275lowerThresholdEntry
    MAX-ACCESS not-accessible
    STATUS     current
    DESCRIPTION
    "
    Name      : Lower Threshold
    Menu Path : /Audio/AAP 1 Configuration/DTS Neural Loudness Ctrl 1
    Units     : dB
    Precision : 0
    Low Range : -20
    High Range: 0
    Details   : Specifies the lowest measured loudness of the input that will be permitted before gain is applied.

     NOTE: Precision/Units/Ranges represent the state of the
           parameter during the MIB generation, and does not
           neccessary reflect the current state of the parameter
    "
::= { enc1Params 1275 }

enc1P1275lowerThresholdEntry OBJECT-TYPE
    SYNTAX Enc1P1275lowerThresholdEntry
    MAX-ACCESS not-accessible
    STATUS     current
    DESCRIPTION
    "Table Entry for Lower Threshold"
    INDEX { slotId }
::= { enc1P1275lowerThresholdTable 1 }

Enc1P1275lowerThresholdEntry ::= SEQUENCE {
    enc1P1275lowerThresholdValue    INTEGER
}

enc1P1275lowerThresholdValue OBJECT-TYPE
    SYNTAX     INTEGER
    MAX-ACCESS read-write
    STATUS     current
    DESCRIPTION
    "Specifies the lowest measured loudness of the input that will be permitted before gain is applied."
::= { enc1P1275lowerThresholdEntry 1 }

enc1P1276freezeWindowTable OBJECT-TYPE
    SYNTAX SEQUENCE OF Enc1P1276freezeWindowEntry
    MAX-ACCESS not-accessible
    STATUS     current
    DESCRIPTION
    "
    Name      : Freeze Window
    Menu Path : /Audio/AAP 1 Configuration/DTS Neural Loudness Ctrl 1
    Units     : dB
    Precision : 1
    Low Range : 0
    High Range: 100
    Details   : Specifies the size of a window which small loudness differences are allowed without the need to change gain or attenuation.

     NOTE: Precision/Units/Ranges represent the state of the
           parameter during the MIB generation, and does not
           neccessary reflect the current state of the parameter
    "
::= { enc1Params 1276 }

enc1P1276freezeWindowEntry OBJECT-TYPE
    SYNTAX Enc1P1276freezeWindowEntry
    MAX-ACCESS not-accessible
    STATUS     current
    DESCRIPTION
    "Table Entry for Freeze Window"
    INDEX { slotId }
::= { enc1P1276freezeWindowTable 1 }

Enc1P1276freezeWindowEntry ::= SEQUENCE {
    enc1P1276freezeWindowValue    INTEGER
}

enc1P1276freezeWindowValue OBJECT-TYPE
    SYNTAX     INTEGER
    MAX-ACCESS read-write
    STATUS     current
    DESCRIPTION
    "Specifies the size of a window which small loudness differences are allowed without the need to change gain or attenuation."
::= { enc1P1276freezeWindowEntry 1 }

enc1P1277quietThresholdTable OBJECT-TYPE
    SYNTAX SEQUENCE OF Enc1P1277quietThresholdEntry
    MAX-ACCESS not-accessible
    STATUS     current
    DESCRIPTION
    "
    Name      : Quiet Threshold
    Menu Path : /Audio/AAP 1 Configuration/DTS Neural Loudness Ctrl 1
    Units     : dBEq
    Precision : 0
    Low Range : -80
    High Range: -20
    Details   : Controls the noise floor level.

     NOTE: Precision/Units/Ranges represent the state of the
           parameter during the MIB generation, and does not
           neccessary reflect the current state of the parameter
    "
::= { enc1Params 1277 }

enc1P1277quietThresholdEntry OBJECT-TYPE
    SYNTAX Enc1P1277quietThresholdEntry
    MAX-ACCESS not-accessible
    STATUS     current
    DESCRIPTION
    "Table Entry for Quiet Threshold"
    INDEX { slotId }
::= { enc1P1277quietThresholdTable 1 }

Enc1P1277quietThresholdEntry ::= SEQUENCE {
    enc1P1277quietThresholdValue    INTEGER
}

enc1P1277quietThresholdValue OBJECT-TYPE
    SYNTAX     INTEGER
    MAX-ACCESS read-write
    STATUS     current
    DESCRIPTION
    "Controls the noise floor level."
::= { enc1P1277quietThresholdEntry 1 }

enc1P1278attackTimeTable OBJECT-TYPE
    SYNTAX SEQUENCE OF Enc1P1278attackTimeEntry
    MAX-ACCESS not-accessible
    STATUS     current
    DESCRIPTION
    "
    Name      : Attack Time
    Menu Path : /Audio/AAP 1 Configuration/DTS Neural Loudness Ctrl 1
    Units     : ms
    Precision : 0
    Low Range : 5
    High Range: 150
    Details   : Controls how quickly the processing will respond to sharp increases in loudness.

     NOTE: Precision/Units/Ranges represent the state of the
           parameter during the MIB generation, and does not
           neccessary reflect the current state of the parameter
    "
::= { enc1Params 1278 }

enc1P1278attackTimeEntry OBJECT-TYPE
    SYNTAX Enc1P1278attackTimeEntry
    MAX-ACCESS not-accessible
    STATUS     current
    DESCRIPTION
    "Table Entry for Attack Time"
    INDEX { slotId }
::= { enc1P1278attackTimeTable 1 }

Enc1P1278attackTimeEntry ::= SEQUENCE {
    enc1P1278attackTimeValue    INTEGER
}

enc1P1278attackTimeValue OBJECT-TYPE
    SYNTAX     INTEGER
    MAX-ACCESS read-write
    STATUS     current
    DESCRIPTION
    "Controls how quickly the processing will respond to sharp increases in loudness."
::= { enc1P1278attackTimeEntry 1 }

enc1P1279releaseTimeTable OBJECT-TYPE
    SYNTAX SEQUENCE OF Enc1P1279releaseTimeEntry
    MAX-ACCESS not-accessible
    STATUS     current
    DESCRIPTION
    "
    Name      : Release Time
    Menu Path : /Audio/AAP 1 Configuration/DTS Neural Loudness Ctrl 1
    Units     : ms
    Precision : 0
    Low Range : 20
    High Range: 500
    Details   : Controls how quickly the processing will respond to sharp decreases in loudness.

     NOTE: Precision/Units/Ranges represent the state of the
           parameter during the MIB generation, and does not
           neccessary reflect the current state of the parameter
    "
::= { enc1Params 1279 }

enc1P1279releaseTimeEntry OBJECT-TYPE
    SYNTAX Enc1P1279releaseTimeEntry
    MAX-ACCESS not-accessible
    STATUS     current
    DESCRIPTION
    "Table Entry for Release Time"
    INDEX { slotId }
::= { enc1P1279releaseTimeTable 1 }

Enc1P1279releaseTimeEntry ::= SEQUENCE {
    enc1P1279releaseTimeValue    INTEGER
}

enc1P1279releaseTimeValue OBJECT-TYPE
    SYNTAX     INTEGER
    MAX-ACCESS read-write
    STATUS     current
    DESCRIPTION
    "Controls how quickly the processing will respond to sharp decreases in loudness."
::= { enc1P1279releaseTimeEntry 1 }

enc1P1280compressorThresholdTable OBJECT-TYPE
    SYNTAX SEQUENCE OF Enc1P1280compressorThresholdEntry
    MAX-ACCESS not-accessible
    STATUS     current
    DESCRIPTION
    "
    Name      : Compressor Threshold
    Menu Path : /Audio/AAP 1 Configuration/DTS Neural Loudness Ctrl 1
    Units     : dB
    Precision : 0
    Low Range : 0
    High Range: 16
    Details   : Specifies the allowable short-term peak above the target level.

     NOTE: Precision/Units/Ranges represent the state of the
           parameter during the MIB generation, and does not
           neccessary reflect the current state of the parameter
    "
::= { enc1Params 1280 }

enc1P1280compressorThresholdEntry OBJECT-TYPE
    SYNTAX Enc1P1280compressorThresholdEntry
    MAX-ACCESS not-accessible
    STATUS     current
    DESCRIPTION
    "Table Entry for Compressor Threshold"
    INDEX { slotId }
::= { enc1P1280compressorThresholdTable 1 }

Enc1P1280compressorThresholdEntry ::= SEQUENCE {
    enc1P1280compressorThresholdValue    INTEGER
}

enc1P1280compressorThresholdValue OBJECT-TYPE
    SYNTAX     INTEGER
    MAX-ACCESS read-write
    STATUS     current
    DESCRIPTION
    "Specifies the allowable short-term peak above the target level."
::= { enc1P1280compressorThresholdEntry 1 }

enc1P1281compressorRatioTable OBJECT-TYPE
    SYNTAX SEQUENCE OF Enc1P1281compressorRatioEntry
    MAX-ACCESS not-accessible
    STATUS     current
    DESCRIPTION
    "
    Name      : Compressor Ratio
    Menu Path : /Audio/AAP 1 Configuration/DTS Neural Loudness Ctrl 1
    Units     : 
    Precision : 2
    Low Range : 0
    High Range: 100
    Details   : Controls the amount of attenuation applied when short-term peaks exceed the compressor threshold.

     NOTE: Precision/Units/Ranges represent the state of the
           parameter during the MIB generation, and does not
           neccessary reflect the current state of the parameter
    "
::= { enc1Params 1281 }

enc1P1281compressorRatioEntry OBJECT-TYPE
    SYNTAX Enc1P1281compressorRatioEntry
    MAX-ACCESS not-accessible
    STATUS     current
    DESCRIPTION
    "Table Entry for Compressor Ratio"
    INDEX { slotId }
::= { enc1P1281compressorRatioTable 1 }

Enc1P1281compressorRatioEntry ::= SEQUENCE {
    enc1P1281compressorRatioValue    INTEGER
}

enc1P1281compressorRatioValue OBJECT-TYPE
    SYNTAX     INTEGER
    MAX-ACCESS read-write
    STATUS     current
    DESCRIPTION
    "Controls the amount of attenuation applied when short-term peaks exceed the compressor threshold."
::= { enc1P1281compressorRatioEntry 1 }

enc1P1282loudnessShapingTable OBJECT-TYPE
    SYNTAX SEQUENCE OF Enc1P1282loudnessShapingEntry
    MAX-ACCESS not-accessible
    STATUS     current
    DESCRIPTION
    "
    Name      : Loudness Shaping
    Menu Path : /Audio/AAP 1 Configuration/DTS Neural Loudness Ctrl 1
    Units     : 
    Precision : 1
    Low Range : 0
    High Range: 10
    Details   : Specifies the amount of loudness shaping desired.

     NOTE: Precision/Units/Ranges represent the state of the
           parameter during the MIB generation, and does not
           neccessary reflect the current state of the parameter
    "
::= { enc1Params 1282 }

enc1P1282loudnessShapingEntry OBJECT-TYPE
    SYNTAX Enc1P1282loudnessShapingEntry
    MAX-ACCESS not-accessible
    STATUS     current
    DESCRIPTION
    "Table Entry for Loudness Shaping"
    INDEX { slotId }
::= { enc1P1282loudnessShapingTable 1 }

Enc1P1282loudnessShapingEntry ::= SEQUENCE {
    enc1P1282loudnessShapingValue    INTEGER
}

enc1P1282loudnessShapingValue OBJECT-TYPE
    SYNTAX     INTEGER
    MAX-ACCESS read-write
    STATUS     current
    DESCRIPTION
    "Specifies the amount of loudness shaping desired."
::= { enc1P1282loudnessShapingEntry 1 }

enc1P1283finalLimiterCeilingTable OBJECT-TYPE
    SYNTAX SEQUENCE OF Enc1P1283finalLimiterCeilingEntry
    MAX-ACCESS not-accessible
    STATUS     current
    DESCRIPTION
    "
    Name      : Final Limiter Ceiling
    Menu Path : /Audio/AAP 1 Configuration/DTS Neural Loudness Ctrl 1
    Units     : dBFS
    Precision : 0
    Low Range : -20
    High Range: 0
    Details   : Specifies the threshold above which final limiting will be applied.

     NOTE: Precision/Units/Ranges represent the state of the
           parameter during the MIB generation, and does not
           neccessary reflect the current state of the parameter
    "
::= { enc1Params 1283 }

enc1P1283finalLimiterCeilingEntry OBJECT-TYPE
    SYNTAX Enc1P1283finalLimiterCeilingEntry
    MAX-ACCESS not-accessible
    STATUS     current
    DESCRIPTION
    "Table Entry for Final Limiter Ceiling"
    INDEX { slotId }
::= { enc1P1283finalLimiterCeilingTable 1 }

Enc1P1283finalLimiterCeilingEntry ::= SEQUENCE {
    enc1P1283finalLimiterCeilingValue    INTEGER
}

enc1P1283finalLimiterCeilingValue OBJECT-TYPE
    SYNTAX     INTEGER
    MAX-ACCESS read-write
    STATUS     current
    DESCRIPTION
    "Specifies the threshold above which final limiting will be applied."
::= { enc1P1283finalLimiterCeilingEntry 1 }

enc1P1284runFinalLimitersTable OBJECT-TYPE
    SYNTAX SEQUENCE OF Enc1P1284runFinalLimitersEntry
    MAX-ACCESS not-accessible
    STATUS     current
    DESCRIPTION
    "
    Name      : Run Final Limiters
    Menu Path : /Audio/AAP 1 Configuration/DTS Neural Loudness Ctrl 1
    Details   : Enables final limiters to be applied according to the value of the Final Limiter Ceiling.
    "
::= { enc1Params 1284 }

enc1P1284runFinalLimitersEntry OBJECT-TYPE
    SYNTAX Enc1P1284runFinalLimitersEntry
    MAX-ACCESS not-accessible
    STATUS     current
    DESCRIPTION
    "Table Entry for Run Final Limiters"
    INDEX { slotId }
::= { enc1P1284runFinalLimitersTable 1 }

Enc1P1284runFinalLimitersEntry ::= SEQUENCE {
    enc1P1284runFinalLimitersValue    Enc1E152enumObj
}

enc1P1284runFinalLimitersValue OBJECT-TYPE
    SYNTAX     Enc1E152enumObj
    MAX-ACCESS read-write
    STATUS     current
    DESCRIPTION
    "Enables final limiters to be applied according to the value of the Final Limiter Ceiling."
::= { enc1P1284runFinalLimitersEntry 1 }

enc1P1285meteringTable OBJECT-TYPE
    SYNTAX SEQUENCE OF Enc1P1285meteringEntry
    MAX-ACCESS not-accessible
    STATUS     current
    DESCRIPTION
    "
    Name      : Metering
    Menu Path : /Audio/AAP 1 Configuration/DTS Neural Loudness Ctrl 1
    Details   : Activates the real-time meters (below).
    "
::= { enc1Params 1285 }

enc1P1285meteringEntry OBJECT-TYPE
    SYNTAX Enc1P1285meteringEntry
    MAX-ACCESS not-accessible
    STATUS     current
    DESCRIPTION
    "Table Entry for Metering"
    INDEX { slotId }
::= { enc1P1285meteringTable 1 }

Enc1P1285meteringEntry ::= SEQUENCE {
    enc1P1285meteringValue    Enc1E154enumObj
}

enc1P1285meteringValue OBJECT-TYPE
    SYNTAX     Enc1E154enumObj
    MAX-ACCESS read-write
    STATUS     current
    DESCRIPTION
    "Activates the real-time meters (below)."
::= { enc1P1285meteringEntry 1 }

enc1P1286currentInputLoudnessTable OBJECT-TYPE
    SYNTAX SEQUENCE OF Enc1P1286currentInputLoudnessEntry
    MAX-ACCESS not-accessible
    STATUS     current
    DESCRIPTION
    "
    Name      : Current Input Loudness
    Menu Path : /Audio/AAP 1 Configuration/DTS Neural Loudness Ctrl 1
    Units     : dBEq
    Precision : 0
    Low Range : -60
    High Range: 20
    Details   : Reports the smoothed input loudness measurement.

     NOTE: Precision/Units/Ranges represent the state of the
           parameter during the MIB generation, and does not
           neccessary reflect the current state of the parameter
    "
::= { enc1Params 1286 }

enc1P1286currentInputLoudnessEntry OBJECT-TYPE
    SYNTAX Enc1P1286currentInputLoudnessEntry
    MAX-ACCESS not-accessible
    STATUS     current
    DESCRIPTION
    "Table Entry for Current Input Loudness"
    INDEX { slotId }
::= { enc1P1286currentInputLoudnessTable 1 }

Enc1P1286currentInputLoudnessEntry ::= SEQUENCE {
    enc1P1286currentInputLoudnessValue    INTEGER
}

enc1P1286currentInputLoudnessValue OBJECT-TYPE
    SYNTAX     INTEGER
    MAX-ACCESS read-only
    STATUS     current
    DESCRIPTION
    "Reports the smoothed input loudness measurement."
::= { enc1P1286currentInputLoudnessEntry 1 }

enc1P1287currentInputPeakTable OBJECT-TYPE
    SYNTAX SEQUENCE OF Enc1P1287currentInputPeakEntry
    MAX-ACCESS not-accessible
    STATUS     current
    DESCRIPTION
    "
    Name      : Current Input Peak
    Menu Path : /Audio/AAP 1 Configuration/DTS Neural Loudness Ctrl 1
    Units     : dBFS
    Precision : 0
    Low Range : -60
    High Range: 20
    Details   : Reports the input peak measurement.

     NOTE: Precision/Units/Ranges represent the state of the
           parameter during the MIB generation, and does not
           neccessary reflect the current state of the parameter
    "
::= { enc1Params 1287 }

enc1P1287currentInputPeakEntry OBJECT-TYPE
    SYNTAX Enc1P1287currentInputPeakEntry
    MAX-ACCESS not-accessible
    STATUS     current
    DESCRIPTION
    "Table Entry for Current Input Peak"
    INDEX { slotId }
::= { enc1P1287currentInputPeakTable 1 }

Enc1P1287currentInputPeakEntry ::= SEQUENCE {
    enc1P1287currentInputPeakValue    INTEGER
}

enc1P1287currentInputPeakValue OBJECT-TYPE
    SYNTAX     INTEGER
    MAX-ACCESS read-only
    STATUS     current
    DESCRIPTION
    "Reports the input peak measurement."
::= { enc1P1287currentInputPeakEntry 1 }

enc1P1288currentOutputLoudnessTable OBJECT-TYPE
    SYNTAX SEQUENCE OF Enc1P1288currentOutputLoudnessEntry
    MAX-ACCESS not-accessible
    STATUS     current
    DESCRIPTION
    "
    Name      : Current Output Loudness
    Menu Path : /Audio/AAP 1 Configuration/DTS Neural Loudness Ctrl 1
    Units     : dBEq
    Precision : 0
    Low Range : -60
    High Range: 20
    Details   : Reports the smoothed output loudness measurement.

     NOTE: Precision/Units/Ranges represent the state of the
           parameter during the MIB generation, and does not
           neccessary reflect the current state of the parameter
    "
::= { enc1Params 1288 }

enc1P1288currentOutputLoudnessEntry OBJECT-TYPE
    SYNTAX Enc1P1288currentOutputLoudnessEntry
    MAX-ACCESS not-accessible
    STATUS     current
    DESCRIPTION
    "Table Entry for Current Output Loudness"
    INDEX { slotId }
::= { enc1P1288currentOutputLoudnessTable 1 }

Enc1P1288currentOutputLoudnessEntry ::= SEQUENCE {
    enc1P1288currentOutputLoudnessValue    INTEGER
}

enc1P1288currentOutputLoudnessValue OBJECT-TYPE
    SYNTAX     INTEGER
    MAX-ACCESS read-only
    STATUS     current
    DESCRIPTION
    "Reports the smoothed output loudness measurement."
::= { enc1P1288currentOutputLoudnessEntry 1 }

enc1P1289currentOutputPeakTable OBJECT-TYPE
    SYNTAX SEQUENCE OF Enc1P1289currentOutputPeakEntry
    MAX-ACCESS not-accessible
    STATUS     current
    DESCRIPTION
    "
    Name      : Current Output Peak
    Menu Path : /Audio/AAP 1 Configuration/DTS Neural Loudness Ctrl 1
    Units     : dBFS
    Precision : 0
    Low Range : -60
    High Range: 20
    Details   : Reports the output peak measurement.

     NOTE: Precision/Units/Ranges represent the state of the
           parameter during the MIB generation, and does not
           neccessary reflect the current state of the parameter
    "
::= { enc1Params 1289 }

enc1P1289currentOutputPeakEntry OBJECT-TYPE
    SYNTAX Enc1P1289currentOutputPeakEntry
    MAX-ACCESS not-accessible
    STATUS     current
    DESCRIPTION
    "Table Entry for Current Output Peak"
    INDEX { slotId }
::= { enc1P1289currentOutputPeakTable 1 }

Enc1P1289currentOutputPeakEntry ::= SEQUENCE {
    enc1P1289currentOutputPeakValue    INTEGER
}

enc1P1289currentOutputPeakValue OBJECT-TYPE
    SYNTAX     INTEGER
    MAX-ACCESS read-only
    STATUS     current
    DESCRIPTION
    "Reports the output peak measurement."
::= { enc1P1289currentOutputPeakEntry 1 }

enc1P1290currentCorrectionTable OBJECT-TYPE
    SYNTAX SEQUENCE OF Enc1P1290currentCorrectionEntry
    MAX-ACCESS not-accessible
    STATUS     current
    DESCRIPTION
    "
    Name      : Current Correction
    Menu Path : /Audio/AAP 1 Configuration/DTS Neural Loudness Ctrl 1
    Units     : dB
    Precision : 0
    Low Range : -60
    High Range: 60
    Details   : Reports the amount of correction being applied.

     NOTE: Precision/Units/Ranges represent the state of the
           parameter during the MIB generation, and does not
           neccessary reflect the current state of the parameter
    "
::= { enc1Params 1290 }

enc1P1290currentCorrectionEntry OBJECT-TYPE
    SYNTAX Enc1P1290currentCorrectionEntry
    MAX-ACCESS not-accessible
    STATUS     current
    DESCRIPTION
    "Table Entry for Current Correction"
    INDEX { slotId }
::= { enc1P1290currentCorrectionTable 1 }

Enc1P1290currentCorrectionEntry ::= SEQUENCE {
    enc1P1290currentCorrectionValue    INTEGER
}

enc1P1290currentCorrectionValue OBJECT-TYPE
    SYNTAX     INTEGER
    MAX-ACCESS read-only
    STATUS     current
    DESCRIPTION
    "Reports the amount of correction being applied."
::= { enc1P1290currentCorrectionEntry 1 }

enc1P1291currentCompressionTable OBJECT-TYPE
    SYNTAX SEQUENCE OF Enc1P1291currentCompressionEntry
    MAX-ACCESS not-accessible
    STATUS     current
    DESCRIPTION
    "
    Name      : Current Compression
    Menu Path : /Audio/AAP 1 Configuration/DTS Neural Loudness Ctrl 1
    Units     : dB
    Precision : 0
    Low Range : -60
    High Range: 60
    Details   : Reports the amount of compression being applied.

     NOTE: Precision/Units/Ranges represent the state of the
           parameter during the MIB generation, and does not
           neccessary reflect the current state of the parameter
    "
::= { enc1Params 1291 }

enc1P1291currentCompressionEntry OBJECT-TYPE
    SYNTAX Enc1P1291currentCompressionEntry
    MAX-ACCESS not-accessible
    STATUS     current
    DESCRIPTION
    "Table Entry for Current Compression"
    INDEX { slotId }
::= { enc1P1291currentCompressionTable 1 }

Enc1P1291currentCompressionEntry ::= SEQUENCE {
    enc1P1291currentCompressionValue    INTEGER
}

enc1P1291currentCompressionValue OBJECT-TYPE
    SYNTAX     INTEGER
    MAX-ACCESS read-only
    STATUS     current
    DESCRIPTION
    "Reports the amount of compression being applied."
::= { enc1P1291currentCompressionEntry 1 }

enc1P1292loudnessControlFunctionTable OBJECT-TYPE
    SYNTAX SEQUENCE OF Enc1P1292loudnessControlFunctionEntry
    MAX-ACCESS not-accessible
    STATUS     current
    DESCRIPTION
    "
    Name      : Loudness Control Function
    Menu Path : /Audio/AAP 1 Configuration/DTS Neural Loudness Ctrl 2
    Details   : Bypasses the loudness control circuit.
    "
::= { enc1Params 1292 }

enc1P1292loudnessControlFunctionEntry OBJECT-TYPE
    SYNTAX Enc1P1292loudnessControlFunctionEntry
    MAX-ACCESS not-accessible
    STATUS     current
    DESCRIPTION
    "Table Entry for Loudness Control Function"
    INDEX { slotId }
::= { enc1P1292loudnessControlFunctionTable 1 }

Enc1P1292loudnessControlFunctionEntry ::= SEQUENCE {
    enc1P1292loudnessControlFunctionValue    Enc1E174enumObj
}

enc1P1292loudnessControlFunctionValue OBJECT-TYPE
    SYNTAX     Enc1E174enumObj
    MAX-ACCESS read-write
    STATUS     current
    DESCRIPTION
    "Bypasses the loudness control circuit."
::= { enc1P1292loudnessControlFunctionEntry 1 }

enc1P1293loudnessControlStatusTable OBJECT-TYPE
    SYNTAX SEQUENCE OF Enc1P1293loudnessControlStatusEntry
    MAX-ACCESS not-accessible
    STATUS     current
    DESCRIPTION
    "
    Name      : Loudness Control Status
    Menu Path : /Audio/AAP 1 Configuration/DTS Neural Loudness Ctrl 2
    Details   : Indicates the state of loudness control processing.
    "
::= { enc1Params 1293 }

enc1P1293loudnessControlStatusEntry OBJECT-TYPE
    SYNTAX Enc1P1293loudnessControlStatusEntry
    MAX-ACCESS not-accessible
    STATUS     current
    DESCRIPTION
    "Table Entry for Loudness Control Status"
    INDEX { slotId }
::= { enc1P1293loudnessControlStatusTable 1 }

Enc1P1293loudnessControlStatusEntry ::= SEQUENCE {
    enc1P1293loudnessControlStatusValue    Enc1E172enumObj
}

enc1P1293loudnessControlStatusValue OBJECT-TYPE
    SYNTAX     Enc1E172enumObj
    MAX-ACCESS read-only
    STATUS     current
    DESCRIPTION
    "Indicates the state of loudness control processing."
::= { enc1P1293loudnessControlStatusEntry 1 }

enc1P1294loudnessMeasurementTypeTable OBJECT-TYPE
    SYNTAX SEQUENCE OF Enc1P1294loudnessMeasurementTypeEntry
    MAX-ACCESS not-accessible
    STATUS     current
    DESCRIPTION
    "
    Name      : Loudness Measurement Type
    Menu Path : /Audio/AAP 1 Configuration/DTS Neural Loudness Ctrl 2
    Details   : Specifies the type of loudness measurement to make prior to performing loudness control.
    "
::= { enc1Params 1294 }

enc1P1294loudnessMeasurementTypeEntry OBJECT-TYPE
    SYNTAX Enc1P1294loudnessMeasurementTypeEntry
    MAX-ACCESS not-accessible
    STATUS     current
    DESCRIPTION
    "Table Entry for Loudness Measurement Type"
    INDEX { slotId }
::= { enc1P1294loudnessMeasurementTypeTable 1 }

Enc1P1294loudnessMeasurementTypeEntry ::= SEQUENCE {
    enc1P1294loudnessMeasurementTypeValue    Enc1E175enumObj
}

enc1P1294loudnessMeasurementTypeValue OBJECT-TYPE
    SYNTAX     Enc1E175enumObj
    MAX-ACCESS read-write
    STATUS     current
    DESCRIPTION
    "Specifies the type of loudness measurement to make prior to performing loudness control."
::= { enc1P1294loudnessMeasurementTypeEntry 1 }

enc1P1295targetLoudnessLevelTable OBJECT-TYPE
    SYNTAX SEQUENCE OF Enc1P1295targetLoudnessLevelEntry
    MAX-ACCESS not-accessible
    STATUS     current
    DESCRIPTION
    "
    Name      : Target Loudness Level
    Menu Path : /Audio/AAP 1 Configuration/DTS Neural Loudness Ctrl 2
    Units     : dBEq/LKFS
    Precision : 0
    Low Range : -40
    High Range: 0
    Details   : Specifies the loudness level that will be targeted.

     NOTE: Precision/Units/Ranges represent the state of the
           parameter during the MIB generation, and does not
           neccessary reflect the current state of the parameter
    "
::= { enc1Params 1295 }

enc1P1295targetLoudnessLevelEntry OBJECT-TYPE
    SYNTAX Enc1P1295targetLoudnessLevelEntry
    MAX-ACCESS not-accessible
    STATUS     current
    DESCRIPTION
    "Table Entry for Target Loudness Level"
    INDEX { slotId }
::= { enc1P1295targetLoudnessLevelTable 1 }

Enc1P1295targetLoudnessLevelEntry ::= SEQUENCE {
    enc1P1295targetLoudnessLevelValue    INTEGER
}

enc1P1295targetLoudnessLevelValue OBJECT-TYPE
    SYNTAX     INTEGER
    MAX-ACCESS read-write
    STATUS     current
    DESCRIPTION
    "Specifies the loudness level that will be targeted."
::= { enc1P1295targetLoudnessLevelEntry 1 }

enc1P1296lcratioTable OBJECT-TYPE
    SYNTAX SEQUENCE OF Enc1P1296lcratioEntry
    MAX-ACCESS not-accessible
    STATUS     current
    DESCRIPTION
    "
    Name      : LC Ratio
    Menu Path : /Audio/AAP 1 Configuration/DTS Neural Loudness Ctrl 2
    Units     : 
    Precision : 2
    Low Range : 0
    High Range: 100
    Details   : Controls the amount of gain or attenuation that is applied when loudness differences are measured.

     NOTE: Precision/Units/Ranges represent the state of the
           parameter during the MIB generation, and does not
           neccessary reflect the current state of the parameter
    "
::= { enc1Params 1296 }

enc1P1296lcratioEntry OBJECT-TYPE
    SYNTAX Enc1P1296lcratioEntry
    MAX-ACCESS not-accessible
    STATUS     current
    DESCRIPTION
    "Table Entry for LC Ratio"
    INDEX { slotId }
::= { enc1P1296lcratioTable 1 }

Enc1P1296lcratioEntry ::= SEQUENCE {
    enc1P1296lcratioValue    INTEGER
}

enc1P1296lcratioValue OBJECT-TYPE
    SYNTAX     INTEGER
    MAX-ACCESS read-write
    STATUS     current
    DESCRIPTION
    "Controls the amount of gain or attenuation that is applied when loudness differences are measured."
::= { enc1P1296lcratioEntry 1 }

enc1P1297upperThresholdTable OBJECT-TYPE
    SYNTAX SEQUENCE OF Enc1P1297upperThresholdEntry
    MAX-ACCESS not-accessible
    STATUS     current
    DESCRIPTION
    "
    Name      : Upper Threshold
    Menu Path : /Audio/AAP 1 Configuration/DTS Neural Loudness Ctrl 2
    Units     : dB
    Precision : 0
    Low Range : 0
    High Range: 20
    Details   : Specifies the highest measured loudness of the input that will be permitted before attenuation is applied.

     NOTE: Precision/Units/Ranges represent the state of the
           parameter during the MIB generation, and does not
           neccessary reflect the current state of the parameter
    "
::= { enc1Params 1297 }

enc1P1297upperThresholdEntry OBJECT-TYPE
    SYNTAX Enc1P1297upperThresholdEntry
    MAX-ACCESS not-accessible
    STATUS     current
    DESCRIPTION
    "Table Entry for Upper Threshold"
    INDEX { slotId }
::= { enc1P1297upperThresholdTable 1 }

Enc1P1297upperThresholdEntry ::= SEQUENCE {
    enc1P1297upperThresholdValue    INTEGER
}

enc1P1297upperThresholdValue OBJECT-TYPE
    SYNTAX     INTEGER
    MAX-ACCESS read-write
    STATUS     current
    DESCRIPTION
    "Specifies the highest measured loudness of the input that will be permitted before attenuation is applied."
::= { enc1P1297upperThresholdEntry 1 }

enc1P1298lowerThresholdTable OBJECT-TYPE
    SYNTAX SEQUENCE OF Enc1P1298lowerThresholdEntry
    MAX-ACCESS not-accessible
    STATUS     current
    DESCRIPTION
    "
    Name      : Lower Threshold
    Menu Path : /Audio/AAP 1 Configuration/DTS Neural Loudness Ctrl 2
    Units     : dB
    Precision : 0
    Low Range : -20
    High Range: 0
    Details   : Specifies the lowest measured loudness of the input that will be permitted before gain is applied.

     NOTE: Precision/Units/Ranges represent the state of the
           parameter during the MIB generation, and does not
           neccessary reflect the current state of the parameter
    "
::= { enc1Params 1298 }

enc1P1298lowerThresholdEntry OBJECT-TYPE
    SYNTAX Enc1P1298lowerThresholdEntry
    MAX-ACCESS not-accessible
    STATUS     current
    DESCRIPTION
    "Table Entry for Lower Threshold"
    INDEX { slotId }
::= { enc1P1298lowerThresholdTable 1 }

Enc1P1298lowerThresholdEntry ::= SEQUENCE {
    enc1P1298lowerThresholdValue    INTEGER
}

enc1P1298lowerThresholdValue OBJECT-TYPE
    SYNTAX     INTEGER
    MAX-ACCESS read-write
    STATUS     current
    DESCRIPTION
    "Specifies the lowest measured loudness of the input that will be permitted before gain is applied."
::= { enc1P1298lowerThresholdEntry 1 }

enc1P1299freezeWindowTable OBJECT-TYPE
    SYNTAX SEQUENCE OF Enc1P1299freezeWindowEntry
    MAX-ACCESS not-accessible
    STATUS     current
    DESCRIPTION
    "
    Name      : Freeze Window
    Menu Path : /Audio/AAP 1 Configuration/DTS Neural Loudness Ctrl 2
    Units     : dB
    Precision : 1
    Low Range : 0
    High Range: 100
    Details   : Specifies the size of a window which small loudness differences are allowed without the need to change gain or attenuation.

     NOTE: Precision/Units/Ranges represent the state of the
           parameter during the MIB generation, and does not
           neccessary reflect the current state of the parameter
    "
::= { enc1Params 1299 }

enc1P1299freezeWindowEntry OBJECT-TYPE
    SYNTAX Enc1P1299freezeWindowEntry
    MAX-ACCESS not-accessible
    STATUS     current
    DESCRIPTION
    "Table Entry for Freeze Window"
    INDEX { slotId }
::= { enc1P1299freezeWindowTable 1 }

Enc1P1299freezeWindowEntry ::= SEQUENCE {
    enc1P1299freezeWindowValue    INTEGER
}

enc1P1299freezeWindowValue OBJECT-TYPE
    SYNTAX     INTEGER
    MAX-ACCESS read-write
    STATUS     current
    DESCRIPTION
    "Specifies the size of a window which small loudness differences are allowed without the need to change gain or attenuation."
::= { enc1P1299freezeWindowEntry 1 }

enc1P1300quietThresholdTable OBJECT-TYPE
    SYNTAX SEQUENCE OF Enc1P1300quietThresholdEntry
    MAX-ACCESS not-accessible
    STATUS     current
    DESCRIPTION
    "
    Name      : Quiet Threshold
    Menu Path : /Audio/AAP 1 Configuration/DTS Neural Loudness Ctrl 2
    Units     : dBEq
    Precision : 0
    Low Range : -80
    High Range: -20
    Details   : Controls the noise floor level.

     NOTE: Precision/Units/Ranges represent the state of the
           parameter during the MIB generation, and does not
           neccessary reflect the current state of the parameter
    "
::= { enc1Params 1300 }

enc1P1300quietThresholdEntry OBJECT-TYPE
    SYNTAX Enc1P1300quietThresholdEntry
    MAX-ACCESS not-accessible
    STATUS     current
    DESCRIPTION
    "Table Entry for Quiet Threshold"
    INDEX { slotId }
::= { enc1P1300quietThresholdTable 1 }

Enc1P1300quietThresholdEntry ::= SEQUENCE {
    enc1P1300quietThresholdValue    INTEGER
}

enc1P1300quietThresholdValue OBJECT-TYPE
    SYNTAX     INTEGER
    MAX-ACCESS read-write
    STATUS     current
    DESCRIPTION
    "Controls the noise floor level."
::= { enc1P1300quietThresholdEntry 1 }

enc1P1301attackTimeTable OBJECT-TYPE
    SYNTAX SEQUENCE OF Enc1P1301attackTimeEntry
    MAX-ACCESS not-accessible
    STATUS     current
    DESCRIPTION
    "
    Name      : Attack Time
    Menu Path : /Audio/AAP 1 Configuration/DTS Neural Loudness Ctrl 2
    Units     : ms
    Precision : 0
    Low Range : 5
    High Range: 150
    Details   : Controls how quickly the processing will respond to sharp increases in loudness.

     NOTE: Precision/Units/Ranges represent the state of the
           parameter during the MIB generation, and does not
           neccessary reflect the current state of the parameter
    "
::= { enc1Params 1301 }

enc1P1301attackTimeEntry OBJECT-TYPE
    SYNTAX Enc1P1301attackTimeEntry
    MAX-ACCESS not-accessible
    STATUS     current
    DESCRIPTION
    "Table Entry for Attack Time"
    INDEX { slotId }
::= { enc1P1301attackTimeTable 1 }

Enc1P1301attackTimeEntry ::= SEQUENCE {
    enc1P1301attackTimeValue    INTEGER
}

enc1P1301attackTimeValue OBJECT-TYPE
    SYNTAX     INTEGER
    MAX-ACCESS read-write
    STATUS     current
    DESCRIPTION
    "Controls how quickly the processing will respond to sharp increases in loudness."
::= { enc1P1301attackTimeEntry 1 }

enc1P1302releaseTimeTable OBJECT-TYPE
    SYNTAX SEQUENCE OF Enc1P1302releaseTimeEntry
    MAX-ACCESS not-accessible
    STATUS     current
    DESCRIPTION
    "
    Name      : Release Time
    Menu Path : /Audio/AAP 1 Configuration/DTS Neural Loudness Ctrl 2
    Units     : ms
    Precision : 0
    Low Range : 20
    High Range: 500
    Details   : Controls how quickly the processing will respond to sharp decreases in loudness.

     NOTE: Precision/Units/Ranges represent the state of the
           parameter during the MIB generation, and does not
           neccessary reflect the current state of the parameter
    "
::= { enc1Params 1302 }

enc1P1302releaseTimeEntry OBJECT-TYPE
    SYNTAX Enc1P1302releaseTimeEntry
    MAX-ACCESS not-accessible
    STATUS     current
    DESCRIPTION
    "Table Entry for Release Time"
    INDEX { slotId }
::= { enc1P1302releaseTimeTable 1 }

Enc1P1302releaseTimeEntry ::= SEQUENCE {
    enc1P1302releaseTimeValue    INTEGER
}

enc1P1302releaseTimeValue OBJECT-TYPE
    SYNTAX     INTEGER
    MAX-ACCESS read-write
    STATUS     current
    DESCRIPTION
    "Controls how quickly the processing will respond to sharp decreases in loudness."
::= { enc1P1302releaseTimeEntry 1 }

enc1P1303compressorThresholdTable OBJECT-TYPE
    SYNTAX SEQUENCE OF Enc1P1303compressorThresholdEntry
    MAX-ACCESS not-accessible
    STATUS     current
    DESCRIPTION
    "
    Name      : Compressor Threshold
    Menu Path : /Audio/AAP 1 Configuration/DTS Neural Loudness Ctrl 2
    Units     : dB
    Precision : 0
    Low Range : 0
    High Range: 16
    Details   : Loudness Control Compressor Threshold

     NOTE: Precision/Units/Ranges represent the state of the
           parameter during the MIB generation, and does not
           neccessary reflect the current state of the parameter
    "
::= { enc1Params 1303 }

enc1P1303compressorThresholdEntry OBJECT-TYPE
    SYNTAX Enc1P1303compressorThresholdEntry
    MAX-ACCESS not-accessible
    STATUS     current
    DESCRIPTION
    "Table Entry for Compressor Threshold"
    INDEX { slotId }
::= { enc1P1303compressorThresholdTable 1 }

Enc1P1303compressorThresholdEntry ::= SEQUENCE {
    enc1P1303compressorThresholdValue    INTEGER
}

enc1P1303compressorThresholdValue OBJECT-TYPE
    SYNTAX     INTEGER
    MAX-ACCESS read-write
    STATUS     current
    DESCRIPTION
    "Loudness Control Compressor Threshold"
::= { enc1P1303compressorThresholdEntry 1 }

enc1P1304compressorRatioTable OBJECT-TYPE
    SYNTAX SEQUENCE OF Enc1P1304compressorRatioEntry
    MAX-ACCESS not-accessible
    STATUS     current
    DESCRIPTION
    "
    Name      : Compressor Ratio
    Menu Path : /Audio/AAP 1 Configuration/DTS Neural Loudness Ctrl 2
    Units     : 
    Precision : 2
    Low Range : 0
    High Range: 100
    Details   : Controls the amount of attenuation applied when short-term peaks exceed the compressor threshold.

     NOTE: Precision/Units/Ranges represent the state of the
           parameter during the MIB generation, and does not
           neccessary reflect the current state of the parameter
    "
::= { enc1Params 1304 }

enc1P1304compressorRatioEntry OBJECT-TYPE
    SYNTAX Enc1P1304compressorRatioEntry
    MAX-ACCESS not-accessible
    STATUS     current
    DESCRIPTION
    "Table Entry for Compressor Ratio"
    INDEX { slotId }
::= { enc1P1304compressorRatioTable 1 }

Enc1P1304compressorRatioEntry ::= SEQUENCE {
    enc1P1304compressorRatioValue    INTEGER
}

enc1P1304compressorRatioValue OBJECT-TYPE
    SYNTAX     INTEGER
    MAX-ACCESS read-write
    STATUS     current
    DESCRIPTION
    "Controls the amount of attenuation applied when short-term peaks exceed the compressor threshold."
::= { enc1P1304compressorRatioEntry 1 }

enc1P1305loudnessShapingTable OBJECT-TYPE
    SYNTAX SEQUENCE OF Enc1P1305loudnessShapingEntry
    MAX-ACCESS not-accessible
    STATUS     current
    DESCRIPTION
    "
    Name      : Loudness Shaping
    Menu Path : /Audio/AAP 1 Configuration/DTS Neural Loudness Ctrl 2
    Units     : 
    Precision : 1
    Low Range : 0
    High Range: 10
    Details   : Specifies the amount of loudness shaping desired.

     NOTE: Precision/Units/Ranges represent the state of the
           parameter during the MIB generation, and does not
           neccessary reflect the current state of the parameter
    "
::= { enc1Params 1305 }

enc1P1305loudnessShapingEntry OBJECT-TYPE
    SYNTAX Enc1P1305loudnessShapingEntry
    MAX-ACCESS not-accessible
    STATUS     current
    DESCRIPTION
    "Table Entry for Loudness Shaping"
    INDEX { slotId }
::= { enc1P1305loudnessShapingTable 1 }

Enc1P1305loudnessShapingEntry ::= SEQUENCE {
    enc1P1305loudnessShapingValue    INTEGER
}

enc1P1305loudnessShapingValue OBJECT-TYPE
    SYNTAX     INTEGER
    MAX-ACCESS read-write
    STATUS     current
    DESCRIPTION
    "Specifies the amount of loudness shaping desired."
::= { enc1P1305loudnessShapingEntry 1 }

enc1P1306finalLimiterCeilingTable OBJECT-TYPE
    SYNTAX SEQUENCE OF Enc1P1306finalLimiterCeilingEntry
    MAX-ACCESS not-accessible
    STATUS     current
    DESCRIPTION
    "
    Name      : Final Limiter Ceiling
    Menu Path : /Audio/AAP 1 Configuration/DTS Neural Loudness Ctrl 2
    Units     : dBFS
    Precision : 0
    Low Range : -20
    High Range: 0
    Details   : Specifies the threshold above which final limiting will be applied.

     NOTE: Precision/Units/Ranges represent the state of the
           parameter during the MIB generation, and does not
           neccessary reflect the current state of the parameter
    "
::= { enc1Params 1306 }

enc1P1306finalLimiterCeilingEntry OBJECT-TYPE
    SYNTAX Enc1P1306finalLimiterCeilingEntry
    MAX-ACCESS not-accessible
    STATUS     current
    DESCRIPTION
    "Table Entry for Final Limiter Ceiling"
    INDEX { slotId }
::= { enc1P1306finalLimiterCeilingTable 1 }

Enc1P1306finalLimiterCeilingEntry ::= SEQUENCE {
    enc1P1306finalLimiterCeilingValue    INTEGER
}

enc1P1306finalLimiterCeilingValue OBJECT-TYPE
    SYNTAX     INTEGER
    MAX-ACCESS read-write
    STATUS     current
    DESCRIPTION
    "Specifies the threshold above which final limiting will be applied."
::= { enc1P1306finalLimiterCeilingEntry 1 }

enc1P1307runFinalLimitersTable OBJECT-TYPE
    SYNTAX SEQUENCE OF Enc1P1307runFinalLimitersEntry
    MAX-ACCESS not-accessible
    STATUS     current
    DESCRIPTION
    "
    Name      : Run Final Limiters
    Menu Path : /Audio/AAP 1 Configuration/DTS Neural Loudness Ctrl 2
    Details   : Enables final limiters to be applied according to the value of the Final Limiter Ceiling.
    "
::= { enc1Params 1307 }

enc1P1307runFinalLimitersEntry OBJECT-TYPE
    SYNTAX Enc1P1307runFinalLimitersEntry
    MAX-ACCESS not-accessible
    STATUS     current
    DESCRIPTION
    "Table Entry for Run Final Limiters"
    INDEX { slotId }
::= { enc1P1307runFinalLimitersTable 1 }

Enc1P1307runFinalLimitersEntry ::= SEQUENCE {
    enc1P1307runFinalLimitersValue    Enc1E152enumObj
}

enc1P1307runFinalLimitersValue OBJECT-TYPE
    SYNTAX     Enc1E152enumObj
    MAX-ACCESS read-write
    STATUS     current
    DESCRIPTION
    "Enables final limiters to be applied according to the value of the Final Limiter Ceiling."
::= { enc1P1307runFinalLimitersEntry 1 }

enc1P1308meteringTable OBJECT-TYPE
    SYNTAX SEQUENCE OF Enc1P1308meteringEntry
    MAX-ACCESS not-accessible
    STATUS     current
    DESCRIPTION
    "
    Name      : Metering
    Menu Path : /Audio/AAP 1 Configuration/DTS Neural Loudness Ctrl 2
    Details   : Activates the real-time meters (below).
    "
::= { enc1Params 1308 }

enc1P1308meteringEntry OBJECT-TYPE
    SYNTAX Enc1P1308meteringEntry
    MAX-ACCESS not-accessible
    STATUS     current
    DESCRIPTION
    "Table Entry for Metering"
    INDEX { slotId }
::= { enc1P1308meteringTable 1 }

Enc1P1308meteringEntry ::= SEQUENCE {
    enc1P1308meteringValue    Enc1E154enumObj
}

enc1P1308meteringValue OBJECT-TYPE
    SYNTAX     Enc1E154enumObj
    MAX-ACCESS read-write
    STATUS     current
    DESCRIPTION
    "Activates the real-time meters (below)."
::= { enc1P1308meteringEntry 1 }

enc1P1309currentInputLoudnessTable OBJECT-TYPE
    SYNTAX SEQUENCE OF Enc1P1309currentInputLoudnessEntry
    MAX-ACCESS not-accessible
    STATUS     current
    DESCRIPTION
    "
    Name      : Current Input Loudness
    Menu Path : /Audio/AAP 1 Configuration/DTS Neural Loudness Ctrl 2
    Units     : dBEq
    Precision : 0
    Low Range : -60
    High Range: 20
    Details   : Reports the smoothed input loudness measurement.

     NOTE: Precision/Units/Ranges represent the state of the
           parameter during the MIB generation, and does not
           neccessary reflect the current state of the parameter
    "
::= { enc1Params 1309 }

enc1P1309currentInputLoudnessEntry OBJECT-TYPE
    SYNTAX Enc1P1309currentInputLoudnessEntry
    MAX-ACCESS not-accessible
    STATUS     current
    DESCRIPTION
    "Table Entry for Current Input Loudness"
    INDEX { slotId }
::= { enc1P1309currentInputLoudnessTable 1 }

Enc1P1309currentInputLoudnessEntry ::= SEQUENCE {
    enc1P1309currentInputLoudnessValue    INTEGER
}

enc1P1309currentInputLoudnessValue OBJECT-TYPE
    SYNTAX     INTEGER
    MAX-ACCESS read-only
    STATUS     current
    DESCRIPTION
    "Reports the smoothed input loudness measurement."
::= { enc1P1309currentInputLoudnessEntry 1 }

enc1P1310currentInputPeakTable OBJECT-TYPE
    SYNTAX SEQUENCE OF Enc1P1310currentInputPeakEntry
    MAX-ACCESS not-accessible
    STATUS     current
    DESCRIPTION
    "
    Name      : Current Input Peak
    Menu Path : /Audio/AAP 1 Configuration/DTS Neural Loudness Ctrl 2
    Units     : dBFS
    Precision : 0
    Low Range : -60
    High Range: 20
    Details   : Reports the input peak measurement.

     NOTE: Precision/Units/Ranges represent the state of the
           parameter during the MIB generation, and does not
           neccessary reflect the current state of the parameter
    "
::= { enc1Params 1310 }

enc1P1310currentInputPeakEntry OBJECT-TYPE
    SYNTAX Enc1P1310currentInputPeakEntry
    MAX-ACCESS not-accessible
    STATUS     current
    DESCRIPTION
    "Table Entry for Current Input Peak"
    INDEX { slotId }
::= { enc1P1310currentInputPeakTable 1 }

Enc1P1310currentInputPeakEntry ::= SEQUENCE {
    enc1P1310currentInputPeakValue    INTEGER
}

enc1P1310currentInputPeakValue OBJECT-TYPE
    SYNTAX     INTEGER
    MAX-ACCESS read-only
    STATUS     current
    DESCRIPTION
    "Reports the input peak measurement."
::= { enc1P1310currentInputPeakEntry 1 }

enc1P1311currentOutputLoudnessTable OBJECT-TYPE
    SYNTAX SEQUENCE OF Enc1P1311currentOutputLoudnessEntry
    MAX-ACCESS not-accessible
    STATUS     current
    DESCRIPTION
    "
    Name      : Current Output Loudness
    Menu Path : /Audio/AAP 1 Configuration/DTS Neural Loudness Ctrl 2
    Units     : dBEq
    Precision : 0
    Low Range : -60
    High Range: 20
    Details   : Reports the smoothed output loudness measurement.

     NOTE: Precision/Units/Ranges represent the state of the
           parameter during the MIB generation, and does not
           neccessary reflect the current state of the parameter
    "
::= { enc1Params 1311 }

enc1P1311currentOutputLoudnessEntry OBJECT-TYPE
    SYNTAX Enc1P1311currentOutputLoudnessEntry
    MAX-ACCESS not-accessible
    STATUS     current
    DESCRIPTION
    "Table Entry for Current Output Loudness"
    INDEX { slotId }
::= { enc1P1311currentOutputLoudnessTable 1 }

Enc1P1311currentOutputLoudnessEntry ::= SEQUENCE {
    enc1P1311currentOutputLoudnessValue    INTEGER
}

enc1P1311currentOutputLoudnessValue OBJECT-TYPE
    SYNTAX     INTEGER
    MAX-ACCESS read-only
    STATUS     current
    DESCRIPTION
    "Reports the smoothed output loudness measurement."
::= { enc1P1311currentOutputLoudnessEntry 1 }

enc1P1312currentOutputPeakTable OBJECT-TYPE
    SYNTAX SEQUENCE OF Enc1P1312currentOutputPeakEntry
    MAX-ACCESS not-accessible
    STATUS     current
    DESCRIPTION
    "
    Name      : Current Output Peak
    Menu Path : /Audio/AAP 1 Configuration/DTS Neural Loudness Ctrl 2
    Units     : dBFS
    Precision : 0
    Low Range : -60
    High Range: 20
    Details   : Reports the output peak measurement.

     NOTE: Precision/Units/Ranges represent the state of the
           parameter during the MIB generation, and does not
           neccessary reflect the current state of the parameter
    "
::= { enc1Params 1312 }

enc1P1312currentOutputPeakEntry OBJECT-TYPE
    SYNTAX Enc1P1312currentOutputPeakEntry
    MAX-ACCESS not-accessible
    STATUS     current
    DESCRIPTION
    "Table Entry for Current Output Peak"
    INDEX { slotId }
::= { enc1P1312currentOutputPeakTable 1 }

Enc1P1312currentOutputPeakEntry ::= SEQUENCE {
    enc1P1312currentOutputPeakValue    INTEGER
}

enc1P1312currentOutputPeakValue OBJECT-TYPE
    SYNTAX     INTEGER
    MAX-ACCESS read-only
    STATUS     current
    DESCRIPTION
    "Reports the output peak measurement."
::= { enc1P1312currentOutputPeakEntry 1 }

enc1P1313currentCorrectionTable OBJECT-TYPE
    SYNTAX SEQUENCE OF Enc1P1313currentCorrectionEntry
    MAX-ACCESS not-accessible
    STATUS     current
    DESCRIPTION
    "
    Name      : Current Correction
    Menu Path : /Audio/AAP 1 Configuration/DTS Neural Loudness Ctrl 2
    Units     : dB
    Precision : 0
    Low Range : -60
    High Range: 60
    Details   : Reports the amount of correction being applied.

     NOTE: Precision/Units/Ranges represent the state of the
           parameter during the MIB generation, and does not
           neccessary reflect the current state of the parameter
    "
::= { enc1Params 1313 }

enc1P1313currentCorrectionEntry OBJECT-TYPE
    SYNTAX Enc1P1313currentCorrectionEntry
    MAX-ACCESS not-accessible
    STATUS     current
    DESCRIPTION
    "Table Entry for Current Correction"
    INDEX { slotId }
::= { enc1P1313currentCorrectionTable 1 }

Enc1P1313currentCorrectionEntry ::= SEQUENCE {
    enc1P1313currentCorrectionValue    INTEGER
}

enc1P1313currentCorrectionValue OBJECT-TYPE
    SYNTAX     INTEGER
    MAX-ACCESS read-only
    STATUS     current
    DESCRIPTION
    "Reports the amount of correction being applied."
::= { enc1P1313currentCorrectionEntry 1 }

enc1P1314currentCompressionTable OBJECT-TYPE
    SYNTAX SEQUENCE OF Enc1P1314currentCompressionEntry
    MAX-ACCESS not-accessible
    STATUS     current
    DESCRIPTION
    "
    Name      : Current Compression
    Menu Path : /Audio/AAP 1 Configuration/DTS Neural Loudness Ctrl 2
    Units     : dB
    Precision : 0
    Low Range : -60
    High Range: 60
    Details   : Reports the amount of compression being applied.

     NOTE: Precision/Units/Ranges represent the state of the
           parameter during the MIB generation, and does not
           neccessary reflect the current state of the parameter
    "
::= { enc1Params 1314 }

enc1P1314currentCompressionEntry OBJECT-TYPE
    SYNTAX Enc1P1314currentCompressionEntry
    MAX-ACCESS not-accessible
    STATUS     current
    DESCRIPTION
    "Table Entry for Current Compression"
    INDEX { slotId }
::= { enc1P1314currentCompressionTable 1 }

Enc1P1314currentCompressionEntry ::= SEQUENCE {
    enc1P1314currentCompressionValue    INTEGER
}

enc1P1314currentCompressionValue OBJECT-TYPE
    SYNTAX     INTEGER
    MAX-ACCESS read-only
    STATUS     current
    DESCRIPTION
    "Reports the amount of compression being applied."
::= { enc1P1314currentCompressionEntry 1 }

enc1P1315loudnessControlFunctionTable OBJECT-TYPE
    SYNTAX SEQUENCE OF Enc1P1315loudnessControlFunctionEntry
    MAX-ACCESS not-accessible
    STATUS     current
    DESCRIPTION
    "
    Name      : Loudness Control Function
    Menu Path : /Audio/AAP 1 Configuration/DTS Neural Loudness Ctrl 3
    Details   : Bypasses the loudness control circuit.
    "
::= { enc1Params 1315 }

enc1P1315loudnessControlFunctionEntry OBJECT-TYPE
    SYNTAX Enc1P1315loudnessControlFunctionEntry
    MAX-ACCESS not-accessible
    STATUS     current
    DESCRIPTION
    "Table Entry for Loudness Control Function"
    INDEX { slotId }
::= { enc1P1315loudnessControlFunctionTable 1 }

Enc1P1315loudnessControlFunctionEntry ::= SEQUENCE {
    enc1P1315loudnessControlFunctionValue    Enc1E174enumObj
}

enc1P1315loudnessControlFunctionValue OBJECT-TYPE
    SYNTAX     Enc1E174enumObj
    MAX-ACCESS read-write
    STATUS     current
    DESCRIPTION
    "Bypasses the loudness control circuit."
::= { enc1P1315loudnessControlFunctionEntry 1 }

enc1P1316loudnessControlStatusTable OBJECT-TYPE
    SYNTAX SEQUENCE OF Enc1P1316loudnessControlStatusEntry
    MAX-ACCESS not-accessible
    STATUS     current
    DESCRIPTION
    "
    Name      : Loudness Control Status
    Menu Path : /Audio/AAP 1 Configuration/DTS Neural Loudness Ctrl 3
    Details   : Indicates the state of loudness control processing.
    "
::= { enc1Params 1316 }

enc1P1316loudnessControlStatusEntry OBJECT-TYPE
    SYNTAX Enc1P1316loudnessControlStatusEntry
    MAX-ACCESS not-accessible
    STATUS     current
    DESCRIPTION
    "Table Entry for Loudness Control Status"
    INDEX { slotId }
::= { enc1P1316loudnessControlStatusTable 1 }

Enc1P1316loudnessControlStatusEntry ::= SEQUENCE {
    enc1P1316loudnessControlStatusValue    Enc1E172enumObj
}

enc1P1316loudnessControlStatusValue OBJECT-TYPE
    SYNTAX     Enc1E172enumObj
    MAX-ACCESS read-only
    STATUS     current
    DESCRIPTION
    "Indicates the state of loudness control processing."
::= { enc1P1316loudnessControlStatusEntry 1 }

enc1P1317loudnessMeasurementTypeTable OBJECT-TYPE
    SYNTAX SEQUENCE OF Enc1P1317loudnessMeasurementTypeEntry
    MAX-ACCESS not-accessible
    STATUS     current
    DESCRIPTION
    "
    Name      : Loudness Measurement Type
    Menu Path : /Audio/AAP 1 Configuration/DTS Neural Loudness Ctrl 3
    Details   : Specifies the type of loudness measurement to make prior to performing loudness control.
    "
::= { enc1Params 1317 }

enc1P1317loudnessMeasurementTypeEntry OBJECT-TYPE
    SYNTAX Enc1P1317loudnessMeasurementTypeEntry
    MAX-ACCESS not-accessible
    STATUS     current
    DESCRIPTION
    "Table Entry for Loudness Measurement Type"
    INDEX { slotId }
::= { enc1P1317loudnessMeasurementTypeTable 1 }

Enc1P1317loudnessMeasurementTypeEntry ::= SEQUENCE {
    enc1P1317loudnessMeasurementTypeValue    Enc1E175enumObj
}

enc1P1317loudnessMeasurementTypeValue OBJECT-TYPE
    SYNTAX     Enc1E175enumObj
    MAX-ACCESS read-write
    STATUS     current
    DESCRIPTION
    "Specifies the type of loudness measurement to make prior to performing loudness control."
::= { enc1P1317loudnessMeasurementTypeEntry 1 }

enc1P1318targetLoudnessLevelTable OBJECT-TYPE
    SYNTAX SEQUENCE OF Enc1P1318targetLoudnessLevelEntry
    MAX-ACCESS not-accessible
    STATUS     current
    DESCRIPTION
    "
    Name      : Target Loudness Level
    Menu Path : /Audio/AAP 1 Configuration/DTS Neural Loudness Ctrl 3
    Units     : dBEq/LKFS
    Precision : 0
    Low Range : -40
    High Range: 0
    Details   : Specifies the loudness level that will be targeted.

     NOTE: Precision/Units/Ranges represent the state of the
           parameter during the MIB generation, and does not
           neccessary reflect the current state of the parameter
    "
::= { enc1Params 1318 }

enc1P1318targetLoudnessLevelEntry OBJECT-TYPE
    SYNTAX Enc1P1318targetLoudnessLevelEntry
    MAX-ACCESS not-accessible
    STATUS     current
    DESCRIPTION
    "Table Entry for Target Loudness Level"
    INDEX { slotId }
::= { enc1P1318targetLoudnessLevelTable 1 }

Enc1P1318targetLoudnessLevelEntry ::= SEQUENCE {
    enc1P1318targetLoudnessLevelValue    INTEGER
}

enc1P1318targetLoudnessLevelValue OBJECT-TYPE
    SYNTAX     INTEGER
    MAX-ACCESS read-write
    STATUS     current
    DESCRIPTION
    "Specifies the loudness level that will be targeted."
::= { enc1P1318targetLoudnessLevelEntry 1 }

enc1P1319lcratioTable OBJECT-TYPE
    SYNTAX SEQUENCE OF Enc1P1319lcratioEntry
    MAX-ACCESS not-accessible
    STATUS     current
    DESCRIPTION
    "
    Name      : LC Ratio
    Menu Path : /Audio/AAP 1 Configuration/DTS Neural Loudness Ctrl 3
    Units     : 
    Precision : 2
    Low Range : 0
    High Range: 100
    Details   : Controls the amount of gain or attenuation that is applied when loudness differences are measured.

     NOTE: Precision/Units/Ranges represent the state of the
           parameter during the MIB generation, and does not
           neccessary reflect the current state of the parameter
    "
::= { enc1Params 1319 }

enc1P1319lcratioEntry OBJECT-TYPE
    SYNTAX Enc1P1319lcratioEntry
    MAX-ACCESS not-accessible
    STATUS     current
    DESCRIPTION
    "Table Entry for LC Ratio"
    INDEX { slotId }
::= { enc1P1319lcratioTable 1 }

Enc1P1319lcratioEntry ::= SEQUENCE {
    enc1P1319lcratioValue    INTEGER
}

enc1P1319lcratioValue OBJECT-TYPE
    SYNTAX     INTEGER
    MAX-ACCESS read-write
    STATUS     current
    DESCRIPTION
    "Controls the amount of gain or attenuation that is applied when loudness differences are measured."
::= { enc1P1319lcratioEntry 1 }

enc1P1320upperThresholdTable OBJECT-TYPE
    SYNTAX SEQUENCE OF Enc1P1320upperThresholdEntry
    MAX-ACCESS not-accessible
    STATUS     current
    DESCRIPTION
    "
    Name      : Upper Threshold
    Menu Path : /Audio/AAP 1 Configuration/DTS Neural Loudness Ctrl 3
    Units     : dB
    Precision : 0
    Low Range : 0
    High Range: 20
    Details   : Specifies the highest measured loudness of the input that will be permitted before attenuation is applied.

     NOTE: Precision/Units/Ranges represent the state of the
           parameter during the MIB generation, and does not
           neccessary reflect the current state of the parameter
    "
::= { enc1Params 1320 }

enc1P1320upperThresholdEntry OBJECT-TYPE
    SYNTAX Enc1P1320upperThresholdEntry
    MAX-ACCESS not-accessible
    STATUS     current
    DESCRIPTION
    "Table Entry for Upper Threshold"
    INDEX { slotId }
::= { enc1P1320upperThresholdTable 1 }

Enc1P1320upperThresholdEntry ::= SEQUENCE {
    enc1P1320upperThresholdValue    INTEGER
}

enc1P1320upperThresholdValue OBJECT-TYPE
    SYNTAX     INTEGER
    MAX-ACCESS read-write
    STATUS     current
    DESCRIPTION
    "Specifies the highest measured loudness of the input that will be permitted before attenuation is applied."
::= { enc1P1320upperThresholdEntry 1 }

enc1P1321lowerThresholdTable OBJECT-TYPE
    SYNTAX SEQUENCE OF Enc1P1321lowerThresholdEntry
    MAX-ACCESS not-accessible
    STATUS     current
    DESCRIPTION
    "
    Name      : Lower Threshold
    Menu Path : /Audio/AAP 1 Configuration/DTS Neural Loudness Ctrl 3
    Units     : dB
    Precision : 0
    Low Range : -20
    High Range: 0
    Details   : Specifies the lowest measured loudness of the input that will be permitted before gain is applied.

     NOTE: Precision/Units/Ranges represent the state of the
           parameter during the MIB generation, and does not
           neccessary reflect the current state of the parameter
    "
::= { enc1Params 1321 }

enc1P1321lowerThresholdEntry OBJECT-TYPE
    SYNTAX Enc1P1321lowerThresholdEntry
    MAX-ACCESS not-accessible
    STATUS     current
    DESCRIPTION
    "Table Entry for Lower Threshold"
    INDEX { slotId }
::= { enc1P1321lowerThresholdTable 1 }

Enc1P1321lowerThresholdEntry ::= SEQUENCE {
    enc1P1321lowerThresholdValue    INTEGER
}

enc1P1321lowerThresholdValue OBJECT-TYPE
    SYNTAX     INTEGER
    MAX-ACCESS read-write
    STATUS     current
    DESCRIPTION
    "Specifies the lowest measured loudness of the input that will be permitted before gain is applied."
::= { enc1P1321lowerThresholdEntry 1 }

enc1P1322freezeWindowTable OBJECT-TYPE
    SYNTAX SEQUENCE OF Enc1P1322freezeWindowEntry
    MAX-ACCESS not-accessible
    STATUS     current
    DESCRIPTION
    "
    Name      : Freeze Window
    Menu Path : /Audio/AAP 1 Configuration/DTS Neural Loudness Ctrl 3
    Units     : dB
    Precision : 1
    Low Range : 0
    High Range: 100
    Details   : Specifies the size of a window which small loudness differences are allowed without the need to change gain or attenuation.

     NOTE: Precision/Units/Ranges represent the state of the
           parameter during the MIB generation, and does not
           neccessary reflect the current state of the parameter
    "
::= { enc1Params 1322 }

enc1P1322freezeWindowEntry OBJECT-TYPE
    SYNTAX Enc1P1322freezeWindowEntry
    MAX-ACCESS not-accessible
    STATUS     current
    DESCRIPTION
    "Table Entry for Freeze Window"
    INDEX { slotId }
::= { enc1P1322freezeWindowTable 1 }

Enc1P1322freezeWindowEntry ::= SEQUENCE {
    enc1P1322freezeWindowValue    INTEGER
}

enc1P1322freezeWindowValue OBJECT-TYPE
    SYNTAX     INTEGER
    MAX-ACCESS read-write
    STATUS     current
    DESCRIPTION
    "Specifies the size of a window which small loudness differences are allowed without the need to change gain or attenuation."
::= { enc1P1322freezeWindowEntry 1 }

enc1P1323quietThresholdTable OBJECT-TYPE
    SYNTAX SEQUENCE OF Enc1P1323quietThresholdEntry
    MAX-ACCESS not-accessible
    STATUS     current
    DESCRIPTION
    "
    Name      : Quiet Threshold
    Menu Path : /Audio/AAP 1 Configuration/DTS Neural Loudness Ctrl 3
    Units     : dBEq
    Precision : 0
    Low Range : -80
    High Range: -20
    Details   : Controls the noise floor level.

     NOTE: Precision/Units/Ranges represent the state of the
           parameter during the MIB generation, and does not
           neccessary reflect the current state of the parameter
    "
::= { enc1Params 1323 }

enc1P1323quietThresholdEntry OBJECT-TYPE
    SYNTAX Enc1P1323quietThresholdEntry
    MAX-ACCESS not-accessible
    STATUS     current
    DESCRIPTION
    "Table Entry for Quiet Threshold"
    INDEX { slotId }
::= { enc1P1323quietThresholdTable 1 }

Enc1P1323quietThresholdEntry ::= SEQUENCE {
    enc1P1323quietThresholdValue    INTEGER
}

enc1P1323quietThresholdValue OBJECT-TYPE
    SYNTAX     INTEGER
    MAX-ACCESS read-write
    STATUS     current
    DESCRIPTION
    "Controls the noise floor level."
::= { enc1P1323quietThresholdEntry 1 }

enc1P1324attackTimeTable OBJECT-TYPE
    SYNTAX SEQUENCE OF Enc1P1324attackTimeEntry
    MAX-ACCESS not-accessible
    STATUS     current
    DESCRIPTION
    "
    Name      : Attack Time
    Menu Path : /Audio/AAP 1 Configuration/DTS Neural Loudness Ctrl 3
    Units     : ms
    Precision : 0
    Low Range : 5
    High Range: 150
    Details   : Controls how quickly the processing will respond to sharp increases in loudness.

     NOTE: Precision/Units/Ranges represent the state of the
           parameter during the MIB generation, and does not
           neccessary reflect the current state of the parameter
    "
::= { enc1Params 1324 }

enc1P1324attackTimeEntry OBJECT-TYPE
    SYNTAX Enc1P1324attackTimeEntry
    MAX-ACCESS not-accessible
    STATUS     current
    DESCRIPTION
    "Table Entry for Attack Time"
    INDEX { slotId }
::= { enc1P1324attackTimeTable 1 }

Enc1P1324attackTimeEntry ::= SEQUENCE {
    enc1P1324attackTimeValue    INTEGER
}

enc1P1324attackTimeValue OBJECT-TYPE
    SYNTAX     INTEGER
    MAX-ACCESS read-write
    STATUS     current
    DESCRIPTION
    "Controls how quickly the processing will respond to sharp increases in loudness."
::= { enc1P1324attackTimeEntry 1 }

enc1P1325releaseTimeTable OBJECT-TYPE
    SYNTAX SEQUENCE OF Enc1P1325releaseTimeEntry
    MAX-ACCESS not-accessible
    STATUS     current
    DESCRIPTION
    "
    Name      : Release Time
    Menu Path : /Audio/AAP 1 Configuration/DTS Neural Loudness Ctrl 3
    Units     : ms
    Precision : 0
    Low Range : 20
    High Range: 500
    Details   : Controls how quickly the processing will respond to sharp decreases in loudness.

     NOTE: Precision/Units/Ranges represent the state of the
           parameter during the MIB generation, and does not
           neccessary reflect the current state of the parameter
    "
::= { enc1Params 1325 }

enc1P1325releaseTimeEntry OBJECT-TYPE
    SYNTAX Enc1P1325releaseTimeEntry
    MAX-ACCESS not-accessible
    STATUS     current
    DESCRIPTION
    "Table Entry for Release Time"
    INDEX { slotId }
::= { enc1P1325releaseTimeTable 1 }

Enc1P1325releaseTimeEntry ::= SEQUENCE {
    enc1P1325releaseTimeValue    INTEGER
}

enc1P1325releaseTimeValue OBJECT-TYPE
    SYNTAX     INTEGER
    MAX-ACCESS read-write
    STATUS     current
    DESCRIPTION
    "Controls how quickly the processing will respond to sharp decreases in loudness."
::= { enc1P1325releaseTimeEntry 1 }

enc1P1326compressorThresholdTable OBJECT-TYPE
    SYNTAX SEQUENCE OF Enc1P1326compressorThresholdEntry
    MAX-ACCESS not-accessible
    STATUS     current
    DESCRIPTION
    "
    Name      : Compressor Threshold
    Menu Path : /Audio/AAP 1 Configuration/DTS Neural Loudness Ctrl 3
    Units     : dB
    Precision : 0
    Low Range : 0
    High Range: 16
    Details   : Loudness Control Compressor Threshold

     NOTE: Precision/Units/Ranges represent the state of the
           parameter during the MIB generation, and does not
           neccessary reflect the current state of the parameter
    "
::= { enc1Params 1326 }

enc1P1326compressorThresholdEntry OBJECT-TYPE
    SYNTAX Enc1P1326compressorThresholdEntry
    MAX-ACCESS not-accessible
    STATUS     current
    DESCRIPTION
    "Table Entry for Compressor Threshold"
    INDEX { slotId }
::= { enc1P1326compressorThresholdTable 1 }

Enc1P1326compressorThresholdEntry ::= SEQUENCE {
    enc1P1326compressorThresholdValue    INTEGER
}

enc1P1326compressorThresholdValue OBJECT-TYPE
    SYNTAX     INTEGER
    MAX-ACCESS read-write
    STATUS     current
    DESCRIPTION
    "Loudness Control Compressor Threshold"
::= { enc1P1326compressorThresholdEntry 1 }

enc1P1327compressorRatioTable OBJECT-TYPE
    SYNTAX SEQUENCE OF Enc1P1327compressorRatioEntry
    MAX-ACCESS not-accessible
    STATUS     current
    DESCRIPTION
    "
    Name      : Compressor Ratio
    Menu Path : /Audio/AAP 1 Configuration/DTS Neural Loudness Ctrl 3
    Units     : 
    Precision : 2
    Low Range : 0
    High Range: 100
    Details   : Controls the amount of attenuation applied when short-term peaks exceed the compressor threshold.

     NOTE: Precision/Units/Ranges represent the state of the
           parameter during the MIB generation, and does not
           neccessary reflect the current state of the parameter
    "
::= { enc1Params 1327 }

enc1P1327compressorRatioEntry OBJECT-TYPE
    SYNTAX Enc1P1327compressorRatioEntry
    MAX-ACCESS not-accessible
    STATUS     current
    DESCRIPTION
    "Table Entry for Compressor Ratio"
    INDEX { slotId }
::= { enc1P1327compressorRatioTable 1 }

Enc1P1327compressorRatioEntry ::= SEQUENCE {
    enc1P1327compressorRatioValue    INTEGER
}

enc1P1327compressorRatioValue OBJECT-TYPE
    SYNTAX     INTEGER
    MAX-ACCESS read-write
    STATUS     current
    DESCRIPTION
    "Controls the amount of attenuation applied when short-term peaks exceed the compressor threshold."
::= { enc1P1327compressorRatioEntry 1 }

enc1P1328loudnessShapingTable OBJECT-TYPE
    SYNTAX SEQUENCE OF Enc1P1328loudnessShapingEntry
    MAX-ACCESS not-accessible
    STATUS     current
    DESCRIPTION
    "
    Name      : Loudness Shaping
    Menu Path : /Audio/AAP 1 Configuration/DTS Neural Loudness Ctrl 3
    Units     : 
    Precision : 1
    Low Range : 0
    High Range: 10
    Details   : Specifies the amount of loudness shaping desired.

     NOTE: Precision/Units/Ranges represent the state of the
           parameter during the MIB generation, and does not
           neccessary reflect the current state of the parameter
    "
::= { enc1Params 1328 }

enc1P1328loudnessShapingEntry OBJECT-TYPE
    SYNTAX Enc1P1328loudnessShapingEntry
    MAX-ACCESS not-accessible
    STATUS     current
    DESCRIPTION
    "Table Entry for Loudness Shaping"
    INDEX { slotId }
::= { enc1P1328loudnessShapingTable 1 }

Enc1P1328loudnessShapingEntry ::= SEQUENCE {
    enc1P1328loudnessShapingValue    INTEGER
}

enc1P1328loudnessShapingValue OBJECT-TYPE
    SYNTAX     INTEGER
    MAX-ACCESS read-write
    STATUS     current
    DESCRIPTION
    "Specifies the amount of loudness shaping desired."
::= { enc1P1328loudnessShapingEntry 1 }

enc1P1329finalLimiterCeilingTable OBJECT-TYPE
    SYNTAX SEQUENCE OF Enc1P1329finalLimiterCeilingEntry
    MAX-ACCESS not-accessible
    STATUS     current
    DESCRIPTION
    "
    Name      : Final Limiter Ceiling
    Menu Path : /Audio/AAP 1 Configuration/DTS Neural Loudness Ctrl 3
    Units     : dBFS
    Precision : 0
    Low Range : -20
    High Range: 0
    Details   : Specifies the threshold above which final limiting will be applied.

     NOTE: Precision/Units/Ranges represent the state of the
           parameter during the MIB generation, and does not
           neccessary reflect the current state of the parameter
    "
::= { enc1Params 1329 }

enc1P1329finalLimiterCeilingEntry OBJECT-TYPE
    SYNTAX Enc1P1329finalLimiterCeilingEntry
    MAX-ACCESS not-accessible
    STATUS     current
    DESCRIPTION
    "Table Entry for Final Limiter Ceiling"
    INDEX { slotId }
::= { enc1P1329finalLimiterCeilingTable 1 }

Enc1P1329finalLimiterCeilingEntry ::= SEQUENCE {
    enc1P1329finalLimiterCeilingValue    INTEGER
}

enc1P1329finalLimiterCeilingValue OBJECT-TYPE
    SYNTAX     INTEGER
    MAX-ACCESS read-write
    STATUS     current
    DESCRIPTION
    "Specifies the threshold above which final limiting will be applied."
::= { enc1P1329finalLimiterCeilingEntry 1 }

enc1P1330runFinalLimitersTable OBJECT-TYPE
    SYNTAX SEQUENCE OF Enc1P1330runFinalLimitersEntry
    MAX-ACCESS not-accessible
    STATUS     current
    DESCRIPTION
    "
    Name      : Run Final Limiters
    Menu Path : /Audio/AAP 1 Configuration/DTS Neural Loudness Ctrl 3
    Details   : Enables final limiters to be applied according to the value of the Final Limiter Ceiling.
    "
::= { enc1Params 1330 }

enc1P1330runFinalLimitersEntry OBJECT-TYPE
    SYNTAX Enc1P1330runFinalLimitersEntry
    MAX-ACCESS not-accessible
    STATUS     current
    DESCRIPTION
    "Table Entry for Run Final Limiters"
    INDEX { slotId }
::= { enc1P1330runFinalLimitersTable 1 }

Enc1P1330runFinalLimitersEntry ::= SEQUENCE {
    enc1P1330runFinalLimitersValue    Enc1E152enumObj
}

enc1P1330runFinalLimitersValue OBJECT-TYPE
    SYNTAX     Enc1E152enumObj
    MAX-ACCESS read-write
    STATUS     current
    DESCRIPTION
    "Enables final limiters to be applied according to the value of the Final Limiter Ceiling."
::= { enc1P1330runFinalLimitersEntry 1 }

enc1P1331meteringTable OBJECT-TYPE
    SYNTAX SEQUENCE OF Enc1P1331meteringEntry
    MAX-ACCESS not-accessible
    STATUS     current
    DESCRIPTION
    "
    Name      : Metering
    Menu Path : /Audio/AAP 1 Configuration/DTS Neural Loudness Ctrl 3
    Details   : Activates the real-time meters (below).
    "
::= { enc1Params 1331 }

enc1P1331meteringEntry OBJECT-TYPE
    SYNTAX Enc1P1331meteringEntry
    MAX-ACCESS not-accessible
    STATUS     current
    DESCRIPTION
    "Table Entry for Metering"
    INDEX { slotId }
::= { enc1P1331meteringTable 1 }

Enc1P1331meteringEntry ::= SEQUENCE {
    enc1P1331meteringValue    Enc1E154enumObj
}

enc1P1331meteringValue OBJECT-TYPE
    SYNTAX     Enc1E154enumObj
    MAX-ACCESS read-write
    STATUS     current
    DESCRIPTION
    "Activates the real-time meters (below)."
::= { enc1P1331meteringEntry 1 }

enc1P1332currentInputLoudnessTable OBJECT-TYPE
    SYNTAX SEQUENCE OF Enc1P1332currentInputLoudnessEntry
    MAX-ACCESS not-accessible
    STATUS     current
    DESCRIPTION
    "
    Name      : Current Input Loudness
    Menu Path : /Audio/AAP 1 Configuration/DTS Neural Loudness Ctrl 3
    Units     : dBEq
    Precision : 0
    Low Range : -60
    High Range: 20
    Details   : Reports the smoothed input loudness measurement.

     NOTE: Precision/Units/Ranges represent the state of the
           parameter during the MIB generation, and does not
           neccessary reflect the current state of the parameter
    "
::= { enc1Params 1332 }

enc1P1332currentInputLoudnessEntry OBJECT-TYPE
    SYNTAX Enc1P1332currentInputLoudnessEntry
    MAX-ACCESS not-accessible
    STATUS     current
    DESCRIPTION
    "Table Entry for Current Input Loudness"
    INDEX { slotId }
::= { enc1P1332currentInputLoudnessTable 1 }

Enc1P1332currentInputLoudnessEntry ::= SEQUENCE {
    enc1P1332currentInputLoudnessValue    INTEGER
}

enc1P1332currentInputLoudnessValue OBJECT-TYPE
    SYNTAX     INTEGER
    MAX-ACCESS read-only
    STATUS     current
    DESCRIPTION
    "Reports the smoothed input loudness measurement."
::= { enc1P1332currentInputLoudnessEntry 1 }

enc1P1333currentInputPeakTable OBJECT-TYPE
    SYNTAX SEQUENCE OF Enc1P1333currentInputPeakEntry
    MAX-ACCESS not-accessible
    STATUS     current
    DESCRIPTION
    "
    Name      : Current Input Peak
    Menu Path : /Audio/AAP 1 Configuration/DTS Neural Loudness Ctrl 3
    Units     : dBFS
    Precision : 0
    Low Range : -60
    High Range: 20
    Details   : Reports the input peak measurement.

     NOTE: Precision/Units/Ranges represent the state of the
           parameter during the MIB generation, and does not
           neccessary reflect the current state of the parameter
    "
::= { enc1Params 1333 }

enc1P1333currentInputPeakEntry OBJECT-TYPE
    SYNTAX Enc1P1333currentInputPeakEntry
    MAX-ACCESS not-accessible
    STATUS     current
    DESCRIPTION
    "Table Entry for Current Input Peak"
    INDEX { slotId }
::= { enc1P1333currentInputPeakTable 1 }

Enc1P1333currentInputPeakEntry ::= SEQUENCE {
    enc1P1333currentInputPeakValue    INTEGER
}

enc1P1333currentInputPeakValue OBJECT-TYPE
    SYNTAX     INTEGER
    MAX-ACCESS read-only
    STATUS     current
    DESCRIPTION
    "Reports the input peak measurement."
::= { enc1P1333currentInputPeakEntry 1 }

enc1P1334currentOutputLoudnessTable OBJECT-TYPE
    SYNTAX SEQUENCE OF Enc1P1334currentOutputLoudnessEntry
    MAX-ACCESS not-accessible
    STATUS     current
    DESCRIPTION
    "
    Name      : Current Output Loudness
    Menu Path : /Audio/AAP 1 Configuration/DTS Neural Loudness Ctrl 3
    Units     : dBEq
    Precision : 0
    Low Range : -60
    High Range: 20
    Details   : Reports the smoothed output loudness measurement.

     NOTE: Precision/Units/Ranges represent the state of the
           parameter during the MIB generation, and does not
           neccessary reflect the current state of the parameter
    "
::= { enc1Params 1334 }

enc1P1334currentOutputLoudnessEntry OBJECT-TYPE
    SYNTAX Enc1P1334currentOutputLoudnessEntry
    MAX-ACCESS not-accessible
    STATUS     current
    DESCRIPTION
    "Table Entry for Current Output Loudness"
    INDEX { slotId }
::= { enc1P1334currentOutputLoudnessTable 1 }

Enc1P1334currentOutputLoudnessEntry ::= SEQUENCE {
    enc1P1334currentOutputLoudnessValue    INTEGER
}

enc1P1334currentOutputLoudnessValue OBJECT-TYPE
    SYNTAX     INTEGER
    MAX-ACCESS read-only
    STATUS     current
    DESCRIPTION
    "Reports the smoothed output loudness measurement."
::= { enc1P1334currentOutputLoudnessEntry 1 }

enc1P1335currentOutputPeakTable OBJECT-TYPE
    SYNTAX SEQUENCE OF Enc1P1335currentOutputPeakEntry
    MAX-ACCESS not-accessible
    STATUS     current
    DESCRIPTION
    "
    Name      : Current Output Peak
    Menu Path : /Audio/AAP 1 Configuration/DTS Neural Loudness Ctrl 3
    Units     : dBFS
    Precision : 0
    Low Range : -60
    High Range: 20
    Details   : Reports the output peak measurement.

     NOTE: Precision/Units/Ranges represent the state of the
           parameter during the MIB generation, and does not
           neccessary reflect the current state of the parameter
    "
::= { enc1Params 1335 }

enc1P1335currentOutputPeakEntry OBJECT-TYPE
    SYNTAX Enc1P1335currentOutputPeakEntry
    MAX-ACCESS not-accessible
    STATUS     current
    DESCRIPTION
    "Table Entry for Current Output Peak"
    INDEX { slotId }
::= { enc1P1335currentOutputPeakTable 1 }

Enc1P1335currentOutputPeakEntry ::= SEQUENCE {
    enc1P1335currentOutputPeakValue    INTEGER
}

enc1P1335currentOutputPeakValue OBJECT-TYPE
    SYNTAX     INTEGER
    MAX-ACCESS read-only
    STATUS     current
    DESCRIPTION
    "Reports the output peak measurement."
::= { enc1P1335currentOutputPeakEntry 1 }

enc1P1336currentCorrectionTable OBJECT-TYPE
    SYNTAX SEQUENCE OF Enc1P1336currentCorrectionEntry
    MAX-ACCESS not-accessible
    STATUS     current
    DESCRIPTION
    "
    Name      : Current Correction
    Menu Path : /Audio/AAP 1 Configuration/DTS Neural Loudness Ctrl 3
    Units     : dB
    Precision : 0
    Low Range : -60
    High Range: 60
    Details   : Reports the amount of correction being applied.

     NOTE: Precision/Units/Ranges represent the state of the
           parameter during the MIB generation, and does not
           neccessary reflect the current state of the parameter
    "
::= { enc1Params 1336 }

enc1P1336currentCorrectionEntry OBJECT-TYPE
    SYNTAX Enc1P1336currentCorrectionEntry
    MAX-ACCESS not-accessible
    STATUS     current
    DESCRIPTION
    "Table Entry for Current Correction"
    INDEX { slotId }
::= { enc1P1336currentCorrectionTable 1 }

Enc1P1336currentCorrectionEntry ::= SEQUENCE {
    enc1P1336currentCorrectionValue    INTEGER
}

enc1P1336currentCorrectionValue OBJECT-TYPE
    SYNTAX     INTEGER
    MAX-ACCESS read-only
    STATUS     current
    DESCRIPTION
    "Reports the amount of correction being applied."
::= { enc1P1336currentCorrectionEntry 1 }

enc1P1337currentCompressionTable OBJECT-TYPE
    SYNTAX SEQUENCE OF Enc1P1337currentCompressionEntry
    MAX-ACCESS not-accessible
    STATUS     current
    DESCRIPTION
    "
    Name      : Current Compression
    Menu Path : /Audio/AAP 1 Configuration/DTS Neural Loudness Ctrl 3
    Units     : dB
    Precision : 0
    Low Range : -60
    High Range: 60
    Details   : Reports the amount of compression being applied.

     NOTE: Precision/Units/Ranges represent the state of the
           parameter during the MIB generation, and does not
           neccessary reflect the current state of the parameter
    "
::= { enc1Params 1337 }

enc1P1337currentCompressionEntry OBJECT-TYPE
    SYNTAX Enc1P1337currentCompressionEntry
    MAX-ACCESS not-accessible
    STATUS     current
    DESCRIPTION
    "Table Entry for Current Compression"
    INDEX { slotId }
::= { enc1P1337currentCompressionTable 1 }

Enc1P1337currentCompressionEntry ::= SEQUENCE {
    enc1P1337currentCompressionValue    INTEGER
}

enc1P1337currentCompressionValue OBJECT-TYPE
    SYNTAX     INTEGER
    MAX-ACCESS read-only
    STATUS     current
    DESCRIPTION
    "Reports the amount of compression being applied."
::= { enc1P1337currentCompressionEntry 1 }

enc1P1338loudnessControlFunctionTable OBJECT-TYPE
    SYNTAX SEQUENCE OF Enc1P1338loudnessControlFunctionEntry
    MAX-ACCESS not-accessible
    STATUS     current
    DESCRIPTION
    "
    Name      : Loudness Control Function
    Menu Path : /Audio/AAP 1 Configuration/DTS Neural Loudness Ctrl 4
    Details   : Bypasses the loudness control circuit.
    "
::= { enc1Params 1338 }

enc1P1338loudnessControlFunctionEntry OBJECT-TYPE
    SYNTAX Enc1P1338loudnessControlFunctionEntry
    MAX-ACCESS not-accessible
    STATUS     current
    DESCRIPTION
    "Table Entry for Loudness Control Function"
    INDEX { slotId }
::= { enc1P1338loudnessControlFunctionTable 1 }

Enc1P1338loudnessControlFunctionEntry ::= SEQUENCE {
    enc1P1338loudnessControlFunctionValue    Enc1E174enumObj
}

enc1P1338loudnessControlFunctionValue OBJECT-TYPE
    SYNTAX     Enc1E174enumObj
    MAX-ACCESS read-write
    STATUS     current
    DESCRIPTION
    "Bypasses the loudness control circuit."
::= { enc1P1338loudnessControlFunctionEntry 1 }

enc1P1339loudnessControlStatusTable OBJECT-TYPE
    SYNTAX SEQUENCE OF Enc1P1339loudnessControlStatusEntry
    MAX-ACCESS not-accessible
    STATUS     current
    DESCRIPTION
    "
    Name      : Loudness Control Status
    Menu Path : /Audio/AAP 1 Configuration/DTS Neural Loudness Ctrl 4
    Details   : Indicates the state of loudness control processing.
    "
::= { enc1Params 1339 }

enc1P1339loudnessControlStatusEntry OBJECT-TYPE
    SYNTAX Enc1P1339loudnessControlStatusEntry
    MAX-ACCESS not-accessible
    STATUS     current
    DESCRIPTION
    "Table Entry for Loudness Control Status"
    INDEX { slotId }
::= { enc1P1339loudnessControlStatusTable 1 }

Enc1P1339loudnessControlStatusEntry ::= SEQUENCE {
    enc1P1339loudnessControlStatusValue    Enc1E172enumObj
}

enc1P1339loudnessControlStatusValue OBJECT-TYPE
    SYNTAX     Enc1E172enumObj
    MAX-ACCESS read-only
    STATUS     current
    DESCRIPTION
    "Indicates the state of loudness control processing."
::= { enc1P1339loudnessControlStatusEntry 1 }

enc1P1340loudnessMeasurementTypeTable OBJECT-TYPE
    SYNTAX SEQUENCE OF Enc1P1340loudnessMeasurementTypeEntry
    MAX-ACCESS not-accessible
    STATUS     current
    DESCRIPTION
    "
    Name      : Loudness Measurement Type
    Menu Path : /Audio/AAP 1 Configuration/DTS Neural Loudness Ctrl 4
    Details   : Specifies the type of loudness measurement to make prior to performing loudness control.
    "
::= { enc1Params 1340 }

enc1P1340loudnessMeasurementTypeEntry OBJECT-TYPE
    SYNTAX Enc1P1340loudnessMeasurementTypeEntry
    MAX-ACCESS not-accessible
    STATUS     current
    DESCRIPTION
    "Table Entry for Loudness Measurement Type"
    INDEX { slotId }
::= { enc1P1340loudnessMeasurementTypeTable 1 }

Enc1P1340loudnessMeasurementTypeEntry ::= SEQUENCE {
    enc1P1340loudnessMeasurementTypeValue    Enc1E175enumObj
}

enc1P1340loudnessMeasurementTypeValue OBJECT-TYPE
    SYNTAX     Enc1E175enumObj
    MAX-ACCESS read-write
    STATUS     current
    DESCRIPTION
    "Specifies the type of loudness measurement to make prior to performing loudness control."
::= { enc1P1340loudnessMeasurementTypeEntry 1 }

enc1P1341targetLoudnessLevelTable OBJECT-TYPE
    SYNTAX SEQUENCE OF Enc1P1341targetLoudnessLevelEntry
    MAX-ACCESS not-accessible
    STATUS     current
    DESCRIPTION
    "
    Name      : Target Loudness Level
    Menu Path : /Audio/AAP 1 Configuration/DTS Neural Loudness Ctrl 4
    Units     : dBEq/LKFS
    Precision : 0
    Low Range : -40
    High Range: 0
    Details   : Specifies the loudness level that will be targeted.

     NOTE: Precision/Units/Ranges represent the state of the
           parameter during the MIB generation, and does not
           neccessary reflect the current state of the parameter
    "
::= { enc1Params 1341 }

enc1P1341targetLoudnessLevelEntry OBJECT-TYPE
    SYNTAX Enc1P1341targetLoudnessLevelEntry
    MAX-ACCESS not-accessible
    STATUS     current
    DESCRIPTION
    "Table Entry for Target Loudness Level"
    INDEX { slotId }
::= { enc1P1341targetLoudnessLevelTable 1 }

Enc1P1341targetLoudnessLevelEntry ::= SEQUENCE {
    enc1P1341targetLoudnessLevelValue    INTEGER
}

enc1P1341targetLoudnessLevelValue OBJECT-TYPE
    SYNTAX     INTEGER
    MAX-ACCESS read-write
    STATUS     current
    DESCRIPTION
    "Specifies the loudness level that will be targeted."
::= { enc1P1341targetLoudnessLevelEntry 1 }

enc1P1342lcratioTable OBJECT-TYPE
    SYNTAX SEQUENCE OF Enc1P1342lcratioEntry
    MAX-ACCESS not-accessible
    STATUS     current
    DESCRIPTION
    "
    Name      : LC Ratio
    Menu Path : /Audio/AAP 1 Configuration/DTS Neural Loudness Ctrl 4
    Units     : 
    Precision : 2
    Low Range : 0
    High Range: 100
    Details   : Controls the amount of gain or attenuation that is applied when loudness differences are measured.

     NOTE: Precision/Units/Ranges represent the state of the
           parameter during the MIB generation, and does not
           neccessary reflect the current state of the parameter
    "
::= { enc1Params 1342 }

enc1P1342lcratioEntry OBJECT-TYPE
    SYNTAX Enc1P1342lcratioEntry
    MAX-ACCESS not-accessible
    STATUS     current
    DESCRIPTION
    "Table Entry for LC Ratio"
    INDEX { slotId }
::= { enc1P1342lcratioTable 1 }

Enc1P1342lcratioEntry ::= SEQUENCE {
    enc1P1342lcratioValue    INTEGER
}

enc1P1342lcratioValue OBJECT-TYPE
    SYNTAX     INTEGER
    MAX-ACCESS read-write
    STATUS     current
    DESCRIPTION
    "Controls the amount of gain or attenuation that is applied when loudness differences are measured."
::= { enc1P1342lcratioEntry 1 }

enc1P1343upperThresholdTable OBJECT-TYPE
    SYNTAX SEQUENCE OF Enc1P1343upperThresholdEntry
    MAX-ACCESS not-accessible
    STATUS     current
    DESCRIPTION
    "
    Name      : Upper Threshold
    Menu Path : /Audio/AAP 1 Configuration/DTS Neural Loudness Ctrl 4
    Units     : dB
    Precision : 0
    Low Range : 0
    High Range: 20
    Details   : Specifies the highest measured loudness of the input that will be permitted before attenuation is applied.

     NOTE: Precision/Units/Ranges represent the state of the
           parameter during the MIB generation, and does not
           neccessary reflect the current state of the parameter
    "
::= { enc1Params 1343 }

enc1P1343upperThresholdEntry OBJECT-TYPE
    SYNTAX Enc1P1343upperThresholdEntry
    MAX-ACCESS not-accessible
    STATUS     current
    DESCRIPTION
    "Table Entry for Upper Threshold"
    INDEX { slotId }
::= { enc1P1343upperThresholdTable 1 }

Enc1P1343upperThresholdEntry ::= SEQUENCE {
    enc1P1343upperThresholdValue    INTEGER
}

enc1P1343upperThresholdValue OBJECT-TYPE
    SYNTAX     INTEGER
    MAX-ACCESS read-write
    STATUS     current
    DESCRIPTION
    "Specifies the highest measured loudness of the input that will be permitted before attenuation is applied."
::= { enc1P1343upperThresholdEntry 1 }

enc1P1344lowerThresholdTable OBJECT-TYPE
    SYNTAX SEQUENCE OF Enc1P1344lowerThresholdEntry
    MAX-ACCESS not-accessible
    STATUS     current
    DESCRIPTION
    "
    Name      : Lower Threshold
    Menu Path : /Audio/AAP 1 Configuration/DTS Neural Loudness Ctrl 4
    Units     : dB
    Precision : 0
    Low Range : -20
    High Range: 0
    Details   : Specifies the lowest measured loudness of the input that will be permitted before gain is applied.

     NOTE: Precision/Units/Ranges represent the state of the
           parameter during the MIB generation, and does not
           neccessary reflect the current state of the parameter
    "
::= { enc1Params 1344 }

enc1P1344lowerThresholdEntry OBJECT-TYPE
    SYNTAX Enc1P1344lowerThresholdEntry
    MAX-ACCESS not-accessible
    STATUS     current
    DESCRIPTION
    "Table Entry for Lower Threshold"
    INDEX { slotId }
::= { enc1P1344lowerThresholdTable 1 }

Enc1P1344lowerThresholdEntry ::= SEQUENCE {
    enc1P1344lowerThresholdValue    INTEGER
}

enc1P1344lowerThresholdValue OBJECT-TYPE
    SYNTAX     INTEGER
    MAX-ACCESS read-write
    STATUS     current
    DESCRIPTION
    "Specifies the lowest measured loudness of the input that will be permitted before gain is applied."
::= { enc1P1344lowerThresholdEntry 1 }

enc1P1345freezeWindowTable OBJECT-TYPE
    SYNTAX SEQUENCE OF Enc1P1345freezeWindowEntry
    MAX-ACCESS not-accessible
    STATUS     current
    DESCRIPTION
    "
    Name      : Freeze Window
    Menu Path : /Audio/AAP 1 Configuration/DTS Neural Loudness Ctrl 4
    Units     : dB
    Precision : 1
    Low Range : 0
    High Range: 100
    Details   : Specifies the size of a window which small loudness differences are allowed without the need to change gain or attenuation.

     NOTE: Precision/Units/Ranges represent the state of the
           parameter during the MIB generation, and does not
           neccessary reflect the current state of the parameter
    "
::= { enc1Params 1345 }

enc1P1345freezeWindowEntry OBJECT-TYPE
    SYNTAX Enc1P1345freezeWindowEntry
    MAX-ACCESS not-accessible
    STATUS     current
    DESCRIPTION
    "Table Entry for Freeze Window"
    INDEX { slotId }
::= { enc1P1345freezeWindowTable 1 }

Enc1P1345freezeWindowEntry ::= SEQUENCE {
    enc1P1345freezeWindowValue    INTEGER
}

enc1P1345freezeWindowValue OBJECT-TYPE
    SYNTAX     INTEGER
    MAX-ACCESS read-write
    STATUS     current
    DESCRIPTION
    "Specifies the size of a window which small loudness differences are allowed without the need to change gain or attenuation."
::= { enc1P1345freezeWindowEntry 1 }

enc1P1346quietThresholdTable OBJECT-TYPE
    SYNTAX SEQUENCE OF Enc1P1346quietThresholdEntry
    MAX-ACCESS not-accessible
    STATUS     current
    DESCRIPTION
    "
    Name      : Quiet Threshold
    Menu Path : /Audio/AAP 1 Configuration/DTS Neural Loudness Ctrl 4
    Units     : dBEq
    Precision : 0
    Low Range : -80
    High Range: -20
    Details   : Controls the noise floor level.

     NOTE: Precision/Units/Ranges represent the state of the
           parameter during the MIB generation, and does not
           neccessary reflect the current state of the parameter
    "
::= { enc1Params 1346 }

enc1P1346quietThresholdEntry OBJECT-TYPE
    SYNTAX Enc1P1346quietThresholdEntry
    MAX-ACCESS not-accessible
    STATUS     current
    DESCRIPTION
    "Table Entry for Quiet Threshold"
    INDEX { slotId }
::= { enc1P1346quietThresholdTable 1 }

Enc1P1346quietThresholdEntry ::= SEQUENCE {
    enc1P1346quietThresholdValue    INTEGER
}

enc1P1346quietThresholdValue OBJECT-TYPE
    SYNTAX     INTEGER
    MAX-ACCESS read-write
    STATUS     current
    DESCRIPTION
    "Controls the noise floor level."
::= { enc1P1346quietThresholdEntry 1 }

enc1P1347attackTimeTable OBJECT-TYPE
    SYNTAX SEQUENCE OF Enc1P1347attackTimeEntry
    MAX-ACCESS not-accessible
    STATUS     current
    DESCRIPTION
    "
    Name      : Attack Time
    Menu Path : /Audio/AAP 1 Configuration/DTS Neural Loudness Ctrl 4
    Units     : ms
    Precision : 0
    Low Range : 5
    High Range: 150
    Details   : Controls how quickly the processing will respond to sharp increases in loudness.

     NOTE: Precision/Units/Ranges represent the state of the
           parameter during the MIB generation, and does not
           neccessary reflect the current state of the parameter
    "
::= { enc1Params 1347 }

enc1P1347attackTimeEntry OBJECT-TYPE
    SYNTAX Enc1P1347attackTimeEntry
    MAX-ACCESS not-accessible
    STATUS     current
    DESCRIPTION
    "Table Entry for Attack Time"
    INDEX { slotId }
::= { enc1P1347attackTimeTable 1 }

Enc1P1347attackTimeEntry ::= SEQUENCE {
    enc1P1347attackTimeValue    INTEGER
}

enc1P1347attackTimeValue OBJECT-TYPE
    SYNTAX     INTEGER
    MAX-ACCESS read-write
    STATUS     current
    DESCRIPTION
    "Controls how quickly the processing will respond to sharp increases in loudness."
::= { enc1P1347attackTimeEntry 1 }

enc1P1348releaseTimeTable OBJECT-TYPE
    SYNTAX SEQUENCE OF Enc1P1348releaseTimeEntry
    MAX-ACCESS not-accessible
    STATUS     current
    DESCRIPTION
    "
    Name      : Release Time
    Menu Path : /Audio/AAP 1 Configuration/DTS Neural Loudness Ctrl 4
    Units     : ms
    Precision : 0
    Low Range : 20
    High Range: 500
    Details   : Controls how quickly the processing will respond to sharp decreases in loudness.

     NOTE: Precision/Units/Ranges represent the state of the
           parameter during the MIB generation, and does not
           neccessary reflect the current state of the parameter
    "
::= { enc1Params 1348 }

enc1P1348releaseTimeEntry OBJECT-TYPE
    SYNTAX Enc1P1348releaseTimeEntry
    MAX-ACCESS not-accessible
    STATUS     current
    DESCRIPTION
    "Table Entry for Release Time"
    INDEX { slotId }
::= { enc1P1348releaseTimeTable 1 }

Enc1P1348releaseTimeEntry ::= SEQUENCE {
    enc1P1348releaseTimeValue    INTEGER
}

enc1P1348releaseTimeValue OBJECT-TYPE
    SYNTAX     INTEGER
    MAX-ACCESS read-write
    STATUS     current
    DESCRIPTION
    "Controls how quickly the processing will respond to sharp decreases in loudness."
::= { enc1P1348releaseTimeEntry 1 }

enc1P1349compressorThresholdTable OBJECT-TYPE
    SYNTAX SEQUENCE OF Enc1P1349compressorThresholdEntry
    MAX-ACCESS not-accessible
    STATUS     current
    DESCRIPTION
    "
    Name      : Compressor Threshold
    Menu Path : /Audio/AAP 1 Configuration/DTS Neural Loudness Ctrl 4
    Units     : dB
    Precision : 0
    Low Range : 0
    High Range: 16
    Details   : Loudness Control Compressor Threshold

     NOTE: Precision/Units/Ranges represent the state of the
           parameter during the MIB generation, and does not
           neccessary reflect the current state of the parameter
    "
::= { enc1Params 1349 }

enc1P1349compressorThresholdEntry OBJECT-TYPE
    SYNTAX Enc1P1349compressorThresholdEntry
    MAX-ACCESS not-accessible
    STATUS     current
    DESCRIPTION
    "Table Entry for Compressor Threshold"
    INDEX { slotId }
::= { enc1P1349compressorThresholdTable 1 }

Enc1P1349compressorThresholdEntry ::= SEQUENCE {
    enc1P1349compressorThresholdValue    INTEGER
}

enc1P1349compressorThresholdValue OBJECT-TYPE
    SYNTAX     INTEGER
    MAX-ACCESS read-write
    STATUS     current
    DESCRIPTION
    "Loudness Control Compressor Threshold"
::= { enc1P1349compressorThresholdEntry 1 }

enc1P1350compressorRatioTable OBJECT-TYPE
    SYNTAX SEQUENCE OF Enc1P1350compressorRatioEntry
    MAX-ACCESS not-accessible
    STATUS     current
    DESCRIPTION
    "
    Name      : Compressor Ratio
    Menu Path : /Audio/AAP 1 Configuration/DTS Neural Loudness Ctrl 4
    Units     : 
    Precision : 2
    Low Range : 0
    High Range: 100
    Details   : Controls the amount of attenuation applied when short-term peaks exceed the compressor threshold.

     NOTE: Precision/Units/Ranges represent the state of the
           parameter during the MIB generation, and does not
           neccessary reflect the current state of the parameter
    "
::= { enc1Params 1350 }

enc1P1350compressorRatioEntry OBJECT-TYPE
    SYNTAX Enc1P1350compressorRatioEntry
    MAX-ACCESS not-accessible
    STATUS     current
    DESCRIPTION
    "Table Entry for Compressor Ratio"
    INDEX { slotId }
::= { enc1P1350compressorRatioTable 1 }

Enc1P1350compressorRatioEntry ::= SEQUENCE {
    enc1P1350compressorRatioValue    INTEGER
}

enc1P1350compressorRatioValue OBJECT-TYPE
    SYNTAX     INTEGER
    MAX-ACCESS read-write
    STATUS     current
    DESCRIPTION
    "Controls the amount of attenuation applied when short-term peaks exceed the compressor threshold."
::= { enc1P1350compressorRatioEntry 1 }

enc1P1351loudnessShapingTable OBJECT-TYPE
    SYNTAX SEQUENCE OF Enc1P1351loudnessShapingEntry
    MAX-ACCESS not-accessible
    STATUS     current
    DESCRIPTION
    "
    Name      : Loudness Shaping
    Menu Path : /Audio/AAP 1 Configuration/DTS Neural Loudness Ctrl 4
    Units     : 
    Precision : 1
    Low Range : 0
    High Range: 10
    Details   : Specifies the amount of loudness shaping desired.

     NOTE: Precision/Units/Ranges represent the state of the
           parameter during the MIB generation, and does not
           neccessary reflect the current state of the parameter
    "
::= { enc1Params 1351 }

enc1P1351loudnessShapingEntry OBJECT-TYPE
    SYNTAX Enc1P1351loudnessShapingEntry
    MAX-ACCESS not-accessible
    STATUS     current
    DESCRIPTION
    "Table Entry for Loudness Shaping"
    INDEX { slotId }
::= { enc1P1351loudnessShapingTable 1 }

Enc1P1351loudnessShapingEntry ::= SEQUENCE {
    enc1P1351loudnessShapingValue    INTEGER
}

enc1P1351loudnessShapingValue OBJECT-TYPE
    SYNTAX     INTEGER
    MAX-ACCESS read-write
    STATUS     current
    DESCRIPTION
    "Specifies the amount of loudness shaping desired."
::= { enc1P1351loudnessShapingEntry 1 }

enc1P1352finalLimiterCeilingTable OBJECT-TYPE
    SYNTAX SEQUENCE OF Enc1P1352finalLimiterCeilingEntry
    MAX-ACCESS not-accessible
    STATUS     current
    DESCRIPTION
    "
    Name      : Final Limiter Ceiling
    Menu Path : /Audio/AAP 1 Configuration/DTS Neural Loudness Ctrl 4
    Units     : dBFS
    Precision : 0
    Low Range : -20
    High Range: 0
    Details   : Specifies the threshold above which final limiting will be applied.

     NOTE: Precision/Units/Ranges represent the state of the
           parameter during the MIB generation, and does not
           neccessary reflect the current state of the parameter
    "
::= { enc1Params 1352 }

enc1P1352finalLimiterCeilingEntry OBJECT-TYPE
    SYNTAX Enc1P1352finalLimiterCeilingEntry
    MAX-ACCESS not-accessible
    STATUS     current
    DESCRIPTION
    "Table Entry for Final Limiter Ceiling"
    INDEX { slotId }
::= { enc1P1352finalLimiterCeilingTable 1 }

Enc1P1352finalLimiterCeilingEntry ::= SEQUENCE {
    enc1P1352finalLimiterCeilingValue    INTEGER
}

enc1P1352finalLimiterCeilingValue OBJECT-TYPE
    SYNTAX     INTEGER
    MAX-ACCESS read-write
    STATUS     current
    DESCRIPTION
    "Specifies the threshold above which final limiting will be applied."
::= { enc1P1352finalLimiterCeilingEntry 1 }

enc1P1353runFinalLimitersTable OBJECT-TYPE
    SYNTAX SEQUENCE OF Enc1P1353runFinalLimitersEntry
    MAX-ACCESS not-accessible
    STATUS     current
    DESCRIPTION
    "
    Name      : Run Final Limiters
    Menu Path : /Audio/AAP 1 Configuration/DTS Neural Loudness Ctrl 4
    Details   : Enables final limiters to be applied according to the value of the Final Limiter Ceiling.
    "
::= { enc1Params 1353 }

enc1P1353runFinalLimitersEntry OBJECT-TYPE
    SYNTAX Enc1P1353runFinalLimitersEntry
    MAX-ACCESS not-accessible
    STATUS     current
    DESCRIPTION
    "Table Entry for Run Final Limiters"
    INDEX { slotId }
::= { enc1P1353runFinalLimitersTable 1 }

Enc1P1353runFinalLimitersEntry ::= SEQUENCE {
    enc1P1353runFinalLimitersValue    Enc1E152enumObj
}

enc1P1353runFinalLimitersValue OBJECT-TYPE
    SYNTAX     Enc1E152enumObj
    MAX-ACCESS read-write
    STATUS     current
    DESCRIPTION
    "Enables final limiters to be applied according to the value of the Final Limiter Ceiling."
::= { enc1P1353runFinalLimitersEntry 1 }

enc1P1354meteringTable OBJECT-TYPE
    SYNTAX SEQUENCE OF Enc1P1354meteringEntry
    MAX-ACCESS not-accessible
    STATUS     current
    DESCRIPTION
    "
    Name      : Metering
    Menu Path : /Audio/AAP 1 Configuration/DTS Neural Loudness Ctrl 4
    Details   : Activates the real-time meters (below).
    "
::= { enc1Params 1354 }

enc1P1354meteringEntry OBJECT-TYPE
    SYNTAX Enc1P1354meteringEntry
    MAX-ACCESS not-accessible
    STATUS     current
    DESCRIPTION
    "Table Entry for Metering"
    INDEX { slotId }
::= { enc1P1354meteringTable 1 }

Enc1P1354meteringEntry ::= SEQUENCE {
    enc1P1354meteringValue    Enc1E154enumObj
}

enc1P1354meteringValue OBJECT-TYPE
    SYNTAX     Enc1E154enumObj
    MAX-ACCESS read-write
    STATUS     current
    DESCRIPTION
    "Activates the real-time meters (below)."
::= { enc1P1354meteringEntry 1 }

enc1P1355currentInputLoudnessTable OBJECT-TYPE
    SYNTAX SEQUENCE OF Enc1P1355currentInputLoudnessEntry
    MAX-ACCESS not-accessible
    STATUS     current
    DESCRIPTION
    "
    Name      : Current Input Loudness
    Menu Path : /Audio/AAP 1 Configuration/DTS Neural Loudness Ctrl 4
    Units     : dBEq
    Precision : 0
    Low Range : -60
    High Range: 20
    Details   : Reports the smoothed input loudness measurement.

     NOTE: Precision/Units/Ranges represent the state of the
           parameter during the MIB generation, and does not
           neccessary reflect the current state of the parameter
    "
::= { enc1Params 1355 }

enc1P1355currentInputLoudnessEntry OBJECT-TYPE
    SYNTAX Enc1P1355currentInputLoudnessEntry
    MAX-ACCESS not-accessible
    STATUS     current
    DESCRIPTION
    "Table Entry for Current Input Loudness"
    INDEX { slotId }
::= { enc1P1355currentInputLoudnessTable 1 }

Enc1P1355currentInputLoudnessEntry ::= SEQUENCE {
    enc1P1355currentInputLoudnessValue    INTEGER
}

enc1P1355currentInputLoudnessValue OBJECT-TYPE
    SYNTAX     INTEGER
    MAX-ACCESS read-only
    STATUS     current
    DESCRIPTION
    "Reports the smoothed input loudness measurement."
::= { enc1P1355currentInputLoudnessEntry 1 }

enc1P1356currentInputPeakTable OBJECT-TYPE
    SYNTAX SEQUENCE OF Enc1P1356currentInputPeakEntry
    MAX-ACCESS not-accessible
    STATUS     current
    DESCRIPTION
    "
    Name      : Current Input Peak
    Menu Path : /Audio/AAP 1 Configuration/DTS Neural Loudness Ctrl 4
    Units     : dBFS
    Precision : 0
    Low Range : -60
    High Range: 20
    Details   : Reports the input peak measurement.

     NOTE: Precision/Units/Ranges represent the state of the
           parameter during the MIB generation, and does not
           neccessary reflect the current state of the parameter
    "
::= { enc1Params 1356 }

enc1P1356currentInputPeakEntry OBJECT-TYPE
    SYNTAX Enc1P1356currentInputPeakEntry
    MAX-ACCESS not-accessible
    STATUS     current
    DESCRIPTION
    "Table Entry for Current Input Peak"
    INDEX { slotId }
::= { enc1P1356currentInputPeakTable 1 }

Enc1P1356currentInputPeakEntry ::= SEQUENCE {
    enc1P1356currentInputPeakValue    INTEGER
}

enc1P1356currentInputPeakValue OBJECT-TYPE
    SYNTAX     INTEGER
    MAX-ACCESS read-only
    STATUS     current
    DESCRIPTION
    "Reports the input peak measurement."
::= { enc1P1356currentInputPeakEntry 1 }

enc1P1357currentOutputLoudnessTable OBJECT-TYPE
    SYNTAX SEQUENCE OF Enc1P1357currentOutputLoudnessEntry
    MAX-ACCESS not-accessible
    STATUS     current
    DESCRIPTION
    "
    Name      : Current Output Loudness
    Menu Path : /Audio/AAP 1 Configuration/DTS Neural Loudness Ctrl 4
    Units     : dBEq
    Precision : 0
    Low Range : -60
    High Range: 20
    Details   : Reports the smoothed output loudness measurement.

     NOTE: Precision/Units/Ranges represent the state of the
           parameter during the MIB generation, and does not
           neccessary reflect the current state of the parameter
    "
::= { enc1Params 1357 }

enc1P1357currentOutputLoudnessEntry OBJECT-TYPE
    SYNTAX Enc1P1357currentOutputLoudnessEntry
    MAX-ACCESS not-accessible
    STATUS     current
    DESCRIPTION
    "Table Entry for Current Output Loudness"
    INDEX { slotId }
::= { enc1P1357currentOutputLoudnessTable 1 }

Enc1P1357currentOutputLoudnessEntry ::= SEQUENCE {
    enc1P1357currentOutputLoudnessValue    INTEGER
}

enc1P1357currentOutputLoudnessValue OBJECT-TYPE
    SYNTAX     INTEGER
    MAX-ACCESS read-only
    STATUS     current
    DESCRIPTION
    "Reports the smoothed output loudness measurement."
::= { enc1P1357currentOutputLoudnessEntry 1 }

enc1P1358currentOutputPeakTable OBJECT-TYPE
    SYNTAX SEQUENCE OF Enc1P1358currentOutputPeakEntry
    MAX-ACCESS not-accessible
    STATUS     current
    DESCRIPTION
    "
    Name      : Current Output Peak
    Menu Path : /Audio/AAP 1 Configuration/DTS Neural Loudness Ctrl 4
    Units     : dBFS
    Precision : 0
    Low Range : -60
    High Range: 20
    Details   : Reports the output peak measurement.

     NOTE: Precision/Units/Ranges represent the state of the
           parameter during the MIB generation, and does not
           neccessary reflect the current state of the parameter
    "
::= { enc1Params 1358 }

enc1P1358currentOutputPeakEntry OBJECT-TYPE
    SYNTAX Enc1P1358currentOutputPeakEntry
    MAX-ACCESS not-accessible
    STATUS     current
    DESCRIPTION
    "Table Entry for Current Output Peak"
    INDEX { slotId }
::= { enc1P1358currentOutputPeakTable 1 }

Enc1P1358currentOutputPeakEntry ::= SEQUENCE {
    enc1P1358currentOutputPeakValue    INTEGER
}

enc1P1358currentOutputPeakValue OBJECT-TYPE
    SYNTAX     INTEGER
    MAX-ACCESS read-only
    STATUS     current
    DESCRIPTION
    "Reports the output peak measurement."
::= { enc1P1358currentOutputPeakEntry 1 }

enc1P1359currentCorrectionTable OBJECT-TYPE
    SYNTAX SEQUENCE OF Enc1P1359currentCorrectionEntry
    MAX-ACCESS not-accessible
    STATUS     current
    DESCRIPTION
    "
    Name      : Current Correction
    Menu Path : /Audio/AAP 1 Configuration/DTS Neural Loudness Ctrl 4
    Units     : dB
    Precision : 0
    Low Range : -60
    High Range: 60
    Details   : Reports the amount of correction being applied.

     NOTE: Precision/Units/Ranges represent the state of the
           parameter during the MIB generation, and does not
           neccessary reflect the current state of the parameter
    "
::= { enc1Params 1359 }

enc1P1359currentCorrectionEntry OBJECT-TYPE
    SYNTAX Enc1P1359currentCorrectionEntry
    MAX-ACCESS not-accessible
    STATUS     current
    DESCRIPTION
    "Table Entry for Current Correction"
    INDEX { slotId }
::= { enc1P1359currentCorrectionTable 1 }

Enc1P1359currentCorrectionEntry ::= SEQUENCE {
    enc1P1359currentCorrectionValue    INTEGER
}

enc1P1359currentCorrectionValue OBJECT-TYPE
    SYNTAX     INTEGER
    MAX-ACCESS read-only
    STATUS     current
    DESCRIPTION
    "Reports the amount of correction being applied."
::= { enc1P1359currentCorrectionEntry 1 }

enc1P1360currentCompressionTable OBJECT-TYPE
    SYNTAX SEQUENCE OF Enc1P1360currentCompressionEntry
    MAX-ACCESS not-accessible
    STATUS     current
    DESCRIPTION
    "
    Name      : Current Compression
    Menu Path : /Audio/AAP 1 Configuration/DTS Neural Loudness Ctrl 4
    Units     : dB
    Precision : 0
    Low Range : -60
    High Range: 60
    Details   : Reports the amount of compression being applied.

     NOTE: Precision/Units/Ranges represent the state of the
           parameter during the MIB generation, and does not
           neccessary reflect the current state of the parameter
    "
::= { enc1Params 1360 }

enc1P1360currentCompressionEntry OBJECT-TYPE
    SYNTAX Enc1P1360currentCompressionEntry
    MAX-ACCESS not-accessible
    STATUS     current
    DESCRIPTION
    "Table Entry for Current Compression"
    INDEX { slotId }
::= { enc1P1360currentCompressionTable 1 }

Enc1P1360currentCompressionEntry ::= SEQUENCE {
    enc1P1360currentCompressionValue    INTEGER
}

enc1P1360currentCompressionValue OBJECT-TYPE
    SYNTAX     INTEGER
    MAX-ACCESS read-only
    STATUS     current
    DESCRIPTION
    "Reports the amount of compression being applied."
::= { enc1P1360currentCompressionEntry 1 }

enc1P1361dolbyEDecoderStatusTable OBJECT-TYPE
    SYNTAX SEQUENCE OF Enc1P1361dolbyEDecoderStatusEntry
    MAX-ACCESS not-accessible
    STATUS     current
    DESCRIPTION
    "
    Name      : Dolby E Decoder Status
    Menu Path : /Audio/AAP 1 Configuration/Dolby E Decoder
    Details   : Indicates the state of Dolby E decoding.
    "
::= { enc1Params 1361 }

enc1P1361dolbyEDecoderStatusEntry OBJECT-TYPE
    SYNTAX Enc1P1361dolbyEDecoderStatusEntry
    MAX-ACCESS not-accessible
    STATUS     current
    DESCRIPTION
    "Table Entry for Dolby E Decoder Status"
    INDEX { slotId }
::= { enc1P1361dolbyEDecoderStatusTable 1 }

Enc1P1361dolbyEDecoderStatusEntry ::= SEQUENCE {
    enc1P1361dolbyEDecoderStatusValue    Enc1E172enumObj
}

enc1P1361dolbyEDecoderStatusValue OBJECT-TYPE
    SYNTAX     Enc1E172enumObj
    MAX-ACCESS read-only
    STATUS     current
    DESCRIPTION
    "Indicates the state of Dolby E decoding."
::= { enc1P1361dolbyEDecoderStatusEntry 1 }

enc1P1362bitstreamFormatTable OBJECT-TYPE
    SYNTAX SEQUENCE OF Enc1P1362bitstreamFormatEntry
    MAX-ACCESS not-accessible
    STATUS     current
    DESCRIPTION
    "
    Name      : Bitstream Format
    Menu Path : /Audio/AAP 1 Configuration/Dolby E Decoder
    Details   : Indicates the format of the input audio bitstream.
    "
::= { enc1Params 1362 }

enc1P1362bitstreamFormatEntry OBJECT-TYPE
    SYNTAX Enc1P1362bitstreamFormatEntry
    MAX-ACCESS not-accessible
    STATUS     current
    DESCRIPTION
    "Table Entry for Bitstream Format"
    INDEX { slotId }
::= { enc1P1362bitstreamFormatTable 1 }

Enc1P1362bitstreamFormatEntry ::= SEQUENCE {
    enc1P1362bitstreamFormatValue    Enc1E167enumObj
}

enc1P1362bitstreamFormatValue OBJECT-TYPE
    SYNTAX     Enc1E167enumObj
    MAX-ACCESS read-only
    STATUS     current
    DESCRIPTION
    "Indicates the format of the input audio bitstream."
::= { enc1P1362bitstreamFormatEntry 1 }

enc1P1363programSelectTable OBJECT-TYPE
    SYNTAX SEQUENCE OF Enc1P1363programSelectEntry
    MAX-ACCESS not-accessible
    STATUS     current
    DESCRIPTION
    "
    Name      : Program Select
    Menu Path : /Audio/AAP 1 Configuration/Dolby E Decoder
    Details   : Selects the metadata program displayed in the following status.
    "
::= { enc1Params 1363 }

enc1P1363programSelectEntry OBJECT-TYPE
    SYNTAX Enc1P1363programSelectEntry
    MAX-ACCESS not-accessible
    STATUS     current
    DESCRIPTION
    "Table Entry for Program Select"
    INDEX { slotId }
::= { enc1P1363programSelectTable 1 }

Enc1P1363programSelectEntry ::= SEQUENCE {
    enc1P1363programSelectValue    Enc1E177enumObj
}

enc1P1363programSelectValue OBJECT-TYPE
    SYNTAX     Enc1E177enumObj
    MAX-ACCESS read-write
    STATUS     current
    DESCRIPTION
    "Selects the metadata program displayed in the following status."
::= { enc1P1363programSelectEntry 1 }

enc1P1364programConfigTable OBJECT-TYPE
    SYNTAX SEQUENCE OF Enc1P1364programConfigEntry
    MAX-ACCESS not-accessible
    STATUS     current
    DESCRIPTION
    "
    Name      : Program Config
    Menu Path : /Audio/AAP 1 Configuration/Dolby E Decoder
    Details   : Indicates how channels are grouped into programs in this Dolby E encoding.
    "
::= { enc1Params 1364 }

enc1P1364programConfigEntry OBJECT-TYPE
    SYNTAX Enc1P1364programConfigEntry
    MAX-ACCESS not-accessible
    STATUS     current
    DESCRIPTION
    "Table Entry for Program Config"
    INDEX { slotId }
::= { enc1P1364programConfigTable 1 }

Enc1P1364programConfigEntry ::= SEQUENCE {
    enc1P1364programConfigValue    Enc1E170enumObj
}

enc1P1364programConfigValue OBJECT-TYPE
    SYNTAX     Enc1E170enumObj
    MAX-ACCESS read-only
    STATUS     current
    DESCRIPTION
    "Indicates how channels are grouped into programs in this Dolby E encoding."
::= { enc1P1364programConfigEntry 1 }

enc1P1365frameRateTable OBJECT-TYPE
    SYNTAX SEQUENCE OF Enc1P1365frameRateEntry
    MAX-ACCESS not-accessible
    STATUS     current
    DESCRIPTION
    "
    Name      : Frame Rate
    Menu Path : /Audio/AAP 1 Configuration/Dolby E Decoder
    Details   : Indicates the video frame rate associated with this Dolby E encoding.
    "
::= { enc1Params 1365 }

enc1P1365frameRateEntry OBJECT-TYPE
    SYNTAX Enc1P1365frameRateEntry
    MAX-ACCESS not-accessible
    STATUS     current
    DESCRIPTION
    "Table Entry for Frame Rate"
    INDEX { slotId }
::= { enc1P1365frameRateTable 1 }

Enc1P1365frameRateEntry ::= SEQUENCE {
    enc1P1365frameRateValue    Enc1E171enumObj
}

enc1P1365frameRateValue OBJECT-TYPE
    SYNTAX     Enc1E171enumObj
    MAX-ACCESS read-only
    STATUS     current
    DESCRIPTION
    "Indicates the video frame rate associated with this Dolby E encoding."
::= { enc1P1365frameRateEntry 1 }

enc1P1366originalFrameRateTable OBJECT-TYPE
    SYNTAX SEQUENCE OF Enc1P1366originalFrameRateEntry
    MAX-ACCESS not-accessible
    STATUS     current
    DESCRIPTION
    "
    Name      : Original Frame Rate
    Menu Path : /Audio/AAP 1 Configuration/Dolby E Decoder
    Details   : Indicates the original video frame rate associated with this Dolby E encoding.
    "
::= { enc1Params 1366 }

enc1P1366originalFrameRateEntry OBJECT-TYPE
    SYNTAX Enc1P1366originalFrameRateEntry
    MAX-ACCESS not-accessible
    STATUS     current
    DESCRIPTION
    "Table Entry for Original Frame Rate"
    INDEX { slotId }
::= { enc1P1366originalFrameRateTable 1 }

Enc1P1366originalFrameRateEntry ::= SEQUENCE {
    enc1P1366originalFrameRateValue    Enc1E171enumObj
}

enc1P1366originalFrameRateValue OBJECT-TYPE
    SYNTAX     Enc1E171enumObj
    MAX-ACCESS read-only
    STATUS     current
    DESCRIPTION
    "Indicates the original video frame rate associated with this Dolby E encoding."
::= { enc1P1366originalFrameRateEntry 1 }

enc1P1367dataRatekbpsTable OBJECT-TYPE
    SYNTAX SEQUENCE OF Enc1P1367dataRatekbpsEntry
    MAX-ACCESS not-accessible
    STATUS     current
    DESCRIPTION
    "
    Name      : Data Rate (kbps)
    Menu Path : /Audio/AAP 1 Configuration/Dolby E Decoder
    Details   : Indicates the suggested Dolby Digital encoding rate.
    "
::= { enc1Params 1367 }

enc1P1367dataRatekbpsEntry OBJECT-TYPE
    SYNTAX Enc1P1367dataRatekbpsEntry
    MAX-ACCESS not-accessible
    STATUS     current
    DESCRIPTION
    "Table Entry for Data Rate (kbps)"
    INDEX { slotId }
::= { enc1P1367dataRatekbpsTable 1 }

Enc1P1367dataRatekbpsEntry ::= SEQUENCE {
    enc1P1367dataRatekbpsValue    Enc1E151enumObj
}

enc1P1367dataRatekbpsValue OBJECT-TYPE
    SYNTAX     Enc1E151enumObj
    MAX-ACCESS read-only
    STATUS     current
    DESCRIPTION
    "Indicates the suggested Dolby Digital encoding rate."
::= { enc1P1367dataRatekbpsEntry 1 }

enc1P1368bitstreamModeTable OBJECT-TYPE
    SYNTAX SEQUENCE OF Enc1P1368bitstreamModeEntry
    MAX-ACCESS not-accessible
    STATUS     current
    DESCRIPTION
    "
    Name      : Bitstream Mode
    Menu Path : /Audio/AAP 1 Configuration/Dolby E Decoder
    Details   : Describes the audio service contained within the bitstream.
    "
::= { enc1Params 1368 }

enc1P1368bitstreamModeEntry OBJECT-TYPE
    SYNTAX Enc1P1368bitstreamModeEntry
    MAX-ACCESS not-accessible
    STATUS     current
    DESCRIPTION
    "Table Entry for Bitstream Mode"
    INDEX { slotId }
::= { enc1P1368bitstreamModeTable 1 }

Enc1P1368bitstreamModeEntry ::= SEQUENCE {
    enc1P1368bitstreamModeValue    Enc1E157enumObj
}

enc1P1368bitstreamModeValue OBJECT-TYPE
    SYNTAX     Enc1E157enumObj
    MAX-ACCESS read-only
    STATUS     current
    DESCRIPTION
    "Describes the audio service contained within the bitstream."
::= { enc1P1368bitstreamModeEntry 1 }

enc1P1369codingModeTable OBJECT-TYPE
    SYNTAX SEQUENCE OF Enc1P1369codingModeEntry
    MAX-ACCESS not-accessible
    STATUS     current
    DESCRIPTION
    "
    Name      : Coding Mode
    Menu Path : /Audio/AAP 1 Configuration/Dolby E Decoder
    Details   : Indicates the active channels within the encoded bitstream.
    "
::= { enc1Params 1369 }

enc1P1369codingModeEntry OBJECT-TYPE
    SYNTAX Enc1P1369codingModeEntry
    MAX-ACCESS not-accessible
    STATUS     current
    DESCRIPTION
    "Table Entry for Coding Mode"
    INDEX { slotId }
::= { enc1P1369codingModeTable 1 }

Enc1P1369codingModeEntry ::= SEQUENCE {
    enc1P1369codingModeValue    Enc1E153enumObj
}

enc1P1369codingModeValue OBJECT-TYPE
    SYNTAX     Enc1E153enumObj
    MAX-ACCESS read-only
    STATUS     current
    DESCRIPTION
    "Indicates the active channels within the encoded bitstream."
::= { enc1P1369codingModeEntry 1 }

enc1P1370centerMixLevelTable OBJECT-TYPE
    SYNTAX SEQUENCE OF Enc1P1370centerMixLevelEntry
    MAX-ACCESS not-accessible
    STATUS     current
    DESCRIPTION
    "
    Name      : Center Mix Level
    Menu Path : /Audio/AAP 1 Configuration/Dolby E Decoder
    Details   : Nominal level for center channel in a stereo downmix.
    "
::= { enc1Params 1370 }

enc1P1370centerMixLevelEntry OBJECT-TYPE
    SYNTAX Enc1P1370centerMixLevelEntry
    MAX-ACCESS not-accessible
    STATUS     current
    DESCRIPTION
    "Table Entry for Center Mix Level"
    INDEX { slotId }
::= { enc1P1370centerMixLevelTable 1 }

Enc1P1370centerMixLevelEntry ::= SEQUENCE {
    enc1P1370centerMixLevelValue    Enc1E168enumObj
}

enc1P1370centerMixLevelValue OBJECT-TYPE
    SYNTAX     Enc1E168enumObj
    MAX-ACCESS read-only
    STATUS     current
    DESCRIPTION
    "Nominal level for center channel in a stereo downmix."
::= { enc1P1370centerMixLevelEntry 1 }

enc1P1371surroundMixLevelTable OBJECT-TYPE
    SYNTAX SEQUENCE OF Enc1P1371surroundMixLevelEntry
    MAX-ACCESS not-accessible
    STATUS     current
    DESCRIPTION
    "
    Name      : Surround Mix Level
    Menu Path : /Audio/AAP 1 Configuration/Dolby E Decoder
    Details   : Nominal level for surround channel(s) in a stereo downmix.
    "
::= { enc1Params 1371 }

enc1P1371surroundMixLevelEntry OBJECT-TYPE
    SYNTAX Enc1P1371surroundMixLevelEntry
    MAX-ACCESS not-accessible
    STATUS     current
    DESCRIPTION
    "Table Entry for Surround Mix Level"
    INDEX { slotId }
::= { enc1P1371surroundMixLevelTable 1 }

Enc1P1371surroundMixLevelEntry ::= SEQUENCE {
    enc1P1371surroundMixLevelValue    Enc1E169enumObj
}

enc1P1371surroundMixLevelValue OBJECT-TYPE
    SYNTAX     Enc1E169enumObj
    MAX-ACCESS read-only
    STATUS     current
    DESCRIPTION
    "Nominal level for surround channel(s) in a stereo downmix."
::= { enc1P1371surroundMixLevelEntry 1 }

enc1P1372dolbySurroundModeTable OBJECT-TYPE
    SYNTAX SEQUENCE OF Enc1P1372dolbySurroundModeEntry
    MAX-ACCESS not-accessible
    STATUS     current
    DESCRIPTION
    "
    Name      : Dolby Surround Mode
    Menu Path : /Audio/AAP 1 Configuration/Dolby E Decoder
    Details   : Indicates whether this is a 2 channel Dolby Surround encoding intended for a Dolby Pro Logic decoder.
    "
::= { enc1Params 1372 }

enc1P1372dolbySurroundModeEntry OBJECT-TYPE
    SYNTAX Enc1P1372dolbySurroundModeEntry
    MAX-ACCESS not-accessible
    STATUS     current
    DESCRIPTION
    "Table Entry for Dolby Surround Mode"
    INDEX { slotId }
::= { enc1P1372dolbySurroundModeTable 1 }

Enc1P1372dolbySurroundModeEntry ::= SEQUENCE {
    enc1P1372dolbySurroundModeValue    Enc1E158enumObj
}

enc1P1372dolbySurroundModeValue OBJECT-TYPE
    SYNTAX     Enc1E158enumObj
    MAX-ACCESS read-only
    STATUS     current
    DESCRIPTION
    "Indicates whether this is a 2 channel Dolby Surround encoding intended for a Dolby Pro Logic decoder."
::= { enc1P1372dolbySurroundModeEntry 1 }

enc1P1373lfechannelTable OBJECT-TYPE
    SYNTAX SEQUENCE OF Enc1P1373lfechannelEntry
    MAX-ACCESS not-accessible
    STATUS     current
    DESCRIPTION
    "
    Name      : LFE Channel
    Menu Path : /Audio/AAP 1 Configuration/Dolby E Decoder
    Details   : Indicates whether a Low Frequency Effects channel is present.
    "
::= { enc1Params 1373 }

enc1P1373lfechannelEntry OBJECT-TYPE
    SYNTAX Enc1P1373lfechannelEntry
    MAX-ACCESS not-accessible
    STATUS     current
    DESCRIPTION
    "Table Entry for LFE Channel"
    INDEX { slotId }
::= { enc1P1373lfechannelTable 1 }

Enc1P1373lfechannelEntry ::= SEQUENCE {
    enc1P1373lfechannelValue    Enc1E154enumObj
}

enc1P1373lfechannelValue OBJECT-TYPE
    SYNTAX     Enc1E154enumObj
    MAX-ACCESS read-only
    STATUS     current
    DESCRIPTION
    "Indicates whether a Low Frequency Effects channel is present."
::= { enc1P1373lfechannelEntry 1 }

enc1P1374dialogueNormalizationTable OBJECT-TYPE
    SYNTAX SEQUENCE OF Enc1P1374dialogueNormalizationEntry
    MAX-ACCESS not-accessible
    STATUS     current
    DESCRIPTION
    "
    Name      : Dialogue Normalization
    Menu Path : /Audio/AAP 1 Configuration/Dolby E Decoder
    Units     : dBFS
    Precision : 0
    Low Range : -31
    High Range: 0
    Details   : Specifies the long-term A-weighted average level of dialogue, Leq(A), equivalent to dBEq/LKFS.

     NOTE: Precision/Units/Ranges represent the state of the
           parameter during the MIB generation, and does not
           neccessary reflect the current state of the parameter
    "
::= { enc1Params 1374 }

enc1P1374dialogueNormalizationEntry OBJECT-TYPE
    SYNTAX Enc1P1374dialogueNormalizationEntry
    MAX-ACCESS not-accessible
    STATUS     current
    DESCRIPTION
    "Table Entry for Dialogue Normalization"
    INDEX { slotId }
::= { enc1P1374dialogueNormalizationTable 1 }

Enc1P1374dialogueNormalizationEntry ::= SEQUENCE {
    enc1P1374dialogueNormalizationValue    INTEGER
}

enc1P1374dialogueNormalizationValue OBJECT-TYPE
    SYNTAX     INTEGER
    MAX-ACCESS read-only
    STATUS     current
    DESCRIPTION
    "Specifies the long-term A-weighted average level of dialogue, Leq(A), equivalent to dBEq/LKFS."
::= { enc1P1374dialogueNormalizationEntry 1 }

enc1P1375audioProductionInfoTable OBJECT-TYPE
    SYNTAX SEQUENCE OF Enc1P1375audioProductionInfoEntry
    MAX-ACCESS not-accessible
    STATUS     current
    DESCRIPTION
    "
    Name      : Audio Production Info
    Menu Path : /Audio/AAP 1 Configuration/Dolby E Decoder
    Details   : Indicates if audio production parameters (Mix Level and Room Type) are specified.
    "
::= { enc1Params 1375 }

enc1P1375audioProductionInfoEntry OBJECT-TYPE
    SYNTAX Enc1P1375audioProductionInfoEntry
    MAX-ACCESS not-accessible
    STATUS     current
    DESCRIPTION
    "Table Entry for Audio Production Info"
    INDEX { slotId }
::= { enc1P1375audioProductionInfoTable 1 }

Enc1P1375audioProductionInfoEntry ::= SEQUENCE {
    enc1P1375audioProductionInfoValue    Enc1E156enumObj
}

enc1P1375audioProductionInfoValue OBJECT-TYPE
    SYNTAX     Enc1E156enumObj
    MAX-ACCESS read-only
    STATUS     current
    DESCRIPTION
    "Indicates if audio production parameters (Mix Level and Room Type) are specified."
::= { enc1P1375audioProductionInfoEntry 1 }

enc1P1376mixLevelTable OBJECT-TYPE
    SYNTAX SEQUENCE OF Enc1P1376mixLevelEntry
    MAX-ACCESS not-accessible
    STATUS     current
    DESCRIPTION
    "
    Name      : Mix Level
    Menu Path : /Audio/AAP 1 Configuration/Dolby E Decoder
    Units     : dB SPL
    Precision : 0
    Low Range : 80
    High Range: 111
    Details   : Specifies the peak sound pressure level (SPL) used during final audio mixing.

     NOTE: Precision/Units/Ranges represent the state of the
           parameter during the MIB generation, and does not
           neccessary reflect the current state of the parameter
    "
::= { enc1Params 1376 }

enc1P1376mixLevelEntry OBJECT-TYPE
    SYNTAX Enc1P1376mixLevelEntry
    MAX-ACCESS not-accessible
    STATUS     current
    DESCRIPTION
    "Table Entry for Mix Level"
    INDEX { slotId }
::= { enc1P1376mixLevelTable 1 }

Enc1P1376mixLevelEntry ::= SEQUENCE {
    enc1P1376mixLevelValue    INTEGER
}

enc1P1376mixLevelValue OBJECT-TYPE
    SYNTAX     INTEGER
    MAX-ACCESS read-only
    STATUS     current
    DESCRIPTION
    "Specifies the peak sound pressure level (SPL) used during final audio mixing."
::= { enc1P1376mixLevelEntry 1 }

enc1P1377roomTypeTable OBJECT-TYPE
    SYNTAX SEQUENCE OF Enc1P1377roomTypeEntry
    MAX-ACCESS not-accessible
    STATUS     current
    DESCRIPTION
    "
    Name      : Room Type
    Menu Path : /Audio/AAP 1 Configuration/Dolby E Decoder
    Details   : Describes equalization used during the final mixing. Large is X-curve, small is flat.
    "
::= { enc1Params 1377 }

enc1P1377roomTypeEntry OBJECT-TYPE
    SYNTAX Enc1P1377roomTypeEntry
    MAX-ACCESS not-accessible
    STATUS     current
    DESCRIPTION
    "Table Entry for Room Type"
    INDEX { slotId }
::= { enc1P1377roomTypeTable 1 }

Enc1P1377roomTypeEntry ::= SEQUENCE {
    enc1P1377roomTypeValue    Enc1E164enumObj
}

enc1P1377roomTypeValue OBJECT-TYPE
    SYNTAX     Enc1E164enumObj
    MAX-ACCESS read-only
    STATUS     current
    DESCRIPTION
    "Describes equalization used during the final mixing. Large is X-curve, small is flat."
::= { enc1P1377roomTypeEntry 1 }

enc1P1378copyrightProtectedTable OBJECT-TYPE
    SYNTAX SEQUENCE OF Enc1P1378copyrightProtectedEntry
    MAX-ACCESS not-accessible
    STATUS     current
    DESCRIPTION
    "
    Name      : Copyright Protected
    Menu Path : /Audio/AAP 1 Configuration/Dolby E Decoder
    Details   : Indicates whether the source material is copyright protected.
    "
::= { enc1Params 1378 }

enc1P1378copyrightProtectedEntry OBJECT-TYPE
    SYNTAX Enc1P1378copyrightProtectedEntry
    MAX-ACCESS not-accessible
    STATUS     current
    DESCRIPTION
    "Table Entry for Copyright Protected"
    INDEX { slotId }
::= { enc1P1378copyrightProtectedTable 1 }

Enc1P1378copyrightProtectedEntry ::= SEQUENCE {
    enc1P1378copyrightProtectedValue    Enc1E156enumObj
}

enc1P1378copyrightProtectedValue OBJECT-TYPE
    SYNTAX     Enc1E156enumObj
    MAX-ACCESS read-only
    STATUS     current
    DESCRIPTION
    "Indicates whether the source material is copyright protected."
::= { enc1P1378copyrightProtectedEntry 1 }

enc1P1379originalBitstreamTable OBJECT-TYPE
    SYNTAX SEQUENCE OF Enc1P1379originalBitstreamEntry
    MAX-ACCESS not-accessible
    STATUS     current
    DESCRIPTION
    "
    Name      : Original Bitstream
    Menu Path : /Audio/AAP 1 Configuration/Dolby E Decoder
    Details   : Indicates whether the source material is the master version or a copy.
    "
::= { enc1Params 1379 }

enc1P1379originalBitstreamEntry OBJECT-TYPE
    SYNTAX Enc1P1379originalBitstreamEntry
    MAX-ACCESS not-accessible
    STATUS     current
    DESCRIPTION
    "Table Entry for Original Bitstream"
    INDEX { slotId }
::= { enc1P1379originalBitstreamTable 1 }

Enc1P1379originalBitstreamEntry ::= SEQUENCE {
    enc1P1379originalBitstreamValue    Enc1E156enumObj
}

enc1P1379originalBitstreamValue OBJECT-TYPE
    SYNTAX     Enc1E156enumObj
    MAX-ACCESS read-only
    STATUS     current
    DESCRIPTION
    "Indicates whether the source material is the master version or a copy."
::= { enc1P1379originalBitstreamEntry 1 }

enc1P1380extBSIValidTable OBJECT-TYPE
    SYNTAX SEQUENCE OF Enc1P1380extBSIValidEntry
    MAX-ACCESS not-accessible
    STATUS     current
    DESCRIPTION
    "
    Name      : Ext BSI Valid
    Menu Path : /Audio/AAP 1 Configuration/Dolby E Decoder
    Details   : Indicates whether or not extended BSI metadata is present.
    "
::= { enc1Params 1380 }

enc1P1380extBSIValidEntry OBJECT-TYPE
    SYNTAX Enc1P1380extBSIValidEntry
    MAX-ACCESS not-accessible
    STATUS     current
    DESCRIPTION
    "Table Entry for Ext BSI Valid"
    INDEX { slotId }
::= { enc1P1380extBSIValidTable 1 }

Enc1P1380extBSIValidEntry ::= SEQUENCE {
    enc1P1380extBSIValidValue    Enc1E156enumObj
}

enc1P1380extBSIValidValue OBJECT-TYPE
    SYNTAX     Enc1E156enumObj
    MAX-ACCESS read-only
    STATUS     current
    DESCRIPTION
    "Indicates whether or not extended BSI metadata is present."
::= { enc1P1380extBSIValidEntry 1 }

enc1P1381extPreferredStereoDownmixTable OBJECT-TYPE
    SYNTAX SEQUENCE OF Enc1P1381extPreferredStereoDownmixEntry
    MAX-ACCESS not-accessible
    STATUS     current
    DESCRIPTION
    "
    Name      : Ext: Preferred Stereo Downmix
    Menu Path : /Audio/AAP 1 Configuration/Dolby E Decoder
    Details   : Indicates the preferred downmix.
    "
::= { enc1Params 1381 }

enc1P1381extPreferredStereoDownmixEntry OBJECT-TYPE
    SYNTAX Enc1P1381extPreferredStereoDownmixEntry
    MAX-ACCESS not-accessible
    STATUS     current
    DESCRIPTION
    "Table Entry for Ext: Preferred Stereo Downmix"
    INDEX { slotId }
::= { enc1P1381extPreferredStereoDownmixTable 1 }

Enc1P1381extPreferredStereoDownmixEntry ::= SEQUENCE {
    enc1P1381extPreferredStereoDownmixValue    Enc1E160enumObj
}

enc1P1381extPreferredStereoDownmixValue OBJECT-TYPE
    SYNTAX     Enc1E160enumObj
    MAX-ACCESS read-only
    STATUS     current
    DESCRIPTION
    "Indicates the preferred downmix."
::= { enc1P1381extPreferredStereoDownmixEntry 1 }

enc1P1382extLtRtCenterMixLevelTable OBJECT-TYPE
    SYNTAX SEQUENCE OF Enc1P1382extLtRtCenterMixLevelEntry
    MAX-ACCESS not-accessible
    STATUS     current
    DESCRIPTION
    "
    Name      : Ext: LtRt Center Mix Level
    Menu Path : /Audio/AAP 1 Configuration/Dolby E Decoder
    Details   : Indicates the level shift applied to the center channel during an Lt/Rt downmix.
    "
::= { enc1Params 1382 }

enc1P1382extLtRtCenterMixLevelEntry OBJECT-TYPE
    SYNTAX Enc1P1382extLtRtCenterMixLevelEntry
    MAX-ACCESS not-accessible
    STATUS     current
    DESCRIPTION
    "Table Entry for Ext: LtRt Center Mix Level"
    INDEX { slotId }
::= { enc1P1382extLtRtCenterMixLevelTable 1 }

Enc1P1382extLtRtCenterMixLevelEntry ::= SEQUENCE {
    enc1P1382extLtRtCenterMixLevelValue    Enc1E161enumObj
}

enc1P1382extLtRtCenterMixLevelValue OBJECT-TYPE
    SYNTAX     Enc1E161enumObj
    MAX-ACCESS read-only
    STATUS     current
    DESCRIPTION
    "Indicates the level shift applied to the center channel during an Lt/Rt downmix."
::= { enc1P1382extLtRtCenterMixLevelEntry 1 }

enc1P1383extLtRtSurroundMixLevelTable OBJECT-TYPE
    SYNTAX SEQUENCE OF Enc1P1383extLtRtSurroundMixLevelEntry
    MAX-ACCESS not-accessible
    STATUS     current
    DESCRIPTION
    "
    Name      : Ext: LtRt Surround Mix Level
    Menu Path : /Audio/AAP 1 Configuration/Dolby E Decoder
    Details   : Indicates the level shift applied to the surround channel(s) during an Lt/Rt downmix.
    "
::= { enc1Params 1383 }

enc1P1383extLtRtSurroundMixLevelEntry OBJECT-TYPE
    SYNTAX Enc1P1383extLtRtSurroundMixLevelEntry
    MAX-ACCESS not-accessible
    STATUS     current
    DESCRIPTION
    "Table Entry for Ext: LtRt Surround Mix Level"
    INDEX { slotId }
::= { enc1P1383extLtRtSurroundMixLevelTable 1 }

Enc1P1383extLtRtSurroundMixLevelEntry ::= SEQUENCE {
    enc1P1383extLtRtSurroundMixLevelValue    Enc1E162enumObj
}

enc1P1383extLtRtSurroundMixLevelValue OBJECT-TYPE
    SYNTAX     Enc1E162enumObj
    MAX-ACCESS read-only
    STATUS     current
    DESCRIPTION
    "Indicates the level shift applied to the surround channel(s) during an Lt/Rt downmix."
::= { enc1P1383extLtRtSurroundMixLevelEntry 1 }

enc1P1384extLoRoCenterMixLevelTable OBJECT-TYPE
    SYNTAX SEQUENCE OF Enc1P1384extLoRoCenterMixLevelEntry
    MAX-ACCESS not-accessible
    STATUS     current
    DESCRIPTION
    "
    Name      : Ext: LoRo Center Mix Level
    Menu Path : /Audio/AAP 1 Configuration/Dolby E Decoder
    Details   : Indicates the level shift applied to the center channel during an Lo/Ro downmix.
    "
::= { enc1Params 1384 }

enc1P1384extLoRoCenterMixLevelEntry OBJECT-TYPE
    SYNTAX Enc1P1384extLoRoCenterMixLevelEntry
    MAX-ACCESS not-accessible
    STATUS     current
    DESCRIPTION
    "Table Entry for Ext: LoRo Center Mix Level"
    INDEX { slotId }
::= { enc1P1384extLoRoCenterMixLevelTable 1 }

Enc1P1384extLoRoCenterMixLevelEntry ::= SEQUENCE {
    enc1P1384extLoRoCenterMixLevelValue    Enc1E161enumObj
}

enc1P1384extLoRoCenterMixLevelValue OBJECT-TYPE
    SYNTAX     Enc1E161enumObj
    MAX-ACCESS read-only
    STATUS     current
    DESCRIPTION
    "Indicates the level shift applied to the center channel during an Lo/Ro downmix."
::= { enc1P1384extLoRoCenterMixLevelEntry 1 }

enc1P1385extLoRoSurroundMixLevelTable OBJECT-TYPE
    SYNTAX SEQUENCE OF Enc1P1385extLoRoSurroundMixLevelEntry
    MAX-ACCESS not-accessible
    STATUS     current
    DESCRIPTION
    "
    Name      : Ext: LoRo Surround Mix Level
    Menu Path : /Audio/AAP 1 Configuration/Dolby E Decoder
    Details   : Indicates the level shift applied to the surround channel(s) during an Lo/Ro downmix.
    "
::= { enc1Params 1385 }

enc1P1385extLoRoSurroundMixLevelEntry OBJECT-TYPE
    SYNTAX Enc1P1385extLoRoSurroundMixLevelEntry
    MAX-ACCESS not-accessible
    STATUS     current
    DESCRIPTION
    "Table Entry for Ext: LoRo Surround Mix Level"
    INDEX { slotId }
::= { enc1P1385extLoRoSurroundMixLevelTable 1 }

Enc1P1385extLoRoSurroundMixLevelEntry ::= SEQUENCE {
    enc1P1385extLoRoSurroundMixLevelValue    Enc1E162enumObj
}

enc1P1385extLoRoSurroundMixLevelValue OBJECT-TYPE
    SYNTAX     Enc1E162enumObj
    MAX-ACCESS read-only
    STATUS     current
    DESCRIPTION
    "Indicates the level shift applied to the surround channel(s) during an Lo/Ro downmix."
::= { enc1P1385extLoRoSurroundMixLevelEntry 1 }

enc1P1386extDolbyDigitalSurroundEXModeTable OBJECT-TYPE
    SYNTAX SEQUENCE OF Enc1P1386extDolbyDigitalSurroundEXModeEntry
    MAX-ACCESS not-accessible
    STATUS     current
    DESCRIPTION
    "
    Name      : Ext: Dolby Digital Surround EX Mode
    Menu Path : /Audio/AAP 1 Configuration/Dolby E Decoder
    Details   : Indicates whether the source material is a 5.1 channel Dolby Digital Surround EX encoding.
    "
::= { enc1Params 1386 }

enc1P1386extDolbyDigitalSurroundEXModeEntry OBJECT-TYPE
    SYNTAX Enc1P1386extDolbyDigitalSurroundEXModeEntry
    MAX-ACCESS not-accessible
    STATUS     current
    DESCRIPTION
    "Table Entry for Ext: Dolby Digital Surround EX Mode"
    INDEX { slotId }
::= { enc1P1386extDolbyDigitalSurroundEXModeTable 1 }

Enc1P1386extDolbyDigitalSurroundEXModeEntry ::= SEQUENCE {
    enc1P1386extDolbyDigitalSurroundEXModeValue    Enc1E159enumObj
}

enc1P1386extDolbyDigitalSurroundEXModeValue OBJECT-TYPE
    SYNTAX     Enc1E159enumObj
    MAX-ACCESS read-only
    STATUS     current
    DESCRIPTION
    "Indicates whether the source material is a 5.1 channel Dolby Digital Surround EX encoding."
::= { enc1P1386extDolbyDigitalSurroundEXModeEntry 1 }

enc1P1387extA-to-DTypeTable OBJECT-TYPE
    SYNTAX SEQUENCE OF Enc1P1387extA-to-DTypeEntry
    MAX-ACCESS not-accessible
    STATUS     current
    DESCRIPTION
    "
    Name      : Ext: A-to-D Type
    Menu Path : /Audio/AAP 1 Configuration/Dolby E Decoder
    Details   : Indicates the type of A/D converter used to capture the program.
    "
::= { enc1Params 1387 }

enc1P1387extA-to-DTypeEntry OBJECT-TYPE
    SYNTAX Enc1P1387extA-to-DTypeEntry
    MAX-ACCESS not-accessible
    STATUS     current
    DESCRIPTION
    "Table Entry for Ext: A-to-D Type"
    INDEX { slotId }
::= { enc1P1387extA-to-DTypeTable 1 }

Enc1P1387extA-to-DTypeEntry ::= SEQUENCE {
    enc1P1387extA-to-DTypeValue    Enc1E163enumObj
}

enc1P1387extA-to-DTypeValue OBJECT-TYPE
    SYNTAX     Enc1E163enumObj
    MAX-ACCESS read-only
    STATUS     current
    DESCRIPTION
    "Indicates the type of A/D converter used to capture the program."
::= { enc1P1387extA-to-DTypeEntry 1 }

enc1P1388dchigh-PassFilterTable OBJECT-TYPE
    SYNTAX SEQUENCE OF Enc1P1388dchigh-PassFilterEntry
    MAX-ACCESS not-accessible
    STATUS     current
    DESCRIPTION
    "
    Name      : DC High-Pass Filter
    Menu Path : /Audio/AAP 1 Configuration/Dolby E Decoder
    Details   : Indicates that a DC-blocking 3 Hz high-pass filter should be applied.
    "
::= { enc1Params 1388 }

enc1P1388dchigh-PassFilterEntry OBJECT-TYPE
    SYNTAX Enc1P1388dchigh-PassFilterEntry
    MAX-ACCESS not-accessible
    STATUS     current
    DESCRIPTION
    "Table Entry for DC High-Pass Filter"
    INDEX { slotId }
::= { enc1P1388dchigh-PassFilterTable 1 }

Enc1P1388dchigh-PassFilterEntry ::= SEQUENCE {
    enc1P1388dchigh-PassFilterValue    Enc1E152enumObj
}

enc1P1388dchigh-PassFilterValue OBJECT-TYPE
    SYNTAX     Enc1E152enumObj
    MAX-ACCESS read-only
    STATUS     current
    DESCRIPTION
    "Indicates that a DC-blocking 3 Hz high-pass filter should be applied."
::= { enc1P1388dchigh-PassFilterEntry 1 }

enc1P1389low-PassFilterTable OBJECT-TYPE
    SYNTAX SEQUENCE OF Enc1P1389low-PassFilterEntry
    MAX-ACCESS not-accessible
    STATUS     current
    DESCRIPTION
    "
    Name      : Low-Pass Filter
    Menu Path : /Audio/AAP 1 Configuration/Dolby E Decoder
    Details   : Indicates that a low-pass filter to remove unencoded frequencies should be applied.
    "
::= { enc1Params 1389 }

enc1P1389low-PassFilterEntry OBJECT-TYPE
    SYNTAX Enc1P1389low-PassFilterEntry
    MAX-ACCESS not-accessible
    STATUS     current
    DESCRIPTION
    "Table Entry for Low-Pass Filter"
    INDEX { slotId }
::= { enc1P1389low-PassFilterTable 1 }

Enc1P1389low-PassFilterEntry ::= SEQUENCE {
    enc1P1389low-PassFilterValue    Enc1E152enumObj
}

enc1P1389low-PassFilterValue OBJECT-TYPE
    SYNTAX     Enc1E152enumObj
    MAX-ACCESS read-only
    STATUS     current
    DESCRIPTION
    "Indicates that a low-pass filter to remove unencoded frequencies should be applied."
::= { enc1P1389low-PassFilterEntry 1 }

enc1P1390lfelow-PassFilterTable OBJECT-TYPE
    SYNTAX SEQUENCE OF Enc1P1390lfelow-PassFilterEntry
    MAX-ACCESS not-accessible
    STATUS     current
    DESCRIPTION
    "
    Name      : LFE Low-Pass Filter
    Menu Path : /Audio/AAP 1 Configuration/Dolby E Decoder
    Details   : Indicates that a 120 Hz low-pass filter should be applied to the LFE channel.
    "
::= { enc1Params 1390 }

enc1P1390lfelow-PassFilterEntry OBJECT-TYPE
    SYNTAX Enc1P1390lfelow-PassFilterEntry
    MAX-ACCESS not-accessible
    STATUS     current
    DESCRIPTION
    "Table Entry for LFE Low-Pass Filter"
    INDEX { slotId }
::= { enc1P1390lfelow-PassFilterTable 1 }

Enc1P1390lfelow-PassFilterEntry ::= SEQUENCE {
    enc1P1390lfelow-PassFilterValue    Enc1E152enumObj
}

enc1P1390lfelow-PassFilterValue OBJECT-TYPE
    SYNTAX     Enc1E152enumObj
    MAX-ACCESS read-only
    STATUS     current
    DESCRIPTION
    "Indicates that a 120 Hz low-pass filter should be applied to the LFE channel."
::= { enc1P1390lfelow-PassFilterEntry 1 }

enc1P1391surroundChannelPhaseShiftTable OBJECT-TYPE
    SYNTAX SEQUENCE OF Enc1P1391surroundChannelPhaseShiftEntry
    MAX-ACCESS not-accessible
    STATUS     current
    DESCRIPTION
    "
    Name      : Surround Channel Phase Shift
    Menu Path : /Audio/AAP 1 Configuration/Dolby E Decoder
    Details   : Indicates if a 90-degree phase shift should be applied to the surround channel(s).
    "
::= { enc1Params 1391 }

enc1P1391surroundChannelPhaseShiftEntry OBJECT-TYPE
    SYNTAX Enc1P1391surroundChannelPhaseShiftEntry
    MAX-ACCESS not-accessible
    STATUS     current
    DESCRIPTION
    "Table Entry for Surround Channel Phase Shift"
    INDEX { slotId }
::= { enc1P1391surroundChannelPhaseShiftTable 1 }

Enc1P1391surroundChannelPhaseShiftEntry ::= SEQUENCE {
    enc1P1391surroundChannelPhaseShiftValue    Enc1E152enumObj
}

enc1P1391surroundChannelPhaseShiftValue OBJECT-TYPE
    SYNTAX     Enc1E152enumObj
    MAX-ACCESS read-only
    STATUS     current
    DESCRIPTION
    "Indicates if a 90-degree phase shift should be applied to the surround channel(s)."
::= { enc1P1391surroundChannelPhaseShiftEntry 1 }

enc1P1392surroundChannelAttenuationTable OBJECT-TYPE
    SYNTAX SEQUENCE OF Enc1P1392surroundChannelAttenuationEntry
    MAX-ACCESS not-accessible
    STATUS     current
    DESCRIPTION
    "
    Name      : Surround Channel Attenuation
    Menu Path : /Audio/AAP 1 Configuration/Dolby E Decoder
    Details   : Indicates if 3dB of additional attenuation should be applied to the surround channel(s).
    "
::= { enc1Params 1392 }

enc1P1392surroundChannelAttenuationEntry OBJECT-TYPE
    SYNTAX Enc1P1392surroundChannelAttenuationEntry
    MAX-ACCESS not-accessible
    STATUS     current
    DESCRIPTION
    "Table Entry for Surround Channel Attenuation"
    INDEX { slotId }
::= { enc1P1392surroundChannelAttenuationTable 1 }

Enc1P1392surroundChannelAttenuationEntry ::= SEQUENCE {
    enc1P1392surroundChannelAttenuationValue    Enc1E152enumObj
}

enc1P1392surroundChannelAttenuationValue OBJECT-TYPE
    SYNTAX     Enc1E152enumObj
    MAX-ACCESS read-only
    STATUS     current
    DESCRIPTION
    "Indicates if 3dB of additional attenuation should be applied to the surround channel(s)."
::= { enc1P1392surroundChannelAttenuationEntry 1 }

enc1P1393rfmodeDynamicRangeProfileTable OBJECT-TYPE
    SYNTAX SEQUENCE OF Enc1P1393rfmodeDynamicRangeProfileEntry
    MAX-ACCESS not-accessible
    STATUS     current
    DESCRIPTION
    "
    Name      : RF Mode Dynamic Range Profile
    Menu Path : /Audio/AAP 1 Configuration/Dolby E Decoder
    Details   : Specifies the dynamic range compression profile for RF output at the decoder (analog TV signal).
    "
::= { enc1Params 1393 }

enc1P1393rfmodeDynamicRangeProfileEntry OBJECT-TYPE
    SYNTAX Enc1P1393rfmodeDynamicRangeProfileEntry
    MAX-ACCESS not-accessible
    STATUS     current
    DESCRIPTION
    "Table Entry for RF Mode Dynamic Range Profile"
    INDEX { slotId }
::= { enc1P1393rfmodeDynamicRangeProfileTable 1 }

Enc1P1393rfmodeDynamicRangeProfileEntry ::= SEQUENCE {
    enc1P1393rfmodeDynamicRangeProfileValue    Enc1E155enumObj
}

enc1P1393rfmodeDynamicRangeProfileValue OBJECT-TYPE
    SYNTAX     Enc1E155enumObj
    MAX-ACCESS read-only
    STATUS     current
    DESCRIPTION
    "Specifies the dynamic range compression profile for RF output at the decoder (analog TV signal)."
::= { enc1P1393rfmodeDynamicRangeProfileEntry 1 }

enc1P1394lineModeDynamicRangeProfileTable OBJECT-TYPE
    SYNTAX SEQUENCE OF Enc1P1394lineModeDynamicRangeProfileEntry
    MAX-ACCESS not-accessible
    STATUS     current
    DESCRIPTION
    "
    Name      : Line Mode Dynamic Range Profile
    Menu Path : /Audio/AAP 1 Configuration/Dolby E Decoder
    Details   : Specifies the dynamic range compression profile for line output at the decoder.
    "
::= { enc1Params 1394 }

enc1P1394lineModeDynamicRangeProfileEntry OBJECT-TYPE
    SYNTAX Enc1P1394lineModeDynamicRangeProfileEntry
    MAX-ACCESS not-accessible
    STATUS     current
    DESCRIPTION
    "Table Entry for Line Mode Dynamic Range Profile"
    INDEX { slotId }
::= { enc1P1394lineModeDynamicRangeProfileTable 1 }

Enc1P1394lineModeDynamicRangeProfileEntry ::= SEQUENCE {
    enc1P1394lineModeDynamicRangeProfileValue    Enc1E155enumObj
}

enc1P1394lineModeDynamicRangeProfileValue OBJECT-TYPE
    SYNTAX     Enc1E155enumObj
    MAX-ACCESS read-only
    STATUS     current
    DESCRIPTION
    "Specifies the dynamic range compression profile for line output at the decoder."
::= { enc1P1394lineModeDynamicRangeProfileEntry 1 }

enc1P1395dtsneuralTotalTable OBJECT-TYPE
    SYNTAX SEQUENCE OF Enc1P1395dtsneuralTotalEntry
    MAX-ACCESS not-accessible
    STATUS     current
    DESCRIPTION
    "
    Name      : DTS Neural, Total
    Menu Path : Not Applicable
    Units     : 
    Precision : 0
    Low Range : 0
    High Range: 32
    Details   : Display the total credits purchased for DTS Neural functions

     NOTE: Precision/Units/Ranges represent the state of the
           parameter during the MIB generation, and does not
           neccessary reflect the current state of the parameter
    "
::= { enc1Params 1395 }

enc1P1395dtsneuralTotalEntry OBJECT-TYPE
    SYNTAX Enc1P1395dtsneuralTotalEntry
    MAX-ACCESS not-accessible
    STATUS     current
    DESCRIPTION
    "Table Entry for DTS Neural, Total"
    INDEX { slotId }
::= { enc1P1395dtsneuralTotalTable 1 }

Enc1P1395dtsneuralTotalEntry ::= SEQUENCE {
    enc1P1395dtsneuralTotalValue    INTEGER
}

enc1P1395dtsneuralTotalValue OBJECT-TYPE
    SYNTAX     INTEGER
    MAX-ACCESS read-only
    STATUS     current
    DESCRIPTION
    "Display the total credits purchased for DTS Neural functions"
::= { enc1P1395dtsneuralTotalEntry 1 }

enc1P1396dtsneuralRemainingTable OBJECT-TYPE
    SYNTAX SEQUENCE OF Enc1P1396dtsneuralRemainingEntry
    MAX-ACCESS not-accessible
    STATUS     current
    DESCRIPTION
    "
    Name      : DTS Neural, Remaining
    Menu Path : Not Applicable
    Units     : 
    Precision : 0
    Low Range : 0
    High Range: 32
    Details   : Display the credits remaining for DTS Neural functions

     NOTE: Precision/Units/Ranges represent the state of the
           parameter during the MIB generation, and does not
           neccessary reflect the current state of the parameter
    "
::= { enc1Params 1396 }

enc1P1396dtsneuralRemainingEntry OBJECT-TYPE
    SYNTAX Enc1P1396dtsneuralRemainingEntry
    MAX-ACCESS not-accessible
    STATUS     current
    DESCRIPTION
    "Table Entry for DTS Neural, Remaining"
    INDEX { slotId }
::= { enc1P1396dtsneuralRemainingTable 1 }

Enc1P1396dtsneuralRemainingEntry ::= SEQUENCE {
    enc1P1396dtsneuralRemainingValue    INTEGER
}

enc1P1396dtsneuralRemainingValue OBJECT-TYPE
    SYNTAX     INTEGER
    MAX-ACCESS read-only
    STATUS     current
    DESCRIPTION
    "Display the credits remaining for DTS Neural functions"
::= { enc1P1396dtsneuralRemainingEntry 1 }

enc1P1397costDolbyEEncoderDEETable OBJECT-TYPE
    SYNTAX SEQUENCE OF Enc1P1397costDolbyEEncoderDEEEntry
    MAX-ACCESS not-accessible
    STATUS     current
    DESCRIPTION
    "
    Name      : Cost, Dolby E Encoder (DEE)
    Menu Path : Not Applicable
    Details   : Reports number of Dolby E encoder license required for the selected function
    "
::= { enc1Params 1397 }

enc1P1397costDolbyEEncoderDEEEntry OBJECT-TYPE
    SYNTAX Enc1P1397costDolbyEEncoderDEEEntry
    MAX-ACCESS not-accessible
    STATUS     current
    DESCRIPTION
    "Table Entry for Cost, Dolby E Encoder (DEE)"
    INDEX { slotId }
::= { enc1P1397costDolbyEEncoderDEETable 1 }

Enc1P1397costDolbyEEncoderDEEEntry ::= SEQUENCE {
    enc1P1397costDolbyEEncoderDEEValue    Enc1E145enumObj
}

enc1P1397costDolbyEEncoderDEEValue OBJECT-TYPE
    SYNTAX     Enc1E145enumObj
    MAX-ACCESS read-only
    STATUS     current
    DESCRIPTION
    "Reports number of Dolby E encoder license required for the selected function"
::= { enc1P1397costDolbyEEncoderDEEEntry 1 }

enc1P1398costDolbyDigitalEncoderDDETable OBJECT-TYPE
    SYNTAX SEQUENCE OF Enc1P1398costDolbyDigitalEncoderDDEEntry
    MAX-ACCESS not-accessible
    STATUS     current
    DESCRIPTION
    "
    Name      : Cost, Dolby Digital Encoder (DDE)
    Menu Path : Not Applicable
    Details   : Reports number of Dolby Digital encoder licensed required for the selected function
    "
::= { enc1Params 1398 }

enc1P1398costDolbyDigitalEncoderDDEEntry OBJECT-TYPE
    SYNTAX Enc1P1398costDolbyDigitalEncoderDDEEntry
    MAX-ACCESS not-accessible
    STATUS     current
    DESCRIPTION
    "Table Entry for Cost, Dolby Digital Encoder (DDE)"
    INDEX { slotId }
::= { enc1P1398costDolbyDigitalEncoderDDETable 1 }

Enc1P1398costDolbyDigitalEncoderDDEEntry ::= SEQUENCE {
    enc1P1398costDolbyDigitalEncoderDDEValue    Enc1E147enumObj
}

enc1P1398costDolbyDigitalEncoderDDEValue OBJECT-TYPE
    SYNTAX     Enc1E147enumObj
    MAX-ACCESS read-only
    STATUS     current
    DESCRIPTION
    "Reports number of Dolby Digital encoder licensed required for the selected function"
::= { enc1P1398costDolbyDigitalEncoderDDEEntry 1 }

enc1P1399costDolbyDigitalDecoderDDDTable OBJECT-TYPE
    SYNTAX SEQUENCE OF Enc1P1399costDolbyDigitalDecoderDDDEntry
    MAX-ACCESS not-accessible
    STATUS     current
    DESCRIPTION
    "
    Name      : Cost, Dolby Digital Decoder (DDD)
    Menu Path : Not Applicable
    Details   : Reports number of Dolby Digital decoder licensed required for the selected function
    "
::= { enc1Params 1399 }

enc1P1399costDolbyDigitalDecoderDDDEntry OBJECT-TYPE
    SYNTAX Enc1P1399costDolbyDigitalDecoderDDDEntry
    MAX-ACCESS not-accessible
    STATUS     current
    DESCRIPTION
    "Table Entry for Cost, Dolby Digital Decoder (DDD)"
    INDEX { slotId }
::= { enc1P1399costDolbyDigitalDecoderDDDTable 1 }

Enc1P1399costDolbyDigitalDecoderDDDEntry ::= SEQUENCE {
    enc1P1399costDolbyDigitalDecoderDDDValue    Enc1E148enumObj
}

enc1P1399costDolbyDigitalDecoderDDDValue OBJECT-TYPE
    SYNTAX     Enc1E148enumObj
    MAX-ACCESS read-only
    STATUS     current
    DESCRIPTION
    "Reports number of Dolby Digital decoder licensed required for the selected function"
::= { enc1P1399costDolbyDigitalDecoderDDDEntry 1 }

enc1P1400encodingModeTable OBJECT-TYPE
    SYNTAX SEQUENCE OF Enc1P1400encodingModeEntry
    MAX-ACCESS not-accessible
    STATUS     current
    DESCRIPTION
    "
    Name      : Encoding Mode
    Menu Path : /Misc
    Details   : Specify the video encoding mode. An encoder restart may be required when the mode is changed.
    "
::= { enc1Params 1400 }

enc1P1400encodingModeEntry OBJECT-TYPE
    SYNTAX Enc1P1400encodingModeEntry
    MAX-ACCESS not-accessible
    STATUS     current
    DESCRIPTION
    "Table Entry for Encoding Mode"
    INDEX { slotId }
::= { enc1P1400encodingModeTable 1 }

Enc1P1400encodingModeEntry ::= SEQUENCE {
    enc1P1400encodingModeValue    Enc1E12enumObj
}

enc1P1400encodingModeValue OBJECT-TYPE
    SYNTAX     Enc1E12enumObj
    MAX-ACCESS read-write
    STATUS     current
    DESCRIPTION
    "Specify the video encoding mode. An encoder restart may be required when the mode is changed."
::= { enc1P1400encodingModeEntry 1 }

enc1P1402source1Table OBJECT-TYPE
    SYNTAX SEQUENCE OF Enc1P1402source1Entry
    MAX-ACCESS not-accessible
    STATUS     current
    DESCRIPTION
    "
    Name      : Source 1
    Menu Path : /Audio/AAP 1 Configuration/General
    Details   : Specifies first audio source (pair) for this AAP.
    "
::= { enc1Params 1402 }

enc1P1402source1Entry OBJECT-TYPE
    SYNTAX Enc1P1402source1Entry
    MAX-ACCESS not-accessible
    STATUS     current
    DESCRIPTION
    "Table Entry for Source 1"
    INDEX { slotId }
::= { enc1P1402source1Table 1 }

Enc1P1402source1Entry ::= SEQUENCE {
    enc1P1402source1Value    Enc1E71enumObj
}

enc1P1402source1Value OBJECT-TYPE
    SYNTAX     Enc1E71enumObj
    MAX-ACCESS read-write
    STATUS     current
    DESCRIPTION
    "Specifies first audio source (pair) for this AAP."
::= { enc1P1402source1Entry 1 }

enc1P1403source2Table OBJECT-TYPE
    SYNTAX SEQUENCE OF Enc1P1403source2Entry
    MAX-ACCESS not-accessible
    STATUS     current
    DESCRIPTION
    "
    Name      : Source 2
    Menu Path : /Audio/AAP 1 Configuration/General
    Details   : Specifies second audio source (pair) for this AAP.
    "
::= { enc1Params 1403 }

enc1P1403source2Entry OBJECT-TYPE
    SYNTAX Enc1P1403source2Entry
    MAX-ACCESS not-accessible
    STATUS     current
    DESCRIPTION
    "Table Entry for Source 2"
    INDEX { slotId }
::= { enc1P1403source2Table 1 }

Enc1P1403source2Entry ::= SEQUENCE {
    enc1P1403source2Value    Enc1E71enumObj
}

enc1P1403source2Value OBJECT-TYPE
    SYNTAX     Enc1E71enumObj
    MAX-ACCESS read-write
    STATUS     current
    DESCRIPTION
    "Specifies second audio source (pair) for this AAP."
::= { enc1P1403source2Entry 1 }

enc1P1404source3Table OBJECT-TYPE
    SYNTAX SEQUENCE OF Enc1P1404source3Entry
    MAX-ACCESS not-accessible
    STATUS     current
    DESCRIPTION
    "
    Name      : Source 3
    Menu Path : /Audio/AAP 1 Configuration/General
    Details   : Specifies third audio source (pair) for this AAP.
    "
::= { enc1Params 1404 }

enc1P1404source3Entry OBJECT-TYPE
    SYNTAX Enc1P1404source3Entry
    MAX-ACCESS not-accessible
    STATUS     current
    DESCRIPTION
    "Table Entry for Source 3"
    INDEX { slotId }
::= { enc1P1404source3Table 1 }

Enc1P1404source3Entry ::= SEQUENCE {
    enc1P1404source3Value    Enc1E71enumObj
}

enc1P1404source3Value OBJECT-TYPE
    SYNTAX     Enc1E71enumObj
    MAX-ACCESS read-write
    STATUS     current
    DESCRIPTION
    "Specifies third audio source (pair) for this AAP."
::= { enc1P1404source3Entry 1 }

enc1P1405source4Table OBJECT-TYPE
    SYNTAX SEQUENCE OF Enc1P1405source4Entry
    MAX-ACCESS not-accessible
    STATUS     current
    DESCRIPTION
    "
    Name      : Source 4
    Menu Path : /Audio/AAP 1 Configuration/General
    Details   : Specifies fourth audio source (pair) for this AAP.
    "
::= { enc1Params 1405 }

enc1P1405source4Entry OBJECT-TYPE
    SYNTAX Enc1P1405source4Entry
    MAX-ACCESS not-accessible
    STATUS     current
    DESCRIPTION
    "Table Entry for Source 4"
    INDEX { slotId }
::= { enc1P1405source4Table 1 }

Enc1P1405source4Entry ::= SEQUENCE {
    enc1P1405source4Value    Enc1E71enumObj
}

enc1P1405source4Value OBJECT-TYPE
    SYNTAX     Enc1E71enumObj
    MAX-ACCESS read-write
    STATUS     current
    DESCRIPTION
    "Specifies fourth audio source (pair) for this AAP."
::= { enc1P1405source4Entry 1 }

enc1P1406formatTable OBJECT-TYPE
    SYNTAX SEQUENCE OF Enc1P1406formatEntry
    MAX-ACCESS not-accessible
    STATUS     current
    DESCRIPTION
    "
    Name      : Format
    Menu Path : /Data/VBI over VANC
    Details   : Specifies VANC over VBI format.
    "
::= { enc1Params 1406 }

enc1P1406formatEntry OBJECT-TYPE
    SYNTAX Enc1P1406formatEntry
    MAX-ACCESS not-accessible
    STATUS     current
    DESCRIPTION
    "Table Entry for Format"
    INDEX { slotId }
::= { enc1P1406formatTable 1 }

Enc1P1406formatEntry ::= SEQUENCE {
    enc1P1406formatValue    Enc1E128enumObj
}

enc1P1406formatValue OBJECT-TYPE
    SYNTAX     Enc1E128enumObj
    MAX-ACCESS read-write
    STATUS     current
    DESCRIPTION
    "Specifies VANC over VBI format."
::= { enc1P1406formatEntry 1 }

enc1P1407smpte-2031RateTable OBJECT-TYPE
    SYNTAX SEQUENCE OF Enc1P1407smpte-2031RateEntry
    MAX-ACCESS not-accessible
    STATUS     current
    DESCRIPTION
    "
    Name      : SMPTE-2031 Rate
    Menu Path : /Data/VBI over VANC
    Units     : Mbits/sec
    Precision : 6
    Low Range : 0
    High Range: 2000000
    Details   : Specifies maximum TS rate dedicated to SMPTE-2031 data. (Units: Mbits/sec)

     NOTE: Precision/Units/Ranges represent the state of the
           parameter during the MIB generation, and does not
           neccessary reflect the current state of the parameter
    "
::= { enc1Params 1407 }

enc1P1407smpte-2031RateEntry OBJECT-TYPE
    SYNTAX Enc1P1407smpte-2031RateEntry
    MAX-ACCESS not-accessible
    STATUS     current
    DESCRIPTION
    "Table Entry for SMPTE-2031 Rate"
    INDEX { slotId }
::= { enc1P1407smpte-2031RateTable 1 }

Enc1P1407smpte-2031RateEntry ::= SEQUENCE {
    enc1P1407smpte-2031RateValue    INTEGER
}

enc1P1407smpte-2031RateValue OBJECT-TYPE
    SYNTAX     INTEGER
    MAX-ACCESS read-write
    STATUS     current
    DESCRIPTION
    "Specifies maximum TS rate dedicated to SMPTE-2031 data. (Units: Mbits/sec)"
::= { enc1P1407smpte-2031RateEntry 1 }

enc1P1409smpte2031RateTable OBJECT-TYPE
    SYNTAX SEQUENCE OF Enc1P1409smpte2031RateEntry
    MAX-ACCESS not-accessible
    STATUS     current
    DESCRIPTION
    "
    Name      : SMPTE 2031 Rate
    Menu Path : /Data/VBI over VANC Status
    Units     : Mbits/sec
    Precision : 6
    Low Range : 0
    High Range: 2000000
    Details   : Shows the peak bitrate for SMPTE 2031 data. (Units: Mbits/sec)

     NOTE: Precision/Units/Ranges represent the state of the
           parameter during the MIB generation, and does not
           neccessary reflect the current state of the parameter
    "
::= { enc1Params 1409 }

enc1P1409smpte2031RateEntry OBJECT-TYPE
    SYNTAX Enc1P1409smpte2031RateEntry
    MAX-ACCESS not-accessible
    STATUS     current
    DESCRIPTION
    "Table Entry for SMPTE 2031 Rate"
    INDEX { slotId }
::= { enc1P1409smpte2031RateTable 1 }

Enc1P1409smpte2031RateEntry ::= SEQUENCE {
    enc1P1409smpte2031RateValue    INTEGER
}

enc1P1409smpte2031RateValue OBJECT-TYPE
    SYNTAX     INTEGER
    MAX-ACCESS read-only
    STATUS     current
    DESCRIPTION
    "Shows the peak bitrate for SMPTE 2031 data. (Units: Mbits/sec)"
::= { enc1P1409smpte2031RateEntry 1 }

enc1P1410smpte2031DropTable OBJECT-TYPE
    SYNTAX SEQUENCE OF Enc1P1410smpte2031DropEntry
    MAX-ACCESS not-accessible
    STATUS     current
    DESCRIPTION
    "
    Name      : SMPTE 2031 Drop
    Menu Path : /Data/VBI over VANC Status
    Units     : 
    Precision : 0
    Low Range : 0
    High Range: -1
    Details   : Shows the number of dropped SMPTE 2031 packets

     NOTE: Precision/Units/Ranges represent the state of the
           parameter during the MIB generation, and does not
           neccessary reflect the current state of the parameter
    "
::= { enc1Params 1410 }

enc1P1410smpte2031DropEntry OBJECT-TYPE
    SYNTAX Enc1P1410smpte2031DropEntry
    MAX-ACCESS not-accessible
    STATUS     current
    DESCRIPTION
    "Table Entry for SMPTE 2031 Drop"
    INDEX { slotId }
::= { enc1P1410smpte2031DropTable 1 }

Enc1P1410smpte2031DropEntry ::= SEQUENCE {
    enc1P1410smpte2031DropValue    INTEGER
}

enc1P1410smpte2031DropValue OBJECT-TYPE
    SYNTAX     INTEGER
    MAX-ACCESS read-only
    STATUS     current
    DESCRIPTION
    "Shows the number of dropped SMPTE 2031 packets"
::= { enc1P1410smpte2031DropEntry 1 }

enc1P1411field1Line6FunctionTable OBJECT-TYPE
    SYNTAX SEQUENCE OF Enc1P1411field1Line6FunctionEntry
    MAX-ACCESS not-accessible
    STATUS     current
    DESCRIPTION
    "
    Name      : Field 1 Line 6 Function
    Menu Path : /Data/VBI over VANC Status
    Details   : Shows this line's function.
    "
::= { enc1Params 1411 }

enc1P1411field1Line6FunctionEntry OBJECT-TYPE
    SYNTAX Enc1P1411field1Line6FunctionEntry
    MAX-ACCESS not-accessible
    STATUS     current
    DESCRIPTION
    "Table Entry for Field 1 Line 6 Function"
    INDEX { slotId }
::= { enc1P1411field1Line6FunctionTable 1 }

Enc1P1411field1Line6FunctionEntry ::= SEQUENCE {
    enc1P1411field1Line6FunctionValue    Enc1E112enumObj
}

enc1P1411field1Line6FunctionValue OBJECT-TYPE
    SYNTAX     Enc1E112enumObj
    MAX-ACCESS read-only
    STATUS     current
    DESCRIPTION
    "Shows this line's function."
::= { enc1P1411field1Line6FunctionEntry 1 }

enc1P1412field1Line7FunctionTable OBJECT-TYPE
    SYNTAX SEQUENCE OF Enc1P1412field1Line7FunctionEntry
    MAX-ACCESS not-accessible
    STATUS     current
    DESCRIPTION
    "
    Name      : Field 1 Line 7 Function
    Menu Path : /Data/VBI over VANC Status
    Details   : Shows this line's function.
    "
::= { enc1Params 1412 }

enc1P1412field1Line7FunctionEntry OBJECT-TYPE
    SYNTAX Enc1P1412field1Line7FunctionEntry
    MAX-ACCESS not-accessible
    STATUS     current
    DESCRIPTION
    "Table Entry for Field 1 Line 7 Function"
    INDEX { slotId }
::= { enc1P1412field1Line7FunctionTable 1 }

Enc1P1412field1Line7FunctionEntry ::= SEQUENCE {
    enc1P1412field1Line7FunctionValue    Enc1E112enumObj
}

enc1P1412field1Line7FunctionValue OBJECT-TYPE
    SYNTAX     Enc1E112enumObj
    MAX-ACCESS read-only
    STATUS     current
    DESCRIPTION
    "Shows this line's function."
::= { enc1P1412field1Line7FunctionEntry 1 }

enc1P1413field1Line8FunctionTable OBJECT-TYPE
    SYNTAX SEQUENCE OF Enc1P1413field1Line8FunctionEntry
    MAX-ACCESS not-accessible
    STATUS     current
    DESCRIPTION
    "
    Name      : Field 1 Line 8 Function
    Menu Path : /Data/VBI over VANC Status
    Details   : Shows this line's function.
    "
::= { enc1Params 1413 }

enc1P1413field1Line8FunctionEntry OBJECT-TYPE
    SYNTAX Enc1P1413field1Line8FunctionEntry
    MAX-ACCESS not-accessible
    STATUS     current
    DESCRIPTION
    "Table Entry for Field 1 Line 8 Function"
    INDEX { slotId }
::= { enc1P1413field1Line8FunctionTable 1 }

Enc1P1413field1Line8FunctionEntry ::= SEQUENCE {
    enc1P1413field1Line8FunctionValue    Enc1E112enumObj
}

enc1P1413field1Line8FunctionValue OBJECT-TYPE
    SYNTAX     Enc1E112enumObj
    MAX-ACCESS read-only
    STATUS     current
    DESCRIPTION
    "Shows this line's function."
::= { enc1P1413field1Line8FunctionEntry 1 }

enc1P1414field1Line9FunctionTable OBJECT-TYPE
    SYNTAX SEQUENCE OF Enc1P1414field1Line9FunctionEntry
    MAX-ACCESS not-accessible
    STATUS     current
    DESCRIPTION
    "
    Name      : Field 1 Line 9 Function
    Menu Path : /Data/VBI over VANC Status
    Details   : Shows this line's function.
    "
::= { enc1Params 1414 }

enc1P1414field1Line9FunctionEntry OBJECT-TYPE
    SYNTAX Enc1P1414field1Line9FunctionEntry
    MAX-ACCESS not-accessible
    STATUS     current
    DESCRIPTION
    "Table Entry for Field 1 Line 9 Function"
    INDEX { slotId }
::= { enc1P1414field1Line9FunctionTable 1 }

Enc1P1414field1Line9FunctionEntry ::= SEQUENCE {
    enc1P1414field1Line9FunctionValue    Enc1E112enumObj
}

enc1P1414field1Line9FunctionValue OBJECT-TYPE
    SYNTAX     Enc1E112enumObj
    MAX-ACCESS read-only
    STATUS     current
    DESCRIPTION
    "Shows this line's function."
::= { enc1P1414field1Line9FunctionEntry 1 }

enc1P1415field1Line10FunctionTable OBJECT-TYPE
    SYNTAX SEQUENCE OF Enc1P1415field1Line10FunctionEntry
    MAX-ACCESS not-accessible
    STATUS     current
    DESCRIPTION
    "
    Name      : Field 1 Line 10 Function
    Menu Path : /Data/VBI over VANC Status
    Details   : Shows this line's function.
    "
::= { enc1Params 1415 }

enc1P1415field1Line10FunctionEntry OBJECT-TYPE
    SYNTAX Enc1P1415field1Line10FunctionEntry
    MAX-ACCESS not-accessible
    STATUS     current
    DESCRIPTION
    "Table Entry for Field 1 Line 10 Function"
    INDEX { slotId }
::= { enc1P1415field1Line10FunctionTable 1 }

Enc1P1415field1Line10FunctionEntry ::= SEQUENCE {
    enc1P1415field1Line10FunctionValue    Enc1E112enumObj
}

enc1P1415field1Line10FunctionValue OBJECT-TYPE
    SYNTAX     Enc1E112enumObj
    MAX-ACCESS read-only
    STATUS     current
    DESCRIPTION
    "Shows this line's function."
::= { enc1P1415field1Line10FunctionEntry 1 }

enc1P1416field1Line11FunctionTable OBJECT-TYPE
    SYNTAX SEQUENCE OF Enc1P1416field1Line11FunctionEntry
    MAX-ACCESS not-accessible
    STATUS     current
    DESCRIPTION
    "
    Name      : Field 1 Line 11 Function
    Menu Path : /Data/VBI over VANC Status
    Details   : Shows this line's function.
    "
::= { enc1Params 1416 }

enc1P1416field1Line11FunctionEntry OBJECT-TYPE
    SYNTAX Enc1P1416field1Line11FunctionEntry
    MAX-ACCESS not-accessible
    STATUS     current
    DESCRIPTION
    "Table Entry for Field 1 Line 11 Function"
    INDEX { slotId }
::= { enc1P1416field1Line11FunctionTable 1 }

Enc1P1416field1Line11FunctionEntry ::= SEQUENCE {
    enc1P1416field1Line11FunctionValue    Enc1E112enumObj
}

enc1P1416field1Line11FunctionValue OBJECT-TYPE
    SYNTAX     Enc1E112enumObj
    MAX-ACCESS read-only
    STATUS     current
    DESCRIPTION
    "Shows this line's function."
::= { enc1P1416field1Line11FunctionEntry 1 }

enc1P1417field1Line12FunctionTable OBJECT-TYPE
    SYNTAX SEQUENCE OF Enc1P1417field1Line12FunctionEntry
    MAX-ACCESS not-accessible
    STATUS     current
    DESCRIPTION
    "
    Name      : Field 1 Line 12 Function
    Menu Path : /Data/VBI over VANC Status
    Details   : Shows this line's function.
    "
::= { enc1Params 1417 }

enc1P1417field1Line12FunctionEntry OBJECT-TYPE
    SYNTAX Enc1P1417field1Line12FunctionEntry
    MAX-ACCESS not-accessible
    STATUS     current
    DESCRIPTION
    "Table Entry for Field 1 Line 12 Function"
    INDEX { slotId }
::= { enc1P1417field1Line12FunctionTable 1 }

Enc1P1417field1Line12FunctionEntry ::= SEQUENCE {
    enc1P1417field1Line12FunctionValue    Enc1E112enumObj
}

enc1P1417field1Line12FunctionValue OBJECT-TYPE
    SYNTAX     Enc1E112enumObj
    MAX-ACCESS read-only
    STATUS     current
    DESCRIPTION
    "Shows this line's function."
::= { enc1P1417field1Line12FunctionEntry 1 }

enc1P1418field1Line13FunctionTable OBJECT-TYPE
    SYNTAX SEQUENCE OF Enc1P1418field1Line13FunctionEntry
    MAX-ACCESS not-accessible
    STATUS     current
    DESCRIPTION
    "
    Name      : Field 1 Line 13 Function
    Menu Path : /Data/VBI over VANC Status
    Details   : Shows this line's function.
    "
::= { enc1Params 1418 }

enc1P1418field1Line13FunctionEntry OBJECT-TYPE
    SYNTAX Enc1P1418field1Line13FunctionEntry
    MAX-ACCESS not-accessible
    STATUS     current
    DESCRIPTION
    "Table Entry for Field 1 Line 13 Function"
    INDEX { slotId }
::= { enc1P1418field1Line13FunctionTable 1 }

Enc1P1418field1Line13FunctionEntry ::= SEQUENCE {
    enc1P1418field1Line13FunctionValue    Enc1E112enumObj
}

enc1P1418field1Line13FunctionValue OBJECT-TYPE
    SYNTAX     Enc1E112enumObj
    MAX-ACCESS read-only
    STATUS     current
    DESCRIPTION
    "Shows this line's function."
::= { enc1P1418field1Line13FunctionEntry 1 }

enc1P1419field1Line14FunctionTable OBJECT-TYPE
    SYNTAX SEQUENCE OF Enc1P1419field1Line14FunctionEntry
    MAX-ACCESS not-accessible
    STATUS     current
    DESCRIPTION
    "
    Name      : Field 1 Line 14 Function
    Menu Path : /Data/VBI over VANC Status
    Details   : Shows this line's function.
    "
::= { enc1Params 1419 }

enc1P1419field1Line14FunctionEntry OBJECT-TYPE
    SYNTAX Enc1P1419field1Line14FunctionEntry
    MAX-ACCESS not-accessible
    STATUS     current
    DESCRIPTION
    "Table Entry for Field 1 Line 14 Function"
    INDEX { slotId }
::= { enc1P1419field1Line14FunctionTable 1 }

Enc1P1419field1Line14FunctionEntry ::= SEQUENCE {
    enc1P1419field1Line14FunctionValue    Enc1E112enumObj
}

enc1P1419field1Line14FunctionValue OBJECT-TYPE
    SYNTAX     Enc1E112enumObj
    MAX-ACCESS read-only
    STATUS     current
    DESCRIPTION
    "Shows this line's function."
::= { enc1P1419field1Line14FunctionEntry 1 }

enc1P1420field1Line15FunctionTable OBJECT-TYPE
    SYNTAX SEQUENCE OF Enc1P1420field1Line15FunctionEntry
    MAX-ACCESS not-accessible
    STATUS     current
    DESCRIPTION
    "
    Name      : Field 1 Line 15 Function
    Menu Path : /Data/VBI over VANC Status
    Details   : Shows this line's function.
    "
::= { enc1Params 1420 }

enc1P1420field1Line15FunctionEntry OBJECT-TYPE
    SYNTAX Enc1P1420field1Line15FunctionEntry
    MAX-ACCESS not-accessible
    STATUS     current
    DESCRIPTION
    "Table Entry for Field 1 Line 15 Function"
    INDEX { slotId }
::= { enc1P1420field1Line15FunctionTable 1 }

Enc1P1420field1Line15FunctionEntry ::= SEQUENCE {
    enc1P1420field1Line15FunctionValue    Enc1E112enumObj
}

enc1P1420field1Line15FunctionValue OBJECT-TYPE
    SYNTAX     Enc1E112enumObj
    MAX-ACCESS read-only
    STATUS     current
    DESCRIPTION
    "Shows this line's function."
::= { enc1P1420field1Line15FunctionEntry 1 }

enc1P1421field1Line16FunctionTable OBJECT-TYPE
    SYNTAX SEQUENCE OF Enc1P1421field1Line16FunctionEntry
    MAX-ACCESS not-accessible
    STATUS     current
    DESCRIPTION
    "
    Name      : Field 1 Line 16 Function
    Menu Path : /Data/VBI over VANC Status
    Details   : Shows this line's function.
    "
::= { enc1Params 1421 }

enc1P1421field1Line16FunctionEntry OBJECT-TYPE
    SYNTAX Enc1P1421field1Line16FunctionEntry
    MAX-ACCESS not-accessible
    STATUS     current
    DESCRIPTION
    "Table Entry for Field 1 Line 16 Function"
    INDEX { slotId }
::= { enc1P1421field1Line16FunctionTable 1 }

Enc1P1421field1Line16FunctionEntry ::= SEQUENCE {
    enc1P1421field1Line16FunctionValue    Enc1E112enumObj
}

enc1P1421field1Line16FunctionValue OBJECT-TYPE
    SYNTAX     Enc1E112enumObj
    MAX-ACCESS read-only
    STATUS     current
    DESCRIPTION
    "Shows this line's function."
::= { enc1P1421field1Line16FunctionEntry 1 }

enc1P1422field1Line17FunctionTable OBJECT-TYPE
    SYNTAX SEQUENCE OF Enc1P1422field1Line17FunctionEntry
    MAX-ACCESS not-accessible
    STATUS     current
    DESCRIPTION
    "
    Name      : Field 1 Line 17 Function
    Menu Path : /Data/VBI over VANC Status
    Details   : Shows this line's function.
    "
::= { enc1Params 1422 }

enc1P1422field1Line17FunctionEntry OBJECT-TYPE
    SYNTAX Enc1P1422field1Line17FunctionEntry
    MAX-ACCESS not-accessible
    STATUS     current
    DESCRIPTION
    "Table Entry for Field 1 Line 17 Function"
    INDEX { slotId }
::= { enc1P1422field1Line17FunctionTable 1 }

Enc1P1422field1Line17FunctionEntry ::= SEQUENCE {
    enc1P1422field1Line17FunctionValue    Enc1E112enumObj
}

enc1P1422field1Line17FunctionValue OBJECT-TYPE
    SYNTAX     Enc1E112enumObj
    MAX-ACCESS read-only
    STATUS     current
    DESCRIPTION
    "Shows this line's function."
::= { enc1P1422field1Line17FunctionEntry 1 }

enc1P1423field1Line18FunctionTable OBJECT-TYPE
    SYNTAX SEQUENCE OF Enc1P1423field1Line18FunctionEntry
    MAX-ACCESS not-accessible
    STATUS     current
    DESCRIPTION
    "
    Name      : Field 1 Line 18 Function
    Menu Path : /Data/VBI over VANC Status
    Details   : Shows this line's function.
    "
::= { enc1Params 1423 }

enc1P1423field1Line18FunctionEntry OBJECT-TYPE
    SYNTAX Enc1P1423field1Line18FunctionEntry
    MAX-ACCESS not-accessible
    STATUS     current
    DESCRIPTION
    "Table Entry for Field 1 Line 18 Function"
    INDEX { slotId }
::= { enc1P1423field1Line18FunctionTable 1 }

Enc1P1423field1Line18FunctionEntry ::= SEQUENCE {
    enc1P1423field1Line18FunctionValue    Enc1E112enumObj
}

enc1P1423field1Line18FunctionValue OBJECT-TYPE
    SYNTAX     Enc1E112enumObj
    MAX-ACCESS read-only
    STATUS     current
    DESCRIPTION
    "Shows this line's function."
::= { enc1P1423field1Line18FunctionEntry 1 }

enc1P1424field1Line19FunctionTable OBJECT-TYPE
    SYNTAX SEQUENCE OF Enc1P1424field1Line19FunctionEntry
    MAX-ACCESS not-accessible
    STATUS     current
    DESCRIPTION
    "
    Name      : Field 1 Line 19 Function
    Menu Path : /Data/VBI over VANC Status
    Details   : Shows this line's function.
    "
::= { enc1Params 1424 }

enc1P1424field1Line19FunctionEntry OBJECT-TYPE
    SYNTAX Enc1P1424field1Line19FunctionEntry
    MAX-ACCESS not-accessible
    STATUS     current
    DESCRIPTION
    "Table Entry for Field 1 Line 19 Function"
    INDEX { slotId }
::= { enc1P1424field1Line19FunctionTable 1 }

Enc1P1424field1Line19FunctionEntry ::= SEQUENCE {
    enc1P1424field1Line19FunctionValue    Enc1E112enumObj
}

enc1P1424field1Line19FunctionValue OBJECT-TYPE
    SYNTAX     Enc1E112enumObj
    MAX-ACCESS read-only
    STATUS     current
    DESCRIPTION
    "Shows this line's function."
::= { enc1P1424field1Line19FunctionEntry 1 }

enc1P1425field1Line20FunctionTable OBJECT-TYPE
    SYNTAX SEQUENCE OF Enc1P1425field1Line20FunctionEntry
    MAX-ACCESS not-accessible
    STATUS     current
    DESCRIPTION
    "
    Name      : Field 1 Line 20 Function
    Menu Path : /Data/VBI over VANC Status
    Details   : Shows this line's function.
    "
::= { enc1Params 1425 }

enc1P1425field1Line20FunctionEntry OBJECT-TYPE
    SYNTAX Enc1P1425field1Line20FunctionEntry
    MAX-ACCESS not-accessible
    STATUS     current
    DESCRIPTION
    "Table Entry for Field 1 Line 20 Function"
    INDEX { slotId }
::= { enc1P1425field1Line20FunctionTable 1 }

Enc1P1425field1Line20FunctionEntry ::= SEQUENCE {
    enc1P1425field1Line20FunctionValue    Enc1E112enumObj
}

enc1P1425field1Line20FunctionValue OBJECT-TYPE
    SYNTAX     Enc1E112enumObj
    MAX-ACCESS read-only
    STATUS     current
    DESCRIPTION
    "Shows this line's function."
::= { enc1P1425field1Line20FunctionEntry 1 }

enc1P1426field1Line21FunctionTable OBJECT-TYPE
    SYNTAX SEQUENCE OF Enc1P1426field1Line21FunctionEntry
    MAX-ACCESS not-accessible
    STATUS     current
    DESCRIPTION
    "
    Name      : Field 1 Line 21 Function
    Menu Path : /Data/VBI over VANC Status
    Details   : Shows this line's function.
    "
::= { enc1Params 1426 }

enc1P1426field1Line21FunctionEntry OBJECT-TYPE
    SYNTAX Enc1P1426field1Line21FunctionEntry
    MAX-ACCESS not-accessible
    STATUS     current
    DESCRIPTION
    "Table Entry for Field 1 Line 21 Function"
    INDEX { slotId }
::= { enc1P1426field1Line21FunctionTable 1 }

Enc1P1426field1Line21FunctionEntry ::= SEQUENCE {
    enc1P1426field1Line21FunctionValue    Enc1E112enumObj
}

enc1P1426field1Line21FunctionValue OBJECT-TYPE
    SYNTAX     Enc1E112enumObj
    MAX-ACCESS read-only
    STATUS     current
    DESCRIPTION
    "Shows this line's function."
::= { enc1P1426field1Line21FunctionEntry 1 }

enc1P1427field1Line22FunctionTable OBJECT-TYPE
    SYNTAX SEQUENCE OF Enc1P1427field1Line22FunctionEntry
    MAX-ACCESS not-accessible
    STATUS     current
    DESCRIPTION
    "
    Name      : Field 1 Line 22 Function
    Menu Path : /Data/VBI over VANC Status
    Details   : Shows this line's function.
    "
::= { enc1Params 1427 }

enc1P1427field1Line22FunctionEntry OBJECT-TYPE
    SYNTAX Enc1P1427field1Line22FunctionEntry
    MAX-ACCESS not-accessible
    STATUS     current
    DESCRIPTION
    "Table Entry for Field 1 Line 22 Function"
    INDEX { slotId }
::= { enc1P1427field1Line22FunctionTable 1 }

Enc1P1427field1Line22FunctionEntry ::= SEQUENCE {
    enc1P1427field1Line22FunctionValue    Enc1E112enumObj
}

enc1P1427field1Line22FunctionValue OBJECT-TYPE
    SYNTAX     Enc1E112enumObj
    MAX-ACCESS read-only
    STATUS     current
    DESCRIPTION
    "Shows this line's function."
::= { enc1P1427field1Line22FunctionEntry 1 }

enc1P1428field1Line23FunctionTable OBJECT-TYPE
    SYNTAX SEQUENCE OF Enc1P1428field1Line23FunctionEntry
    MAX-ACCESS not-accessible
    STATUS     current
    DESCRIPTION
    "
    Name      : Field 1 Line 23 Function
    Menu Path : /Data/VBI over VANC Status
    Details   : Shows this line's function.
    "
::= { enc1Params 1428 }

enc1P1428field1Line23FunctionEntry OBJECT-TYPE
    SYNTAX Enc1P1428field1Line23FunctionEntry
    MAX-ACCESS not-accessible
    STATUS     current
    DESCRIPTION
    "Table Entry for Field 1 Line 23 Function"
    INDEX { slotId }
::= { enc1P1428field1Line23FunctionTable 1 }

Enc1P1428field1Line23FunctionEntry ::= SEQUENCE {
    enc1P1428field1Line23FunctionValue    Enc1E112enumObj
}

enc1P1428field1Line23FunctionValue OBJECT-TYPE
    SYNTAX     Enc1E112enumObj
    MAX-ACCESS read-only
    STATUS     current
    DESCRIPTION
    "Shows this line's function."
::= { enc1P1428field1Line23FunctionEntry 1 }

enc1P1429field2Line5FunctionTable OBJECT-TYPE
    SYNTAX SEQUENCE OF Enc1P1429field2Line5FunctionEntry
    MAX-ACCESS not-accessible
    STATUS     current
    DESCRIPTION
    "
    Name      : Field 2 Line 5 Function
    Menu Path : /Data/VBI over VANC Status
    Details   : Shows this line's function.
    "
::= { enc1Params 1429 }

enc1P1429field2Line5FunctionEntry OBJECT-TYPE
    SYNTAX Enc1P1429field2Line5FunctionEntry
    MAX-ACCESS not-accessible
    STATUS     current
    DESCRIPTION
    "Table Entry for Field 2 Line 5 Function"
    INDEX { slotId }
::= { enc1P1429field2Line5FunctionTable 1 }

Enc1P1429field2Line5FunctionEntry ::= SEQUENCE {
    enc1P1429field2Line5FunctionValue    Enc1E112enumObj
}

enc1P1429field2Line5FunctionValue OBJECT-TYPE
    SYNTAX     Enc1E112enumObj
    MAX-ACCESS read-only
    STATUS     current
    DESCRIPTION
    "Shows this line's function."
::= { enc1P1429field2Line5FunctionEntry 1 }

enc1P1430field2Line6FunctionTable OBJECT-TYPE
    SYNTAX SEQUENCE OF Enc1P1430field2Line6FunctionEntry
    MAX-ACCESS not-accessible
    STATUS     current
    DESCRIPTION
    "
    Name      : Field 2 Line 6 Function
    Menu Path : /Data/VBI over VANC Status
    Details   : Shows this line's function.
    "
::= { enc1Params 1430 }

enc1P1430field2Line6FunctionEntry OBJECT-TYPE
    SYNTAX Enc1P1430field2Line6FunctionEntry
    MAX-ACCESS not-accessible
    STATUS     current
    DESCRIPTION
    "Table Entry for Field 2 Line 6 Function"
    INDEX { slotId }
::= { enc1P1430field2Line6FunctionTable 1 }

Enc1P1430field2Line6FunctionEntry ::= SEQUENCE {
    enc1P1430field2Line6FunctionValue    Enc1E112enumObj
}

enc1P1430field2Line6FunctionValue OBJECT-TYPE
    SYNTAX     Enc1E112enumObj
    MAX-ACCESS read-only
    STATUS     current
    DESCRIPTION
    "Shows this line's function."
::= { enc1P1430field2Line6FunctionEntry 1 }

enc1P1431field2Line7FunctionTable OBJECT-TYPE
    SYNTAX SEQUENCE OF Enc1P1431field2Line7FunctionEntry
    MAX-ACCESS not-accessible
    STATUS     current
    DESCRIPTION
    "
    Name      : Field 2 Line 7 Function
    Menu Path : /Data/VBI over VANC Status
    Details   : Shows this line's function.
    "
::= { enc1Params 1431 }

enc1P1431field2Line7FunctionEntry OBJECT-TYPE
    SYNTAX Enc1P1431field2Line7FunctionEntry
    MAX-ACCESS not-accessible
    STATUS     current
    DESCRIPTION
    "Table Entry for Field 2 Line 7 Function"
    INDEX { slotId }
::= { enc1P1431field2Line7FunctionTable 1 }

Enc1P1431field2Line7FunctionEntry ::= SEQUENCE {
    enc1P1431field2Line7FunctionValue    Enc1E112enumObj
}

enc1P1431field2Line7FunctionValue OBJECT-TYPE
    SYNTAX     Enc1E112enumObj
    MAX-ACCESS read-only
    STATUS     current
    DESCRIPTION
    "Shows this line's function."
::= { enc1P1431field2Line7FunctionEntry 1 }

enc1P1432field2Line8FunctionTable OBJECT-TYPE
    SYNTAX SEQUENCE OF Enc1P1432field2Line8FunctionEntry
    MAX-ACCESS not-accessible
    STATUS     current
    DESCRIPTION
    "
    Name      : Field 2 Line 8 Function
    Menu Path : /Data/VBI over VANC Status
    Details   : Shows this line's function.
    "
::= { enc1Params 1432 }

enc1P1432field2Line8FunctionEntry OBJECT-TYPE
    SYNTAX Enc1P1432field2Line8FunctionEntry
    MAX-ACCESS not-accessible
    STATUS     current
    DESCRIPTION
    "Table Entry for Field 2 Line 8 Function"
    INDEX { slotId }
::= { enc1P1432field2Line8FunctionTable 1 }

Enc1P1432field2Line8FunctionEntry ::= SEQUENCE {
    enc1P1432field2Line8FunctionValue    Enc1E112enumObj
}

enc1P1432field2Line8FunctionValue OBJECT-TYPE
    SYNTAX     Enc1E112enumObj
    MAX-ACCESS read-only
    STATUS     current
    DESCRIPTION
    "Shows this line's function."
::= { enc1P1432field2Line8FunctionEntry 1 }

enc1P1433field2Line9FunctionTable OBJECT-TYPE
    SYNTAX SEQUENCE OF Enc1P1433field2Line9FunctionEntry
    MAX-ACCESS not-accessible
    STATUS     current
    DESCRIPTION
    "
    Name      : Field 2 Line 9 Function
    Menu Path : /Data/VBI over VANC Status
    Details   : Shows this line's function.
    "
::= { enc1Params 1433 }

enc1P1433field2Line9FunctionEntry OBJECT-TYPE
    SYNTAX Enc1P1433field2Line9FunctionEntry
    MAX-ACCESS not-accessible
    STATUS     current
    DESCRIPTION
    "Table Entry for Field 2 Line 9 Function"
    INDEX { slotId }
::= { enc1P1433field2Line9FunctionTable 1 }

Enc1P1433field2Line9FunctionEntry ::= SEQUENCE {
    enc1P1433field2Line9FunctionValue    Enc1E112enumObj
}

enc1P1433field2Line9FunctionValue OBJECT-TYPE
    SYNTAX     Enc1E112enumObj
    MAX-ACCESS read-only
    STATUS     current
    DESCRIPTION
    "Shows this line's function."
::= { enc1P1433field2Line9FunctionEntry 1 }

enc1P1434field2Line10FunctionTable OBJECT-TYPE
    SYNTAX SEQUENCE OF Enc1P1434field2Line10FunctionEntry
    MAX-ACCESS not-accessible
    STATUS     current
    DESCRIPTION
    "
    Name      : Field 2 Line 10 Function
    Menu Path : /Data/VBI over VANC Status
    Details   : Shows this line's function.
    "
::= { enc1Params 1434 }

enc1P1434field2Line10FunctionEntry OBJECT-TYPE
    SYNTAX Enc1P1434field2Line10FunctionEntry
    MAX-ACCESS not-accessible
    STATUS     current
    DESCRIPTION
    "Table Entry for Field 2 Line 10 Function"
    INDEX { slotId }
::= { enc1P1434field2Line10FunctionTable 1 }

Enc1P1434field2Line10FunctionEntry ::= SEQUENCE {
    enc1P1434field2Line10FunctionValue    Enc1E112enumObj
}

enc1P1434field2Line10FunctionValue OBJECT-TYPE
    SYNTAX     Enc1E112enumObj
    MAX-ACCESS read-only
    STATUS     current
    DESCRIPTION
    "Shows this line's function."
::= { enc1P1434field2Line10FunctionEntry 1 }

enc1P1435field2Line11FunctionTable OBJECT-TYPE
    SYNTAX SEQUENCE OF Enc1P1435field2Line11FunctionEntry
    MAX-ACCESS not-accessible
    STATUS     current
    DESCRIPTION
    "
    Name      : Field 2 Line 11 Function
    Menu Path : /Data/VBI over VANC Status
    Details   : Shows this line's function.
    "
::= { enc1Params 1435 }

enc1P1435field2Line11FunctionEntry OBJECT-TYPE
    SYNTAX Enc1P1435field2Line11FunctionEntry
    MAX-ACCESS not-accessible
    STATUS     current
    DESCRIPTION
    "Table Entry for Field 2 Line 11 Function"
    INDEX { slotId }
::= { enc1P1435field2Line11FunctionTable 1 }

Enc1P1435field2Line11FunctionEntry ::= SEQUENCE {
    enc1P1435field2Line11FunctionValue    Enc1E112enumObj
}

enc1P1435field2Line11FunctionValue OBJECT-TYPE
    SYNTAX     Enc1E112enumObj
    MAX-ACCESS read-only
    STATUS     current
    DESCRIPTION
    "Shows this line's function."
::= { enc1P1435field2Line11FunctionEntry 1 }

enc1P1436field2Line12FunctionTable OBJECT-TYPE
    SYNTAX SEQUENCE OF Enc1P1436field2Line12FunctionEntry
    MAX-ACCESS not-accessible
    STATUS     current
    DESCRIPTION
    "
    Name      : Field 2 Line 12 Function
    Menu Path : /Data/VBI over VANC Status
    Details   : Shows this line's function.
    "
::= { enc1Params 1436 }

enc1P1436field2Line12FunctionEntry OBJECT-TYPE
    SYNTAX Enc1P1436field2Line12FunctionEntry
    MAX-ACCESS not-accessible
    STATUS     current
    DESCRIPTION
    "Table Entry for Field 2 Line 12 Function"
    INDEX { slotId }
::= { enc1P1436field2Line12FunctionTable 1 }

Enc1P1436field2Line12FunctionEntry ::= SEQUENCE {
    enc1P1436field2Line12FunctionValue    Enc1E112enumObj
}

enc1P1436field2Line12FunctionValue OBJECT-TYPE
    SYNTAX     Enc1E112enumObj
    MAX-ACCESS read-only
    STATUS     current
    DESCRIPTION
    "Shows this line's function."
::= { enc1P1436field2Line12FunctionEntry 1 }

enc1P1437field2Line13FunctionTable OBJECT-TYPE
    SYNTAX SEQUENCE OF Enc1P1437field2Line13FunctionEntry
    MAX-ACCESS not-accessible
    STATUS     current
    DESCRIPTION
    "
    Name      : Field 2 Line 13 Function
    Menu Path : /Data/VBI over VANC Status
    Details   : Shows this line's function.
    "
::= { enc1Params 1437 }

enc1P1437field2Line13FunctionEntry OBJECT-TYPE
    SYNTAX Enc1P1437field2Line13FunctionEntry
    MAX-ACCESS not-accessible
    STATUS     current
    DESCRIPTION
    "Table Entry for Field 2 Line 13 Function"
    INDEX { slotId }
::= { enc1P1437field2Line13FunctionTable 1 }

Enc1P1437field2Line13FunctionEntry ::= SEQUENCE {
    enc1P1437field2Line13FunctionValue    Enc1E112enumObj
}

enc1P1437field2Line13FunctionValue OBJECT-TYPE
    SYNTAX     Enc1E112enumObj
    MAX-ACCESS read-only
    STATUS     current
    DESCRIPTION
    "Shows this line's function."
::= { enc1P1437field2Line13FunctionEntry 1 }

enc1P1438field2Line14FunctionTable OBJECT-TYPE
    SYNTAX SEQUENCE OF Enc1P1438field2Line14FunctionEntry
    MAX-ACCESS not-accessible
    STATUS     current
    DESCRIPTION
    "
    Name      : Field 2 Line 14 Function
    Menu Path : /Data/VBI over VANC Status
    Details   : Shows this line's function.
    "
::= { enc1Params 1438 }

enc1P1438field2Line14FunctionEntry OBJECT-TYPE
    SYNTAX Enc1P1438field2Line14FunctionEntry
    MAX-ACCESS not-accessible
    STATUS     current
    DESCRIPTION
    "Table Entry for Field 2 Line 14 Function"
    INDEX { slotId }
::= { enc1P1438field2Line14FunctionTable 1 }

Enc1P1438field2Line14FunctionEntry ::= SEQUENCE {
    enc1P1438field2Line14FunctionValue    Enc1E112enumObj
}

enc1P1438field2Line14FunctionValue OBJECT-TYPE
    SYNTAX     Enc1E112enumObj
    MAX-ACCESS read-only
    STATUS     current
    DESCRIPTION
    "Shows this line's function."
::= { enc1P1438field2Line14FunctionEntry 1 }

enc1P1439field2Line15FunctionTable OBJECT-TYPE
    SYNTAX SEQUENCE OF Enc1P1439field2Line15FunctionEntry
    MAX-ACCESS not-accessible
    STATUS     current
    DESCRIPTION
    "
    Name      : Field 2 Line 15 Function
    Menu Path : /Data/VBI over VANC Status
    Details   : Shows this line's function.
    "
::= { enc1Params 1439 }

enc1P1439field2Line15FunctionEntry OBJECT-TYPE
    SYNTAX Enc1P1439field2Line15FunctionEntry
    MAX-ACCESS not-accessible
    STATUS     current
    DESCRIPTION
    "Table Entry for Field 2 Line 15 Function"
    INDEX { slotId }
::= { enc1P1439field2Line15FunctionTable 1 }

Enc1P1439field2Line15FunctionEntry ::= SEQUENCE {
    enc1P1439field2Line15FunctionValue    Enc1E112enumObj
}

enc1P1439field2Line15FunctionValue OBJECT-TYPE
    SYNTAX     Enc1E112enumObj
    MAX-ACCESS read-only
    STATUS     current
    DESCRIPTION
    "Shows this line's function."
::= { enc1P1439field2Line15FunctionEntry 1 }

enc1P1440field2Line16FunctionTable OBJECT-TYPE
    SYNTAX SEQUENCE OF Enc1P1440field2Line16FunctionEntry
    MAX-ACCESS not-accessible
    STATUS     current
    DESCRIPTION
    "
    Name      : Field 2 Line 16 Function
    Menu Path : /Data/VBI over VANC Status
    Details   : Shows this line's function.
    "
::= { enc1Params 1440 }

enc1P1440field2Line16FunctionEntry OBJECT-TYPE
    SYNTAX Enc1P1440field2Line16FunctionEntry
    MAX-ACCESS not-accessible
    STATUS     current
    DESCRIPTION
    "Table Entry for Field 2 Line 16 Function"
    INDEX { slotId }
::= { enc1P1440field2Line16FunctionTable 1 }

Enc1P1440field2Line16FunctionEntry ::= SEQUENCE {
    enc1P1440field2Line16FunctionValue    Enc1E112enumObj
}

enc1P1440field2Line16FunctionValue OBJECT-TYPE
    SYNTAX     Enc1E112enumObj
    MAX-ACCESS read-only
    STATUS     current
    DESCRIPTION
    "Shows this line's function."
::= { enc1P1440field2Line16FunctionEntry 1 }

enc1P1441field2Line17FunctionTable OBJECT-TYPE
    SYNTAX SEQUENCE OF Enc1P1441field2Line17FunctionEntry
    MAX-ACCESS not-accessible
    STATUS     current
    DESCRIPTION
    "
    Name      : Field 2 Line 17 Function
    Menu Path : /Data/VBI over VANC Status
    Details   : Shows this line's function.
    "
::= { enc1Params 1441 }

enc1P1441field2Line17FunctionEntry OBJECT-TYPE
    SYNTAX Enc1P1441field2Line17FunctionEntry
    MAX-ACCESS not-accessible
    STATUS     current
    DESCRIPTION
    "Table Entry for Field 2 Line 17 Function"
    INDEX { slotId }
::= { enc1P1441field2Line17FunctionTable 1 }

Enc1P1441field2Line17FunctionEntry ::= SEQUENCE {
    enc1P1441field2Line17FunctionValue    Enc1E112enumObj
}

enc1P1441field2Line17FunctionValue OBJECT-TYPE
    SYNTAX     Enc1E112enumObj
    MAX-ACCESS read-only
    STATUS     current
    DESCRIPTION
    "Shows this line's function."
::= { enc1P1441field2Line17FunctionEntry 1 }

enc1P1442field2Line18FunctionTable OBJECT-TYPE
    SYNTAX SEQUENCE OF Enc1P1442field2Line18FunctionEntry
    MAX-ACCESS not-accessible
    STATUS     current
    DESCRIPTION
    "
    Name      : Field 2 Line 18 Function
    Menu Path : /Data/VBI over VANC Status
    Details   : Shows this line's function.
    "
::= { enc1Params 1442 }

enc1P1442field2Line18FunctionEntry OBJECT-TYPE
    SYNTAX Enc1P1442field2Line18FunctionEntry
    MAX-ACCESS not-accessible
    STATUS     current
    DESCRIPTION
    "Table Entry for Field 2 Line 18 Function"
    INDEX { slotId }
::= { enc1P1442field2Line18FunctionTable 1 }

Enc1P1442field2Line18FunctionEntry ::= SEQUENCE {
    enc1P1442field2Line18FunctionValue    Enc1E112enumObj
}

enc1P1442field2Line18FunctionValue OBJECT-TYPE
    SYNTAX     Enc1E112enumObj
    MAX-ACCESS read-only
    STATUS     current
    DESCRIPTION
    "Shows this line's function."
::= { enc1P1442field2Line18FunctionEntry 1 }

enc1P1443field2Line19FunctionTable OBJECT-TYPE
    SYNTAX SEQUENCE OF Enc1P1443field2Line19FunctionEntry
    MAX-ACCESS not-accessible
    STATUS     current
    DESCRIPTION
    "
    Name      : Field 2 Line 19 Function
    Menu Path : /Data/VBI over VANC Status
    Details   : Shows this line's function.
    "
::= { enc1Params 1443 }

enc1P1443field2Line19FunctionEntry OBJECT-TYPE
    SYNTAX Enc1P1443field2Line19FunctionEntry
    MAX-ACCESS not-accessible
    STATUS     current
    DESCRIPTION
    "Table Entry for Field 2 Line 19 Function"
    INDEX { slotId }
::= { enc1P1443field2Line19FunctionTable 1 }

Enc1P1443field2Line19FunctionEntry ::= SEQUENCE {
    enc1P1443field2Line19FunctionValue    Enc1E112enumObj
}

enc1P1443field2Line19FunctionValue OBJECT-TYPE
    SYNTAX     Enc1E112enumObj
    MAX-ACCESS read-only
    STATUS     current
    DESCRIPTION
    "Shows this line's function."
::= { enc1P1443field2Line19FunctionEntry 1 }

enc1P1444field2Line20FunctionTable OBJECT-TYPE
    SYNTAX SEQUENCE OF Enc1P1444field2Line20FunctionEntry
    MAX-ACCESS not-accessible
    STATUS     current
    DESCRIPTION
    "
    Name      : Field 2 Line 20 Function
    Menu Path : /Data/VBI over VANC Status
    Details   : Shows this line's function.
    "
::= { enc1Params 1444 }

enc1P1444field2Line20FunctionEntry OBJECT-TYPE
    SYNTAX Enc1P1444field2Line20FunctionEntry
    MAX-ACCESS not-accessible
    STATUS     current
    DESCRIPTION
    "Table Entry for Field 2 Line 20 Function"
    INDEX { slotId }
::= { enc1P1444field2Line20FunctionTable 1 }

Enc1P1444field2Line20FunctionEntry ::= SEQUENCE {
    enc1P1444field2Line20FunctionValue    Enc1E112enumObj
}

enc1P1444field2Line20FunctionValue OBJECT-TYPE
    SYNTAX     Enc1E112enumObj
    MAX-ACCESS read-only
    STATUS     current
    DESCRIPTION
    "Shows this line's function."
::= { enc1P1444field2Line20FunctionEntry 1 }

enc1P1445field2Line21FunctionTable OBJECT-TYPE
    SYNTAX SEQUENCE OF Enc1P1445field2Line21FunctionEntry
    MAX-ACCESS not-accessible
    STATUS     current
    DESCRIPTION
    "
    Name      : Field 2 Line 21 Function
    Menu Path : /Data/VBI over VANC Status
    Details   : Shows this line's function.
    "
::= { enc1Params 1445 }

enc1P1445field2Line21FunctionEntry OBJECT-TYPE
    SYNTAX Enc1P1445field2Line21FunctionEntry
    MAX-ACCESS not-accessible
    STATUS     current
    DESCRIPTION
    "Table Entry for Field 2 Line 21 Function"
    INDEX { slotId }
::= { enc1P1445field2Line21FunctionTable 1 }

Enc1P1445field2Line21FunctionEntry ::= SEQUENCE {
    enc1P1445field2Line21FunctionValue    Enc1E112enumObj
}

enc1P1445field2Line21FunctionValue OBJECT-TYPE
    SYNTAX     Enc1E112enumObj
    MAX-ACCESS read-only
    STATUS     current
    DESCRIPTION
    "Shows this line's function."
::= { enc1P1445field2Line21FunctionEntry 1 }

enc1P1446field2Line22FunctionTable OBJECT-TYPE
    SYNTAX SEQUENCE OF Enc1P1446field2Line22FunctionEntry
    MAX-ACCESS not-accessible
    STATUS     current
    DESCRIPTION
    "
    Name      : Field 2 Line 22 Function
    Menu Path : /Data/VBI over VANC Status
    Details   : Shows this line's function.
    "
::= { enc1Params 1446 }

enc1P1446field2Line22FunctionEntry OBJECT-TYPE
    SYNTAX Enc1P1446field2Line22FunctionEntry
    MAX-ACCESS not-accessible
    STATUS     current
    DESCRIPTION
    "Table Entry for Field 2 Line 22 Function"
    INDEX { slotId }
::= { enc1P1446field2Line22FunctionTable 1 }

Enc1P1446field2Line22FunctionEntry ::= SEQUENCE {
    enc1P1446field2Line22FunctionValue    Enc1E112enumObj
}

enc1P1446field2Line22FunctionValue OBJECT-TYPE
    SYNTAX     Enc1E112enumObj
    MAX-ACCESS read-only
    STATUS     current
    DESCRIPTION
    "Shows this line's function."
::= { enc1P1446field2Line22FunctionEntry 1 }

enc1P1458lossofSignalTable OBJECT-TYPE
    SYNTAX SEQUENCE OF Enc1P1458lossofSignalEntry
    MAX-ACCESS not-accessible
    STATUS     current
    DESCRIPTION
    "
    Name      : Loss of Signal
    Menu Path : /Audio/AAP 1 Configuration/General
    Details   : Indicates loss of a selected source signal.
    "
::= { enc1Params 1458 }

enc1P1458lossofSignalEntry OBJECT-TYPE
    SYNTAX Enc1P1458lossofSignalEntry
    MAX-ACCESS not-accessible
    STATUS     current
    DESCRIPTION
    "Table Entry for Loss of Signal"
    INDEX { slotId }
::= { enc1P1458lossofSignalTable 1 }

Enc1P1458lossofSignalEntry ::= SEQUENCE {
    enc1P1458lossofSignalValue    Enc1E5enumObj
}

enc1P1458lossofSignalValue OBJECT-TYPE
    SYNTAX     Enc1E5enumObj
    MAX-ACCESS read-only
    STATUS     current
    DESCRIPTION
    "Indicates loss of a selected source signal."
::= { enc1P1458lossofSignalEntry 1 }

enc1P1459maxVBVDelayTable OBJECT-TYPE
    SYNTAX SEQUENCE OF Enc1P1459maxVBVDelayEntry
    MAX-ACCESS not-accessible
    STATUS     current
    DESCRIPTION
    "
    Name      : Max VBV Delay
    Menu Path : /Video/Compression/Advanced Parameters
    Units     : msec
    Precision : 0
    Low Range : 350
    High Range: 1000
    Details   : Specify maximum VBV delay allowed in msec.

     NOTE: Precision/Units/Ranges represent the state of the
           parameter during the MIB generation, and does not
           neccessary reflect the current state of the parameter
    "
::= { enc1Params 1459 }

enc1P1459maxVBVDelayEntry OBJECT-TYPE
    SYNTAX Enc1P1459maxVBVDelayEntry
    MAX-ACCESS not-accessible
    STATUS     current
    DESCRIPTION
    "Table Entry for Max VBV Delay"
    INDEX { slotId }
::= { enc1P1459maxVBVDelayTable 1 }

Enc1P1459maxVBVDelayEntry ::= SEQUENCE {
    enc1P1459maxVBVDelayValue    INTEGER
}

enc1P1459maxVBVDelayValue OBJECT-TYPE
    SYNTAX     INTEGER
    MAX-ACCESS read-write
    STATUS     current
    DESCRIPTION
    "Specify maximum VBV delay allowed in msec."
::= { enc1P1459maxVBVDelayEntry 1 }

enc1P1460mpeg2MaxFrameSizeTable OBJECT-TYPE
    SYNTAX SEQUENCE OF Enc1P1460mpeg2MaxFrameSizeEntry
    MAX-ACCESS not-accessible
    STATUS     current
    DESCRIPTION
    "
    Name      : MPEG2 Max Frame Size
    Menu Path : /Video/Compression/Advanced Parameters
    Units     : Mbits
    Precision : 3
    Low Range : 0
    High Range: -1
    Details   : Limit for MPEG2 maximum coded frame size in bits.

     NOTE: Precision/Units/Ranges represent the state of the
           parameter during the MIB generation, and does not
           neccessary reflect the current state of the parameter
    "
::= { enc1Params 1460 }

enc1P1460mpeg2MaxFrameSizeEntry OBJECT-TYPE
    SYNTAX Enc1P1460mpeg2MaxFrameSizeEntry
    MAX-ACCESS not-accessible
    STATUS     current
    DESCRIPTION
    "Table Entry for MPEG2 Max Frame Size"
    INDEX { slotId }
::= { enc1P1460mpeg2MaxFrameSizeTable 1 }

Enc1P1460mpeg2MaxFrameSizeEntry ::= SEQUENCE {
    enc1P1460mpeg2MaxFrameSizeValue    INTEGER
}

enc1P1460mpeg2MaxFrameSizeValue OBJECT-TYPE
    SYNTAX     INTEGER
    MAX-ACCESS read-write
    STATUS     current
    DESCRIPTION
    "Limit for MPEG2 maximum coded frame size in bits."
::= { enc1P1460mpeg2MaxFrameSizeEntry 1 }

enc1P1461mpeg2MinQPTable OBJECT-TYPE
    SYNTAX SEQUENCE OF Enc1P1461mpeg2MinQPEntry
    MAX-ACCESS not-accessible
    STATUS     current
    DESCRIPTION
    "
    Name      : MPEG2 Min QP
    Menu Path : /Video/Compression/Advanced Parameters
    Units     : 
    Precision : 0
    Low Range : 0
    High Range: -1
    Details   : Specify a minimum QP for MPEG2 encoding.

     NOTE: Precision/Units/Ranges represent the state of the
           parameter during the MIB generation, and does not
           neccessary reflect the current state of the parameter
    "
::= { enc1Params 1461 }

enc1P1461mpeg2MinQPEntry OBJECT-TYPE
    SYNTAX Enc1P1461mpeg2MinQPEntry
    MAX-ACCESS not-accessible
    STATUS     current
    DESCRIPTION
    "Table Entry for MPEG2 Min QP"
    INDEX { slotId }
::= { enc1P1461mpeg2MinQPTable 1 }

Enc1P1461mpeg2MinQPEntry ::= SEQUENCE {
    enc1P1461mpeg2MinQPValue    INTEGER
}

enc1P1461mpeg2MinQPValue OBJECT-TYPE
    SYNTAX     INTEGER
    MAX-ACCESS read-write
    STATUS     current
    DESCRIPTION
    "Specify a minimum QP for MPEG2 encoding."
::= { enc1P1461mpeg2MinQPEntry 1 }

enc1P1462ecmchannelIDTable OBJECT-TYPE
    SYNTAX SEQUENCE OF Enc1P1462ecmchannelIDEntry
    MAX-ACCESS not-accessible
    STATUS     current
    DESCRIPTION
    "
    Name      : ECM Channel ID
    Menu Path : /IP Encapsulation/ATSC MH IP
    Units     : 
    Precision : 0
    Low Range : 0
    High Range: 65535
    Details   : Specifies ECM Channel ID for program.

     NOTE: Precision/Units/Ranges represent the state of the
           parameter during the MIB generation, and does not
           neccessary reflect the current state of the parameter
    "
::= { enc1Params 1462 }

enc1P1462ecmchannelIDEntry OBJECT-TYPE
    SYNTAX Enc1P1462ecmchannelIDEntry
    MAX-ACCESS not-accessible
    STATUS     current
    DESCRIPTION
    "Table Entry for ECM Channel ID"
    INDEX { slotId }
::= { enc1P1462ecmchannelIDTable 1 }

Enc1P1462ecmchannelIDEntry ::= SEQUENCE {
    enc1P1462ecmchannelIDValue    INTEGER
}

enc1P1462ecmchannelIDValue OBJECT-TYPE
    SYNTAX     INTEGER
    MAX-ACCESS read-write
    STATUS     current
    DESCRIPTION
    "Specifies ECM Channel ID for program."
::= { enc1P1462ecmchannelIDEntry 1 }

enc1P1463statmuxTable OBJECT-TYPE
    SYNTAX SEQUENCE OF Enc1P1463statmuxEntry
    MAX-ACCESS not-accessible
    STATUS     current
    DESCRIPTION
    "
    Name      : Statmux
    Menu Path : /Video/Compression/Status
    Details   : Shows whether statmux is enabled or disabled
    "
::= { enc1Params 1463 }

enc1P1463statmuxEntry OBJECT-TYPE
    SYNTAX Enc1P1463statmuxEntry
    MAX-ACCESS not-accessible
    STATUS     current
    DESCRIPTION
    "Table Entry for Statmux"
    INDEX { slotId }
::= { enc1P1463statmuxTable 1 }

Enc1P1463statmuxEntry ::= SEQUENCE {
    enc1P1463statmuxValue    Enc1E26enumObj
}

enc1P1463statmuxValue OBJECT-TYPE
    SYNTAX     Enc1E26enumObj
    MAX-ACCESS read-only
    STATUS     current
    DESCRIPTION
    "Shows whether statmux is enabled or disabled"
::= { enc1P1463statmuxEntry 1 }

enc1P1464quantizationTableTable OBJECT-TYPE
    SYNTAX SEQUENCE OF Enc1P1464quantizationTableEntry
    MAX-ACCESS not-accessible
    STATUS     current
    DESCRIPTION
    "
    Name      : Quantization Table
    Menu Path : /Video/Compression/Advanced Parameters
    Details   : Specifies quantization table for encoding.
    "
::= { enc1Params 1464 }

enc1P1464quantizationTableEntry OBJECT-TYPE
    SYNTAX Enc1P1464quantizationTableEntry
    MAX-ACCESS not-accessible
    STATUS     current
    DESCRIPTION
    "Table Entry for Quantization Table"
    INDEX { slotId }
::= { enc1P1464quantizationTableTable 1 }

Enc1P1464quantizationTableEntry ::= SEQUENCE {
    enc1P1464quantizationTableValue    Enc1E63enumObj
}

enc1P1464quantizationTableValue OBJECT-TYPE
    SYNTAX     Enc1E63enumObj
    MAX-ACCESS read-write
    STATUS     current
    DESCRIPTION
    "Specifies quantization table for encoding."
::= { enc1P1464quantizationTableEntry 1 }

enc1P1467invertFieldOrderTable OBJECT-TYPE
    SYNTAX SEQUENCE OF Enc1P1467invertFieldOrderEntry
    MAX-ACCESS not-accessible
    STATUS     current
    DESCRIPTION
    "
    Name      : Invert Field Order
    Menu Path : /Video/Compression/Advanced Parameters
    Details   : Enable/Disable inverting the field order.
    "
::= { enc1Params 1467 }

enc1P1467invertFieldOrderEntry OBJECT-TYPE
    SYNTAX Enc1P1467invertFieldOrderEntry
    MAX-ACCESS not-accessible
    STATUS     current
    DESCRIPTION
    "Table Entry for Invert Field Order"
    INDEX { slotId }
::= { enc1P1467invertFieldOrderTable 1 }

Enc1P1467invertFieldOrderEntry ::= SEQUENCE {
    enc1P1467invertFieldOrderValue    Enc1E0enumObj
}

enc1P1467invertFieldOrderValue OBJECT-TYPE
    SYNTAX     Enc1E0enumObj
    MAX-ACCESS read-write
    STATUS     current
    DESCRIPTION
    "Enable/Disable inverting the field order."
::= { enc1P1467invertFieldOrderEntry 1 }

enc1P1468forceIFrameTable OBJECT-TYPE
    SYNTAX SEQUENCE OF Enc1P1468forceIFrameEntry
    MAX-ACCESS not-accessible
    STATUS     current
    DESCRIPTION
    "
    Name      : Force I Frame
    Menu Path : /Data/Splice
    Details   : Specifies whether or not an I frame is inserted at the splice point.
    "
::= { enc1Params 1468 }

enc1P1468forceIFrameEntry OBJECT-TYPE
    SYNTAX Enc1P1468forceIFrameEntry
    MAX-ACCESS not-accessible
    STATUS     current
    DESCRIPTION
    "Table Entry for Force I Frame"
    INDEX { slotId }
::= { enc1P1468forceIFrameTable 1 }

Enc1P1468forceIFrameEntry ::= SEQUENCE {
    enc1P1468forceIFrameValue    Enc1E109enumObj
}

enc1P1468forceIFrameValue OBJECT-TYPE
    SYNTAX     Enc1E109enumObj
    MAX-ACCESS read-write
    STATUS     current
    DESCRIPTION
    "Specifies whether or not an I frame is inserted at the splice point."
::= { enc1P1468forceIFrameEntry 1 }

enc1P1469restorePrimaryInputTable OBJECT-TYPE
    SYNTAX SEQUENCE OF Enc1P1469restorePrimaryInputEntry
    MAX-ACCESS not-accessible
    STATUS     current
    DESCRIPTION
    "
    Name      : Restore Primary Input
    Menu Path : /Video/Input
    Details   : Restores primary video input.
    "
::= { enc1Params 1469 }

enc1P1469restorePrimaryInputEntry OBJECT-TYPE
    SYNTAX Enc1P1469restorePrimaryInputEntry
    MAX-ACCESS not-accessible
    STATUS     current
    DESCRIPTION
    "Table Entry for Restore Primary Input"
    INDEX { slotId }
::= { enc1P1469restorePrimaryInputTable 1 }

Enc1P1469restorePrimaryInputEntry ::= SEQUENCE {
    enc1P1469restorePrimaryInputValue    Enc1E34enumObj
}

enc1P1469restorePrimaryInputValue OBJECT-TYPE
    SYNTAX     Enc1E34enumObj
    MAX-ACCESS read-write
    STATUS     current
    DESCRIPTION
    "Restores primary video input."
::= { enc1P1469restorePrimaryInputEntry 1 }

enc1P1470serviceInfoInsertTable OBJECT-TYPE
    SYNTAX SEQUENCE OF Enc1P1470serviceInfoInsertEntry
    MAX-ACCESS not-accessible
    STATUS     current
    DESCRIPTION
    "
    Name      : Service Info Insert
    Menu Path : /Data/Closed Caption
    Details   : Specifies the closed caption service descriptor insertion behavior.
    "
::= { enc1Params 1470 }

enc1P1470serviceInfoInsertEntry OBJECT-TYPE
    SYNTAX Enc1P1470serviceInfoInsertEntry
    MAX-ACCESS not-accessible
    STATUS     current
    DESCRIPTION
    "Table Entry for Service Info Insert"
    INDEX { slotId }
::= { enc1P1470serviceInfoInsertTable 1 }

Enc1P1470serviceInfoInsertEntry ::= SEQUENCE {
    enc1P1470serviceInfoInsertValue    Enc1E119enumObj
}

enc1P1470serviceInfoInsertValue OBJECT-TYPE
    SYNTAX     Enc1E119enumObj
    MAX-ACCESS read-write
    STATUS     current
    DESCRIPTION
    "Specifies the closed caption service descriptor insertion behavior."
::= { enc1P1470serviceInfoInsertEntry 1 }

enc1P1471ccserviceDescriptorTable OBJECT-TYPE
    SYNTAX SEQUENCE OF Enc1P1471ccserviceDescriptorEntry
    MAX-ACCESS not-accessible
    STATUS     current
    DESCRIPTION
    "
    Name      : CC Service Descriptor
    Menu Path : /Data/Closed Caption
    Details   : Specifies closed caption service descriptor. Enter hexadecimal string for entire descriptor (max 250 chars).
    "
::= { enc1Params 1471 }

enc1P1471ccserviceDescriptorEntry OBJECT-TYPE
    SYNTAX Enc1P1471ccserviceDescriptorEntry
    MAX-ACCESS not-accessible
    STATUS     current
    DESCRIPTION
    "Table Entry for CC Service Descriptor"
    INDEX { slotId }
::= { enc1P1471ccserviceDescriptorTable 1 }

Enc1P1471ccserviceDescriptorEntry ::= SEQUENCE {
    enc1P1471ccserviceDescriptorValue    DisplayString
}

enc1P1471ccserviceDescriptorValue OBJECT-TYPE
    SYNTAX     DisplayString
    MAX-ACCESS read-write
    STATUS     current
    DESCRIPTION
    "Specifies closed caption service descriptor. Enter hexadecimal string for entire descriptor (max 250 chars)."
::= { enc1P1471ccserviceDescriptorEntry 1 }

enc1P1472backModuleTypeTable OBJECT-TYPE
    SYNTAX SEQUENCE OF Enc1P1472backModuleTypeEntry
    MAX-ACCESS not-accessible
    STATUS     current
    DESCRIPTION
    "
    Name      : Back Module Type
    Menu Path : /Video/Input/Status
    Details   : Indicates which back module is being used.
    "
::= { enc1Params 1472 }

enc1P1472backModuleTypeEntry OBJECT-TYPE
    SYNTAX Enc1P1472backModuleTypeEntry
    MAX-ACCESS not-accessible
    STATUS     current
    DESCRIPTION
    "Table Entry for Back Module Type"
    INDEX { slotId }
::= { enc1P1472backModuleTypeTable 1 }

Enc1P1472backModuleTypeEntry ::= SEQUENCE {
    enc1P1472backModuleTypeValue    Enc1E37enumObj
}

enc1P1472backModuleTypeValue OBJECT-TYPE
    SYNTAX     Enc1E37enumObj
    MAX-ACCESS read-only
    STATUS     current
    DESCRIPTION
    "Indicates which back module is being used."
::= { enc1P1472backModuleTypeEntry 1 }

enc1P1473nd2LanguageCodeTable OBJECT-TYPE
    SYNTAX SEQUENCE OF Enc1P1473nd2LanguageCodeEntry
    MAX-ACCESS not-accessible
    STATUS     current
    DESCRIPTION
    "
    Name      : 2nd Language Code
    Menu Path : /Audio/Audio 1
    Details   : Specifies the 2nd language code for dual mono.
    "
::= { enc1Params 1473 }

enc1P1473nd2LanguageCodeEntry OBJECT-TYPE
    SYNTAX Enc1P1473nd2LanguageCodeEntry
    MAX-ACCESS not-accessible
    STATUS     current
    DESCRIPTION
    "Table Entry for 2nd Language Code"
    INDEX { slotId }
::= { enc1P1473nd2LanguageCodeTable 1 }

Enc1P1473nd2LanguageCodeEntry ::= SEQUENCE {
    enc1P1473nd2LanguageCodeValue    DisplayString
}

enc1P1473nd2LanguageCodeValue OBJECT-TYPE
    SYNTAX     DisplayString
    MAX-ACCESS read-write
    STATUS     current
    DESCRIPTION
    "Specifies the 2nd language code for dual mono."
::= { enc1P1473nd2LanguageCodeEntry 1 }

enc1P1474nd2LanguageCodeTable OBJECT-TYPE
    SYNTAX SEQUENCE OF Enc1P1474nd2LanguageCodeEntry
    MAX-ACCESS not-accessible
    STATUS     current
    DESCRIPTION
    "
    Name      : 2nd Language Code
    Menu Path : /Audio/Audio 2
    Details   : Specifies the 2nd language code for dual mono.
    "
::= { enc1Params 1474 }

enc1P1474nd2LanguageCodeEntry OBJECT-TYPE
    SYNTAX Enc1P1474nd2LanguageCodeEntry
    MAX-ACCESS not-accessible
    STATUS     current
    DESCRIPTION
    "Table Entry for 2nd Language Code"
    INDEX { slotId }
::= { enc1P1474nd2LanguageCodeTable 1 }

Enc1P1474nd2LanguageCodeEntry ::= SEQUENCE {
    enc1P1474nd2LanguageCodeValue    DisplayString
}

enc1P1474nd2LanguageCodeValue OBJECT-TYPE
    SYNTAX     DisplayString
    MAX-ACCESS read-write
    STATUS     current
    DESCRIPTION
    "Specifies the 2nd language code for dual mono."
::= { enc1P1474nd2LanguageCodeEntry 1 }

enc1P1475nd2LanguageCodeTable OBJECT-TYPE
    SYNTAX SEQUENCE OF Enc1P1475nd2LanguageCodeEntry
    MAX-ACCESS not-accessible
    STATUS     current
    DESCRIPTION
    "
    Name      : 2nd Language Code
    Menu Path : /Audio/Audio 3
    Details   : Specifies the 2nd language code for dual mono.
    "
::= { enc1Params 1475 }

enc1P1475nd2LanguageCodeEntry OBJECT-TYPE
    SYNTAX Enc1P1475nd2LanguageCodeEntry
    MAX-ACCESS not-accessible
    STATUS     current
    DESCRIPTION
    "Table Entry for 2nd Language Code"
    INDEX { slotId }
::= { enc1P1475nd2LanguageCodeTable 1 }

Enc1P1475nd2LanguageCodeEntry ::= SEQUENCE {
    enc1P1475nd2LanguageCodeValue    DisplayString
}

enc1P1475nd2LanguageCodeValue OBJECT-TYPE
    SYNTAX     DisplayString
    MAX-ACCESS read-write
    STATUS     current
    DESCRIPTION
    "Specifies the 2nd language code for dual mono."
::= { enc1P1475nd2LanguageCodeEntry 1 }

enc1P1476nd2LanguageCodeTable OBJECT-TYPE
    SYNTAX SEQUENCE OF Enc1P1476nd2LanguageCodeEntry
    MAX-ACCESS not-accessible
    STATUS     current
    DESCRIPTION
    "
    Name      : 2nd Language Code
    Menu Path : /Audio/Audio 4
    Details   : Specifies the 2nd language code for dual mono.
    "
::= { enc1Params 1476 }

enc1P1476nd2LanguageCodeEntry OBJECT-TYPE
    SYNTAX Enc1P1476nd2LanguageCodeEntry
    MAX-ACCESS not-accessible
    STATUS     current
    DESCRIPTION
    "Table Entry for 2nd Language Code"
    INDEX { slotId }
::= { enc1P1476nd2LanguageCodeTable 1 }

Enc1P1476nd2LanguageCodeEntry ::= SEQUENCE {
    enc1P1476nd2LanguageCodeValue    DisplayString
}

enc1P1476nd2LanguageCodeValue OBJECT-TYPE
    SYNTAX     DisplayString
    MAX-ACCESS read-write
    STATUS     current
    DESCRIPTION
    "Specifies the 2nd language code for dual mono."
::= { enc1P1476nd2LanguageCodeEntry 1 }

enc1P1477nd2LanguageCodeTable OBJECT-TYPE
    SYNTAX SEQUENCE OF Enc1P1477nd2LanguageCodeEntry
    MAX-ACCESS not-accessible
    STATUS     current
    DESCRIPTION
    "
    Name      : 2nd Language Code
    Menu Path : /Audio/Audio 5
    Details   : Specifies the 2nd language code for dual mono.
    "
::= { enc1Params 1477 }

enc1P1477nd2LanguageCodeEntry OBJECT-TYPE
    SYNTAX Enc1P1477nd2LanguageCodeEntry
    MAX-ACCESS not-accessible
    STATUS     current
    DESCRIPTION
    "Table Entry for 2nd Language Code"
    INDEX { slotId }
::= { enc1P1477nd2LanguageCodeTable 1 }

Enc1P1477nd2LanguageCodeEntry ::= SEQUENCE {
    enc1P1477nd2LanguageCodeValue    DisplayString
}

enc1P1477nd2LanguageCodeValue OBJECT-TYPE
    SYNTAX     DisplayString
    MAX-ACCESS read-write
    STATUS     current
    DESCRIPTION
    "Specifies the 2nd language code for dual mono."
::= { enc1P1477nd2LanguageCodeEntry 1 }

enc1P1478nd2LanguageCodeTable OBJECT-TYPE
    SYNTAX SEQUENCE OF Enc1P1478nd2LanguageCodeEntry
    MAX-ACCESS not-accessible
    STATUS     current
    DESCRIPTION
    "
    Name      : 2nd Language Code
    Menu Path : /Audio/Audio 6
    Details   : Specifies the 2nd language code for dual mono.
    "
::= { enc1Params 1478 }

enc1P1478nd2LanguageCodeEntry OBJECT-TYPE
    SYNTAX Enc1P1478nd2LanguageCodeEntry
    MAX-ACCESS not-accessible
    STATUS     current
    DESCRIPTION
    "Table Entry for 2nd Language Code"
    INDEX { slotId }
::= { enc1P1478nd2LanguageCodeTable 1 }

Enc1P1478nd2LanguageCodeEntry ::= SEQUENCE {
    enc1P1478nd2LanguageCodeValue    DisplayString
}

enc1P1478nd2LanguageCodeValue OBJECT-TYPE
    SYNTAX     DisplayString
    MAX-ACCESS read-write
    STATUS     current
    DESCRIPTION
    "Specifies the 2nd language code for dual mono."
::= { enc1P1478nd2LanguageCodeEntry 1 }

enc1P1479nd2LanguageCodeTable OBJECT-TYPE
    SYNTAX SEQUENCE OF Enc1P1479nd2LanguageCodeEntry
    MAX-ACCESS not-accessible
    STATUS     current
    DESCRIPTION
    "
    Name      : 2nd Language Code
    Menu Path : /Audio/Audio 7
    Details   : Specifies the 2nd language code for dual mono.
    "
::= { enc1Params 1479 }

enc1P1479nd2LanguageCodeEntry OBJECT-TYPE
    SYNTAX Enc1P1479nd2LanguageCodeEntry
    MAX-ACCESS not-accessible
    STATUS     current
    DESCRIPTION
    "Table Entry for 2nd Language Code"
    INDEX { slotId }
::= { enc1P1479nd2LanguageCodeTable 1 }

Enc1P1479nd2LanguageCodeEntry ::= SEQUENCE {
    enc1P1479nd2LanguageCodeValue    DisplayString
}

enc1P1479nd2LanguageCodeValue OBJECT-TYPE
    SYNTAX     DisplayString
    MAX-ACCESS read-write
    STATUS     current
    DESCRIPTION
    "Specifies the 2nd language code for dual mono."
::= { enc1P1479nd2LanguageCodeEntry 1 }

enc1P1480nd2LanguageCodeTable OBJECT-TYPE
    SYNTAX SEQUENCE OF Enc1P1480nd2LanguageCodeEntry
    MAX-ACCESS not-accessible
    STATUS     current
    DESCRIPTION
    "
    Name      : 2nd Language Code
    Menu Path : /Audio/Audio 8
    Details   : Specifies the 2nd language code for dual mono.
    "
::= { enc1Params 1480 }

enc1P1480nd2LanguageCodeEntry OBJECT-TYPE
    SYNTAX Enc1P1480nd2LanguageCodeEntry
    MAX-ACCESS not-accessible
    STATUS     current
    DESCRIPTION
    "Table Entry for 2nd Language Code"
    INDEX { slotId }
::= { enc1P1480nd2LanguageCodeTable 1 }

Enc1P1480nd2LanguageCodeEntry ::= SEQUENCE {
    enc1P1480nd2LanguageCodeValue    DisplayString
}

enc1P1480nd2LanguageCodeValue OBJECT-TYPE
    SYNTAX     DisplayString
    MAX-ACCESS read-write
    STATUS     current
    DESCRIPTION
    "Specifies the 2nd language code for dual mono."
::= { enc1P1480nd2LanguageCodeEntry 1 }

enc1P1481isdb-TbMobileInsertionTable OBJECT-TYPE
    SYNTAX SEQUENCE OF Enc1P1481isdb-TbMobileInsertionEntry
    MAX-ACCESS not-accessible
    STATUS     current
    DESCRIPTION
    "
    Name      : ISDB-Tb Mobile Insertion
    Menu Path : /Data/Closed Caption
    Details   : Enables closed caption insertion into an ISDB-Tb Mobile stream (if one is being generated).
    "
::= { enc1Params 1481 }

enc1P1481isdb-TbMobileInsertionEntry OBJECT-TYPE
    SYNTAX Enc1P1481isdb-TbMobileInsertionEntry
    MAX-ACCESS not-accessible
    STATUS     current
    DESCRIPTION
    "Table Entry for ISDB-Tb Mobile Insertion"
    INDEX { slotId }
::= { enc1P1481isdb-TbMobileInsertionTable 1 }

Enc1P1481isdb-TbMobileInsertionEntry ::= SEQUENCE {
    enc1P1481isdb-TbMobileInsertionValue    Enc1E0enumObj
}

enc1P1481isdb-TbMobileInsertionValue OBJECT-TYPE
    SYNTAX     Enc1E0enumObj
    MAX-ACCESS read-write
    STATUS     current
    DESCRIPTION
    "Enables closed caption insertion into an ISDB-Tb Mobile stream (if one is being generated)."
::= { enc1P1481isdb-TbMobileInsertionEntry 1 }

enc1P1482isdbccpidTable OBJECT-TYPE
    SYNTAX SEQUENCE OF Enc1P1482isdbccpidEntry
    MAX-ACCESS not-accessible
    STATUS     current
    DESCRIPTION
    "
    Name      : ISDB CC PID
    Menu Path : /TS Mux/MPEG Parameters/Pip Program
    Units     : 
    Precision : 0
    Low Range : 16
    High Range: 8190
    Details   : Specifies the PID used for ISDB captions.

     NOTE: Precision/Units/Ranges represent the state of the
           parameter during the MIB generation, and does not
           neccessary reflect the current state of the parameter
    "
::= { enc1Params 1482 }

enc1P1482isdbccpidEntry OBJECT-TYPE
    SYNTAX Enc1P1482isdbccpidEntry
    MAX-ACCESS not-accessible
    STATUS     current
    DESCRIPTION
    "Table Entry for ISDB CC PID"
    INDEX { slotId }
::= { enc1P1482isdbccpidTable 1 }

Enc1P1482isdbccpidEntry ::= SEQUENCE {
    enc1P1482isdbccpidValue    INTEGER
}

enc1P1482isdbccpidValue OBJECT-TYPE
    SYNTAX     INTEGER
    MAX-ACCESS read-write
    STATUS     current
    DESCRIPTION
    "Specifies the PID used for ISDB captions."
::= { enc1P1482isdbccpidEntry 1 }

enc1P1485configurationErrorStatusTable OBJECT-TYPE
    SYNTAX SEQUENCE OF Enc1P1485configurationErrorStatusEntry
    MAX-ACCESS not-accessible
    STATUS     current
    DESCRIPTION
    "
    Name      : Configuration Error Status
    Menu Path : /Audio/AAP 1 Configuration/General
    Details   : Reports reason for configuration error, if any.
    "
::= { enc1Params 1485 }

enc1P1485configurationErrorStatusEntry OBJECT-TYPE
    SYNTAX Enc1P1485configurationErrorStatusEntry
    MAX-ACCESS not-accessible
    STATUS     current
    DESCRIPTION
    "Table Entry for Configuration Error Status"
    INDEX { slotId }
::= { enc1P1485configurationErrorStatusTable 1 }

Enc1P1485configurationErrorStatusEntry ::= SEQUENCE {
    enc1P1485configurationErrorStatusValue    DisplayString
}

enc1P1485configurationErrorStatusValue OBJECT-TYPE
    SYNTAX     DisplayString
    MAX-ACCESS read-only
    STATUS     current
    DESCRIPTION
    "Reports reason for configuration error, if any."
::= { enc1P1485configurationErrorStatusEntry 1 }

enc1P1486activateScriptTable OBJECT-TYPE
    SYNTAX SEQUENCE OF Enc1P1486activateScriptEntry
    MAX-ACCESS not-accessible
    STATUS     current
    DESCRIPTION
    "
    Name      : Activate Script
    Menu Path : /Misc/Parameter Control Script
    Details   : 
    "
::= { enc1Params 1486 }

enc1P1486activateScriptEntry OBJECT-TYPE
    SYNTAX Enc1P1486activateScriptEntry
    MAX-ACCESS not-accessible
    STATUS     current
    DESCRIPTION
    "Table Entry for Activate Script"
    INDEX { slotId }
::= { enc1P1486activateScriptTable 1 }

Enc1P1486activateScriptEntry ::= SEQUENCE {
    enc1P1486activateScriptValue    Enc1E152enumObj
}

enc1P1486activateScriptValue OBJECT-TYPE
    SYNTAX     Enc1E152enumObj
    MAX-ACCESS read-write
    STATUS     current
    DESCRIPTION
    ""
::= { enc1P1486activateScriptEntry 1 }

enc1P1487scriptPartITable OBJECT-TYPE
    SYNTAX SEQUENCE OF Enc1P1487scriptPartIEntry
    MAX-ACCESS not-accessible
    STATUS     current
    DESCRIPTION
    "
    Name      : Script (Part I)
    Menu Path : /Misc/Parameter Control Script
    Details   : First part of the script to change parameter value based on some other parameters' value
    "
::= { enc1Params 1487 }

enc1P1487scriptPartIEntry OBJECT-TYPE
    SYNTAX Enc1P1487scriptPartIEntry
    MAX-ACCESS not-accessible
    STATUS     current
    DESCRIPTION
    "Table Entry for Script (Part I)"
    INDEX { slotId }
::= { enc1P1487scriptPartITable 1 }

Enc1P1487scriptPartIEntry ::= SEQUENCE {
    enc1P1487scriptPartIValue    DisplayString
}

enc1P1487scriptPartIValue OBJECT-TYPE
    SYNTAX     DisplayString
    MAX-ACCESS read-write
    STATUS     current
    DESCRIPTION
    "First part of the script to change parameter value based on some other parameters' value"
::= { enc1P1487scriptPartIEntry 1 }

enc1P1488scriptPartIITable OBJECT-TYPE
    SYNTAX SEQUENCE OF Enc1P1488scriptPartIIEntry
    MAX-ACCESS not-accessible
    STATUS     current
    DESCRIPTION
    "
    Name      : Script (Part II)
    Menu Path : /Misc/Parameter Control Script
    Details   : Additional part of the script if there is any
    "
::= { enc1Params 1488 }

enc1P1488scriptPartIIEntry OBJECT-TYPE
    SYNTAX Enc1P1488scriptPartIIEntry
    MAX-ACCESS not-accessible
    STATUS     current
    DESCRIPTION
    "Table Entry for Script (Part II)"
    INDEX { slotId }
::= { enc1P1488scriptPartIITable 1 }

Enc1P1488scriptPartIIEntry ::= SEQUENCE {
    enc1P1488scriptPartIIValue    DisplayString
}

enc1P1488scriptPartIIValue OBJECT-TYPE
    SYNTAX     DisplayString
    MAX-ACCESS read-write
    STATUS     current
    DESCRIPTION
    "Additional part of the script if there is any"
::= { enc1P1488scriptPartIIEntry 1 }

enc1P1489scriptPartIIITable OBJECT-TYPE
    SYNTAX SEQUENCE OF Enc1P1489scriptPartIIIEntry
    MAX-ACCESS not-accessible
    STATUS     current
    DESCRIPTION
    "
    Name      : Script (Part III)
    Menu Path : /Misc/Parameter Control Script
    Details   : Additional part of the script if there is any
    "
::= { enc1Params 1489 }

enc1P1489scriptPartIIIEntry OBJECT-TYPE
    SYNTAX Enc1P1489scriptPartIIIEntry
    MAX-ACCESS not-accessible
    STATUS     current
    DESCRIPTION
    "Table Entry for Script (Part III)"
    INDEX { slotId }
::= { enc1P1489scriptPartIIITable 1 }

Enc1P1489scriptPartIIIEntry ::= SEQUENCE {
    enc1P1489scriptPartIIIValue    DisplayString
}

enc1P1489scriptPartIIIValue OBJECT-TYPE
    SYNTAX     DisplayString
    MAX-ACCESS read-write
    STATUS     current
    DESCRIPTION
    "Additional part of the script if there is any"
::= { enc1P1489scriptPartIIIEntry 1 }

enc1P1490scriptPartIVTable OBJECT-TYPE
    SYNTAX SEQUENCE OF Enc1P1490scriptPartIVEntry
    MAX-ACCESS not-accessible
    STATUS     current
    DESCRIPTION
    "
    Name      : Script (Part IV)
    Menu Path : /Misc/Parameter Control Script
    Details   : Additional part of the script if there is any
    "
::= { enc1Params 1490 }

enc1P1490scriptPartIVEntry OBJECT-TYPE
    SYNTAX Enc1P1490scriptPartIVEntry
    MAX-ACCESS not-accessible
    STATUS     current
    DESCRIPTION
    "Table Entry for Script (Part IV)"
    INDEX { slotId }
::= { enc1P1490scriptPartIVTable 1 }

Enc1P1490scriptPartIVEntry ::= SEQUENCE {
    enc1P1490scriptPartIVValue    DisplayString
}

enc1P1490scriptPartIVValue OBJECT-TYPE
    SYNTAX     DisplayString
    MAX-ACCESS read-write
    STATUS     current
    DESCRIPTION
    "Additional part of the script if there is any"
::= { enc1P1490scriptPartIVEntry 1 }

enc1P1491scriptStatusTable OBJECT-TYPE
    SYNTAX SEQUENCE OF Enc1P1491scriptStatusEntry
    MAX-ACCESS not-accessible
    STATUS     current
    DESCRIPTION
    "
    Name      : Script Status
    Menu Path : /Misc/Parameter Control Script
    Details   : Reports the parsing and active status of custom input script
    "
::= { enc1Params 1491 }

enc1P1491scriptStatusEntry OBJECT-TYPE
    SYNTAX Enc1P1491scriptStatusEntry
    MAX-ACCESS not-accessible
    STATUS     current
    DESCRIPTION
    "Table Entry for Script Status"
    INDEX { slotId }
::= { enc1P1491scriptStatusTable 1 }

Enc1P1491scriptStatusEntry ::= SEQUENCE {
    enc1P1491scriptStatusValue    DisplayString
}

enc1P1491scriptStatusValue OBJECT-TYPE
    SYNTAX     DisplayString
    MAX-ACCESS read-only
    STATUS     current
    DESCRIPTION
    "Reports the parsing and active status of custom input script"
::= { enc1P1491scriptStatusEntry 1 }

enc1P1492customInputScriptTable OBJECT-TYPE
    SYNTAX SEQUENCE OF Enc1P1492customInputScriptEntry
    MAX-ACCESS not-accessible
    STATUS     current
    DESCRIPTION
    "
    Name      : Custom Input Script
    Menu Path : /Control/GPI/Custom GPI
    Details   : Customerized GPI input script
    "
::= { enc1Params 1492 }

enc1P1492customInputScriptEntry OBJECT-TYPE
    SYNTAX Enc1P1492customInputScriptEntry
    MAX-ACCESS not-accessible
    STATUS     current
    DESCRIPTION
    "Table Entry for Custom Input Script"
    INDEX { slotId }
::= { enc1P1492customInputScriptTable 1 }

Enc1P1492customInputScriptEntry ::= SEQUENCE {
    enc1P1492customInputScriptValue    DisplayString
}

enc1P1492customInputScriptValue OBJECT-TYPE
    SYNTAX     DisplayString
    MAX-ACCESS read-write
    STATUS     current
    DESCRIPTION
    "Customerized GPI input script"
::= { enc1P1492customInputScriptEntry 1 }

enc1P1493customInputScriptcontinuedTable OBJECT-TYPE
    SYNTAX SEQUENCE OF Enc1P1493customInputScriptcontinuedEntry
    MAX-ACCESS not-accessible
    STATUS     current
    DESCRIPTION
    "
    Name      : Custom Input Script(continued)
    Menu Path : /Control/GPI/Custom GPI
    Details   : Second part of customerized GPI input script
    "
::= { enc1Params 1493 }

enc1P1493customInputScriptcontinuedEntry OBJECT-TYPE
    SYNTAX Enc1P1493customInputScriptcontinuedEntry
    MAX-ACCESS not-accessible
    STATUS     current
    DESCRIPTION
    "Table Entry for Custom Input Script(continued)"
    INDEX { slotId }
::= { enc1P1493customInputScriptcontinuedTable 1 }

Enc1P1493customInputScriptcontinuedEntry ::= SEQUENCE {
    enc1P1493customInputScriptcontinuedValue    DisplayString
}

enc1P1493customInputScriptcontinuedValue OBJECT-TYPE
    SYNTAX     DisplayString
    MAX-ACCESS read-write
    STATUS     current
    DESCRIPTION
    "Second part of customerized GPI input script"
::= { enc1P1493customInputScriptcontinuedEntry 1 }

enc1P1494customInputStatusTable OBJECT-TYPE
    SYNTAX SEQUENCE OF Enc1P1494customInputStatusEntry
    MAX-ACCESS not-accessible
    STATUS     current
    DESCRIPTION
    "
    Name      : Custom Input Status
    Menu Path : /Control/GPI/Custom GPI
    Details   : Reports the parsing and active status of custom input script
    "
::= { enc1Params 1494 }

enc1P1494customInputStatusEntry OBJECT-TYPE
    SYNTAX Enc1P1494customInputStatusEntry
    MAX-ACCESS not-accessible
    STATUS     current
    DESCRIPTION
    "Table Entry for Custom Input Status"
    INDEX { slotId }
::= { enc1P1494customInputStatusTable 1 }

Enc1P1494customInputStatusEntry ::= SEQUENCE {
    enc1P1494customInputStatusValue    DisplayString
}

enc1P1494customInputStatusValue OBJECT-TYPE
    SYNTAX     DisplayString
    MAX-ACCESS read-only
    STATUS     current
    DESCRIPTION
    "Reports the parsing and active status of custom input script"
::= { enc1P1494customInputStatusEntry 1 }

enc1P1495levelTable OBJECT-TYPE
    SYNTAX SEQUENCE OF Enc1P1495levelEntry
    MAX-ACCESS not-accessible
    STATUS     current
    DESCRIPTION
    "
    Name      : Level
    Menu Path : /Video/Compression
    Details   : Specifies the coding level.
    "
::= { enc1Params 1495 }

enc1P1495levelEntry OBJECT-TYPE
    SYNTAX Enc1P1495levelEntry
    MAX-ACCESS not-accessible
    STATUS     current
    DESCRIPTION
    "Table Entry for Level"
    INDEX { slotId }
::= { enc1P1495levelTable 1 }

Enc1P1495levelEntry ::= SEQUENCE {
    enc1P1495levelValue    Enc1E45enumObj
}

enc1P1495levelValue OBJECT-TYPE
    SYNTAX     Enc1E45enumObj
    MAX-ACCESS read-write
    STATUS     current
    DESCRIPTION
    "Specifies the coding level."
::= { enc1P1495levelEntry 1 }

enc1P1498gopSizeTable OBJECT-TYPE
    SYNTAX SEQUENCE OF Enc1P1498gopSizeEntry
    MAX-ACCESS not-accessible
    STATUS     current
    DESCRIPTION
    "
    Name      : Gop Size
    Menu Path : /Video/Pip
    Details   : Specifies GOP size to be used while encoding.
    "
::= { enc1Params 1498 }

enc1P1498gopSizeEntry OBJECT-TYPE
    SYNTAX Enc1P1498gopSizeEntry
    MAX-ACCESS not-accessible
    STATUS     current
    DESCRIPTION
    "Table Entry for Gop Size"
    INDEX { slotId }
::= { enc1P1498gopSizeTable 1 }

Enc1P1498gopSizeEntry ::= SEQUENCE {
    enc1P1498gopSizeValue    Enc1E58enumObj
}

enc1P1498gopSizeValue OBJECT-TYPE
    SYNTAX     Enc1E58enumObj
    MAX-ACCESS read-write
    STATUS     current
    DESCRIPTION
    "Specifies GOP size to be used while encoding."
::= { enc1P1498gopSizeEntry 1 }

enc1P1499resolutionTable OBJECT-TYPE
    SYNTAX SEQUENCE OF Enc1P1499resolutionEntry
    MAX-ACCESS not-accessible
    STATUS     current
    DESCRIPTION
    "
    Name      : Resolution
    Menu Path : /Video/Input
    Details   : Specifies video encoding resolution.
    "
::= { enc1Params 1499 }

enc1P1499resolutionEntry OBJECT-TYPE
    SYNTAX Enc1P1499resolutionEntry
    MAX-ACCESS not-accessible
    STATUS     current
    DESCRIPTION
    "Table Entry for Resolution"
    INDEX { slotId }
::= { enc1P1499resolutionTable 1 }

Enc1P1499resolutionEntry ::= SEQUENCE {
    enc1P1499resolutionValue    Enc1E41enumObj
}

enc1P1499resolutionValue OBJECT-TYPE
    SYNTAX     Enc1E41enumObj
    MAX-ACCESS read-write
    STATUS     current
    DESCRIPTION
    "Specifies video encoding resolution."
::= { enc1P1499resolutionEntry 1 }

enc1P1500charomaScalingListTable OBJECT-TYPE
    SYNTAX SEQUENCE OF Enc1P1500charomaScalingListEntry
    MAX-ACCESS not-accessible
    STATUS     current
    DESCRIPTION
    "
    Name      : Charoma Scaling List
    Menu Path : /Video/Compression
    Details   : Improve Sarnoff-like content.
    "
::= { enc1Params 1500 }

enc1P1500charomaScalingListEntry OBJECT-TYPE
    SYNTAX Enc1P1500charomaScalingListEntry
    MAX-ACCESS not-accessible
    STATUS     current
    DESCRIPTION
    "Table Entry for Charoma Scaling List"
    INDEX { slotId }
::= { enc1P1500charomaScalingListTable 1 }

Enc1P1500charomaScalingListEntry ::= SEQUENCE {
    enc1P1500charomaScalingListValue    Enc1E28enumObj
}

enc1P1500charomaScalingListValue OBJECT-TYPE
    SYNTAX     Enc1E28enumObj
    MAX-ACCESS read-write
    STATUS     current
    DESCRIPTION
    "Improve Sarnoff-like content."
::= { enc1P1500charomaScalingListEntry 1 }

enc1P1501epfstrengthTable OBJECT-TYPE
    SYNTAX SEQUENCE OF Enc1P1501epfstrengthEntry
    MAX-ACCESS not-accessible
    STATUS     current
    DESCRIPTION
    "
    Name      : EPF Strength
    Menu Path : /Video/Compression/Advanced Parameters
    Details   : Specifies the Edge Preservation Filter Strength.
    "
::= { enc1Params 1501 }

enc1P1501epfstrengthEntry OBJECT-TYPE
    SYNTAX Enc1P1501epfstrengthEntry
    MAX-ACCESS not-accessible
    STATUS     current
    DESCRIPTION
    "Table Entry for EPF Strength"
    INDEX { slotId }
::= { enc1P1501epfstrengthTable 1 }

Enc1P1501epfstrengthEntry ::= SEQUENCE {
    enc1P1501epfstrengthValue    Enc1E31enumObj
}

enc1P1501epfstrengthValue OBJECT-TYPE
    SYNTAX     Enc1E31enumObj
    MAX-ACCESS read-write
    STATUS     current
    DESCRIPTION
    "Specifies the Edge Preservation Filter Strength."
::= { enc1P1501epfstrengthEntry 1 }

enc1P1502lpfstrengthTable OBJECT-TYPE
    SYNTAX SEQUENCE OF Enc1P1502lpfstrengthEntry
    MAX-ACCESS not-accessible
    STATUS     current
    DESCRIPTION
    "
    Name      : LPF Strength
    Menu Path : /Video/Compression/Advanced Parameters
    Details   : Specifies the Low Pass Filter Strength.
    "
::= { enc1Params 1502 }

enc1P1502lpfstrengthEntry OBJECT-TYPE
    SYNTAX Enc1P1502lpfstrengthEntry
    MAX-ACCESS not-accessible
    STATUS     current
    DESCRIPTION
    "Table Entry for LPF Strength"
    INDEX { slotId }
::= { enc1P1502lpfstrengthTable 1 }

Enc1P1502lpfstrengthEntry ::= SEQUENCE {
    enc1P1502lpfstrengthValue    Enc1E32enumObj
}

enc1P1502lpfstrengthValue OBJECT-TYPE
    SYNTAX     Enc1E32enumObj
    MAX-ACCESS read-write
    STATUS     current
    DESCRIPTION
    "Specifies the Low Pass Filter Strength."
::= { enc1P1502lpfstrengthEntry 1 }


-- Alarm Definitions
enc1A1moduleFailureTable OBJECT-TYPE
    SYNTAX SEQUENCE OF Enc1A1moduleFailureEntry
    MAX-ACCESS not-accessible
    STATUS     current
    DESCRIPTION
    "Module Failure"
::= { enc1Alarms 1 }

enc1A1moduleFailureEntry OBJECT-TYPE
    SYNTAX Enc1A1moduleFailureEntry
    MAX-ACCESS not-accessible
    STATUS     current
    DESCRIPTION
    "Table Entry for Module Failure"
    INDEX { slotId }
::= { enc1A1moduleFailureTable 1 }

Enc1A1moduleFailureEntry ::= SEQUENCE {
    enc1A1moduleFailureEnabled    AlarmEnabled,
    enc1A1moduleFailurePriority    INTEGER,
    enc1A1moduleFailureAcknowledged    AlarmAcknowledged,
    enc1A1moduleFailureTriggerTime    INTEGER,
    enc1A1moduleFailureClearTime    INTEGER
}

enc1A1moduleFailureEnabled  OBJECT-TYPE
    SYNTAX     AlarmEnabled
    MAX-ACCESS read-write
    STATUS     current
    DESCRIPTION
        "Property to enable or disable the alarm"
::= { enc1A1moduleFailureEntry 1 }

enc1A1moduleFailurePriority  OBJECT-TYPE
    SYNTAX     INTEGER
    MAX-ACCESS read-write
    STATUS     current
    DESCRIPTION
        "Set the priority of the alarm from 1 to 10 (where 10 is highest priority)"
::= { enc1A1moduleFailureEntry 2 }

enc1A1moduleFailureAcknowledged  OBJECT-TYPE
    SYNTAX     AlarmAcknowledged
    MAX-ACCESS read-write
    STATUS     current
    DESCRIPTION
        "Acknowledge the alarm such that other clients can see that the alarm has been acknowledged"
::= { enc1A1moduleFailureEntry 3 }

enc1A1moduleFailureTriggerTime  OBJECT-TYPE
    SYNTAX     INTEGER
    MAX-ACCESS read-write
    STATUS     current
    DESCRIPTION
        "Time in 1/10 of a second that an alarm needs to stay triggered until alarm is asserted"
::= { enc1A1moduleFailureEntry 4 }

enc1A1moduleFailureClearTime  OBJECT-TYPE
    SYNTAX     INTEGER
    MAX-ACCESS read-write
    STATUS     current
    DESCRIPTION
        "Time in 1/10 of a second that an alarm needs to stay clear until alarm is unasserted"
::= { enc1A1moduleFailureEntry 5 }

enc1A2configurationErrorTable OBJECT-TYPE
    SYNTAX SEQUENCE OF Enc1A2configurationErrorEntry
    MAX-ACCESS not-accessible
    STATUS     current
    DESCRIPTION
    "Configuration Error"
::= { enc1Alarms 2 }

enc1A2configurationErrorEntry OBJECT-TYPE
    SYNTAX Enc1A2configurationErrorEntry
    MAX-ACCESS not-accessible
    STATUS     current
    DESCRIPTION
    "Table Entry for Configuration Error"
    INDEX { slotId }
::= { enc1A2configurationErrorTable 1 }

Enc1A2configurationErrorEntry ::= SEQUENCE {
    enc1A2configurationErrorEnabled    AlarmEnabled,
    enc1A2configurationErrorPriority    INTEGER,
    enc1A2configurationErrorAcknowledged    AlarmAcknowledged,
    enc1A2configurationErrorTriggerTime    INTEGER,
    enc1A2configurationErrorClearTime    INTEGER
}

enc1A2configurationErrorEnabled  OBJECT-TYPE
    SYNTAX     AlarmEnabled
    MAX-ACCESS read-write
    STATUS     current
    DESCRIPTION
        "Property to enable or disable the alarm"
::= { enc1A2configurationErrorEntry 1 }

enc1A2configurationErrorPriority  OBJECT-TYPE
    SYNTAX     INTEGER
    MAX-ACCESS read-write
    STATUS     current
    DESCRIPTION
        "Set the priority of the alarm from 1 to 10 (where 10 is highest priority)"
::= { enc1A2configurationErrorEntry 2 }

enc1A2configurationErrorAcknowledged  OBJECT-TYPE
    SYNTAX     AlarmAcknowledged
    MAX-ACCESS read-write
    STATUS     current
    DESCRIPTION
        "Acknowledge the alarm such that other clients can see that the alarm has been acknowledged"
::= { enc1A2configurationErrorEntry 3 }

enc1A2configurationErrorTriggerTime  OBJECT-TYPE
    SYNTAX     INTEGER
    MAX-ACCESS read-write
    STATUS     current
    DESCRIPTION
        "Time in 1/10 of a second that an alarm needs to stay triggered until alarm is asserted"
::= { enc1A2configurationErrorEntry 4 }

enc1A2configurationErrorClearTime  OBJECT-TYPE
    SYNTAX     INTEGER
    MAX-ACCESS read-write
    STATUS     current
    DESCRIPTION
        "Time in 1/10 of a second that an alarm needs to stay clear until alarm is unasserted"
::= { enc1A2configurationErrorEntry 5 }

enc1A3featureNotSupportedTable OBJECT-TYPE
    SYNTAX SEQUENCE OF Enc1A3featureNotSupportedEntry
    MAX-ACCESS not-accessible
    STATUS     current
    DESCRIPTION
    "Feature Not Supported"
::= { enc1Alarms 3 }

enc1A3featureNotSupportedEntry OBJECT-TYPE
    SYNTAX Enc1A3featureNotSupportedEntry
    MAX-ACCESS not-accessible
    STATUS     current
    DESCRIPTION
    "Table Entry for Feature Not Supported"
    INDEX { slotId }
::= { enc1A3featureNotSupportedTable 1 }

Enc1A3featureNotSupportedEntry ::= SEQUENCE {
    enc1A3featureNotSupportedEnabled    AlarmEnabled,
    enc1A3featureNotSupportedPriority    INTEGER,
    enc1A3featureNotSupportedAcknowledged    AlarmAcknowledged,
    enc1A3featureNotSupportedTriggerTime    INTEGER,
    enc1A3featureNotSupportedClearTime    INTEGER
}

enc1A3featureNotSupportedEnabled  OBJECT-TYPE
    SYNTAX     AlarmEnabled
    MAX-ACCESS read-write
    STATUS     current
    DESCRIPTION
        "Property to enable or disable the alarm"
::= { enc1A3featureNotSupportedEntry 1 }

enc1A3featureNotSupportedPriority  OBJECT-TYPE
    SYNTAX     INTEGER
    MAX-ACCESS read-write
    STATUS     current
    DESCRIPTION
        "Set the priority of the alarm from 1 to 10 (where 10 is highest priority)"
::= { enc1A3featureNotSupportedEntry 2 }

enc1A3featureNotSupportedAcknowledged  OBJECT-TYPE
    SYNTAX     AlarmAcknowledged
    MAX-ACCESS read-write
    STATUS     current
    DESCRIPTION
        "Acknowledge the alarm such that other clients can see that the alarm has been acknowledged"
::= { enc1A3featureNotSupportedEntry 3 }

enc1A3featureNotSupportedTriggerTime  OBJECT-TYPE
    SYNTAX     INTEGER
    MAX-ACCESS read-write
    STATUS     current
    DESCRIPTION
        "Time in 1/10 of a second that an alarm needs to stay triggered until alarm is asserted"
::= { enc1A3featureNotSupportedEntry 4 }

enc1A3featureNotSupportedClearTime  OBJECT-TYPE
    SYNTAX     INTEGER
    MAX-ACCESS read-write
    STATUS     current
    DESCRIPTION
        "Time in 1/10 of a second that an alarm needs to stay clear until alarm is unasserted"
::= { enc1A3featureNotSupportedEntry 5 }

enc1A4videoLossOfSignalTable OBJECT-TYPE
    SYNTAX SEQUENCE OF Enc1A4videoLossOfSignalEntry
    MAX-ACCESS not-accessible
    STATUS     current
    DESCRIPTION
    "Video Loss Of Signal"
::= { enc1Alarms 4 }

enc1A4videoLossOfSignalEntry OBJECT-TYPE
    SYNTAX Enc1A4videoLossOfSignalEntry
    MAX-ACCESS not-accessible
    STATUS     current
    DESCRIPTION
    "Table Entry for Video Loss Of Signal"
    INDEX { slotId }
::= { enc1A4videoLossOfSignalTable 1 }

Enc1A4videoLossOfSignalEntry ::= SEQUENCE {
    enc1A4videoLossOfSignalEnabled    AlarmEnabled,
    enc1A4videoLossOfSignalPriority    INTEGER,
    enc1A4videoLossOfSignalAcknowledged    AlarmAcknowledged,
    enc1A4videoLossOfSignalTriggerTime    INTEGER,
    enc1A4videoLossOfSignalClearTime    INTEGER
}

enc1A4videoLossOfSignalEnabled  OBJECT-TYPE
    SYNTAX     AlarmEnabled
    MAX-ACCESS read-write
    STATUS     current
    DESCRIPTION
        "Property to enable or disable the alarm"
::= { enc1A4videoLossOfSignalEntry 1 }

enc1A4videoLossOfSignalPriority  OBJECT-TYPE
    SYNTAX     INTEGER
    MAX-ACCESS read-write
    STATUS     current
    DESCRIPTION
        "Set the priority of the alarm from 1 to 10 (where 10 is highest priority)"
::= { enc1A4videoLossOfSignalEntry 2 }

enc1A4videoLossOfSignalAcknowledged  OBJECT-TYPE
    SYNTAX     AlarmAcknowledged
    MAX-ACCESS read-write
    STATUS     current
    DESCRIPTION
        "Acknowledge the alarm such that other clients can see that the alarm has been acknowledged"
::= { enc1A4videoLossOfSignalEntry 3 }

enc1A4videoLossOfSignalTriggerTime  OBJECT-TYPE
    SYNTAX     INTEGER
    MAX-ACCESS read-write
    STATUS     current
    DESCRIPTION
        "Time in 1/10 of a second that an alarm needs to stay triggered until alarm is asserted"
::= { enc1A4videoLossOfSignalEntry 4 }

enc1A4videoLossOfSignalClearTime  OBJECT-TYPE
    SYNTAX     INTEGER
    MAX-ACCESS read-write
    STATUS     current
    DESCRIPTION
        "Time in 1/10 of a second that an alarm needs to stay clear until alarm is unasserted"
::= { enc1A4videoLossOfSignalEntry 5 }

enc1A5incorrectInputVideoFormatTable OBJECT-TYPE
    SYNTAX SEQUENCE OF Enc1A5incorrectInputVideoFormatEntry
    MAX-ACCESS not-accessible
    STATUS     current
    DESCRIPTION
    "Incorrect Input Video Format"
::= { enc1Alarms 5 }

enc1A5incorrectInputVideoFormatEntry OBJECT-TYPE
    SYNTAX Enc1A5incorrectInputVideoFormatEntry
    MAX-ACCESS not-accessible
    STATUS     current
    DESCRIPTION
    "Table Entry for Incorrect Input Video Format"
    INDEX { slotId }
::= { enc1A5incorrectInputVideoFormatTable 1 }

Enc1A5incorrectInputVideoFormatEntry ::= SEQUENCE {
    enc1A5incorrectInputVideoFormatEnabled    AlarmEnabled,
    enc1A5incorrectInputVideoFormatPriority    INTEGER,
    enc1A5incorrectInputVideoFormatAcknowledged    AlarmAcknowledged,
    enc1A5incorrectInputVideoFormatTriggerTime    INTEGER,
    enc1A5incorrectInputVideoFormatClearTime    INTEGER
}

enc1A5incorrectInputVideoFormatEnabled  OBJECT-TYPE
    SYNTAX     AlarmEnabled
    MAX-ACCESS read-write
    STATUS     current
    DESCRIPTION
        "Property to enable or disable the alarm"
::= { enc1A5incorrectInputVideoFormatEntry 1 }

enc1A5incorrectInputVideoFormatPriority  OBJECT-TYPE
    SYNTAX     INTEGER
    MAX-ACCESS read-write
    STATUS     current
    DESCRIPTION
        "Set the priority of the alarm from 1 to 10 (where 10 is highest priority)"
::= { enc1A5incorrectInputVideoFormatEntry 2 }

enc1A5incorrectInputVideoFormatAcknowledged  OBJECT-TYPE
    SYNTAX     AlarmAcknowledged
    MAX-ACCESS read-write
    STATUS     current
    DESCRIPTION
        "Acknowledge the alarm such that other clients can see that the alarm has been acknowledged"
::= { enc1A5incorrectInputVideoFormatEntry 3 }

enc1A5incorrectInputVideoFormatTriggerTime  OBJECT-TYPE
    SYNTAX     INTEGER
    MAX-ACCESS read-write
    STATUS     current
    DESCRIPTION
        "Time in 1/10 of a second that an alarm needs to stay triggered until alarm is asserted"
::= { enc1A5incorrectInputVideoFormatEntry 4 }

enc1A5incorrectInputVideoFormatClearTime  OBJECT-TYPE
    SYNTAX     INTEGER
    MAX-ACCESS read-write
    STATUS     current
    DESCRIPTION
        "Time in 1/10 of a second that an alarm needs to stay clear until alarm is unasserted"
::= { enc1A5incorrectInputVideoFormatEntry 5 }

enc1A6errorsInVideoInputSignalTable OBJECT-TYPE
    SYNTAX SEQUENCE OF Enc1A6errorsInVideoInputSignalEntry
    MAX-ACCESS not-accessible
    STATUS     current
    DESCRIPTION
    "Errors In Video Input Signal"
::= { enc1Alarms 6 }

enc1A6errorsInVideoInputSignalEntry OBJECT-TYPE
    SYNTAX Enc1A6errorsInVideoInputSignalEntry
    MAX-ACCESS not-accessible
    STATUS     current
    DESCRIPTION
    "Table Entry for Errors In Video Input Signal"
    INDEX { slotId }
::= { enc1A6errorsInVideoInputSignalTable 1 }

Enc1A6errorsInVideoInputSignalEntry ::= SEQUENCE {
    enc1A6errorsInVideoInputSignalEnabled    AlarmEnabled,
    enc1A6errorsInVideoInputSignalPriority    INTEGER,
    enc1A6errorsInVideoInputSignalAcknowledged    AlarmAcknowledged,
    enc1A6errorsInVideoInputSignalTriggerTime    INTEGER,
    enc1A6errorsInVideoInputSignalClearTime    INTEGER
}

enc1A6errorsInVideoInputSignalEnabled  OBJECT-TYPE
    SYNTAX     AlarmEnabled
    MAX-ACCESS read-write
    STATUS     current
    DESCRIPTION
        "Property to enable or disable the alarm"
::= { enc1A6errorsInVideoInputSignalEntry 1 }

enc1A6errorsInVideoInputSignalPriority  OBJECT-TYPE
    SYNTAX     INTEGER
    MAX-ACCESS read-write
    STATUS     current
    DESCRIPTION
        "Set the priority of the alarm from 1 to 10 (where 10 is highest priority)"
::= { enc1A6errorsInVideoInputSignalEntry 2 }

enc1A6errorsInVideoInputSignalAcknowledged  OBJECT-TYPE
    SYNTAX     AlarmAcknowledged
    MAX-ACCESS read-write
    STATUS     current
    DESCRIPTION
        "Acknowledge the alarm such that other clients can see that the alarm has been acknowledged"
::= { enc1A6errorsInVideoInputSignalEntry 3 }

enc1A6errorsInVideoInputSignalTriggerTime  OBJECT-TYPE
    SYNTAX     INTEGER
    MAX-ACCESS read-write
    STATUS     current
    DESCRIPTION
        "Time in 1/10 of a second that an alarm needs to stay triggered until alarm is asserted"
::= { enc1A6errorsInVideoInputSignalEntry 4 }

enc1A6errorsInVideoInputSignalClearTime  OBJECT-TYPE
    SYNTAX     INTEGER
    MAX-ACCESS read-write
    STATUS     current
    DESCRIPTION
        "Time in 1/10 of a second that an alarm needs to stay clear until alarm is unasserted"
::= { enc1A6errorsInVideoInputSignalEntry 5 }

enc1A7audioLossOfSignalTable OBJECT-TYPE
    SYNTAX SEQUENCE OF Enc1A7audioLossOfSignalEntry
    MAX-ACCESS not-accessible
    STATUS     current
    DESCRIPTION
    "Audio Loss Of Signal"
::= { enc1Alarms 7 }

enc1A7audioLossOfSignalEntry OBJECT-TYPE
    SYNTAX Enc1A7audioLossOfSignalEntry
    MAX-ACCESS not-accessible
    STATUS     current
    DESCRIPTION
    "Table Entry for Audio Loss Of Signal"
    INDEX { slotId }
::= { enc1A7audioLossOfSignalTable 1 }

Enc1A7audioLossOfSignalEntry ::= SEQUENCE {
    enc1A7audioLossOfSignalEnabled    AlarmEnabled,
    enc1A7audioLossOfSignalPriority    INTEGER,
    enc1A7audioLossOfSignalAcknowledged    AlarmAcknowledged,
    enc1A7audioLossOfSignalTriggerTime    INTEGER,
    enc1A7audioLossOfSignalClearTime    INTEGER
}

enc1A7audioLossOfSignalEnabled  OBJECT-TYPE
    SYNTAX     AlarmEnabled
    MAX-ACCESS read-write
    STATUS     current
    DESCRIPTION
        "Property to enable or disable the alarm"
::= { enc1A7audioLossOfSignalEntry 1 }

enc1A7audioLossOfSignalPriority  OBJECT-TYPE
    SYNTAX     INTEGER
    MAX-ACCESS read-write
    STATUS     current
    DESCRIPTION
        "Set the priority of the alarm from 1 to 10 (where 10 is highest priority)"
::= { enc1A7audioLossOfSignalEntry 2 }

enc1A7audioLossOfSignalAcknowledged  OBJECT-TYPE
    SYNTAX     AlarmAcknowledged
    MAX-ACCESS read-write
    STATUS     current
    DESCRIPTION
        "Acknowledge the alarm such that other clients can see that the alarm has been acknowledged"
::= { enc1A7audioLossOfSignalEntry 3 }

enc1A7audioLossOfSignalTriggerTime  OBJECT-TYPE
    SYNTAX     INTEGER
    MAX-ACCESS read-write
    STATUS     current
    DESCRIPTION
        "Time in 1/10 of a second that an alarm needs to stay triggered until alarm is asserted"
::= { enc1A7audioLossOfSignalEntry 4 }

enc1A7audioLossOfSignalClearTime  OBJECT-TYPE
    SYNTAX     INTEGER
    MAX-ACCESS read-write
    STATUS     current
    DESCRIPTION
        "Time in 1/10 of a second that an alarm needs to stay clear until alarm is unasserted"
::= { enc1A7audioLossOfSignalEntry 5 }

enc1A8audioEmbeddedChannelIsNotPresentTable OBJECT-TYPE
    SYNTAX SEQUENCE OF Enc1A8audioEmbeddedChannelIsNotPresentEntry
    MAX-ACCESS not-accessible
    STATUS     current
    DESCRIPTION
    "Audio Embedded Channel Is Not Present"
::= { enc1Alarms 8 }

enc1A8audioEmbeddedChannelIsNotPresentEntry OBJECT-TYPE
    SYNTAX Enc1A8audioEmbeddedChannelIsNotPresentEntry
    MAX-ACCESS not-accessible
    STATUS     current
    DESCRIPTION
    "Table Entry for Audio Embedded Channel Is Not Present"
    INDEX { slotId }
::= { enc1A8audioEmbeddedChannelIsNotPresentTable 1 }

Enc1A8audioEmbeddedChannelIsNotPresentEntry ::= SEQUENCE {
    enc1A8audioEmbeddedChannelIsNotPresentEnabled    AlarmEnabled,
    enc1A8audioEmbeddedChannelIsNotPresentPriority    INTEGER,
    enc1A8audioEmbeddedChannelIsNotPresentAcknowledged    AlarmAcknowledged,
    enc1A8audioEmbeddedChannelIsNotPresentTriggerTime    INTEGER,
    enc1A8audioEmbeddedChannelIsNotPresentClearTime    INTEGER
}

enc1A8audioEmbeddedChannelIsNotPresentEnabled  OBJECT-TYPE
    SYNTAX     AlarmEnabled
    MAX-ACCESS read-write
    STATUS     current
    DESCRIPTION
        "Property to enable or disable the alarm"
::= { enc1A8audioEmbeddedChannelIsNotPresentEntry 1 }

enc1A8audioEmbeddedChannelIsNotPresentPriority  OBJECT-TYPE
    SYNTAX     INTEGER
    MAX-ACCESS read-write
    STATUS     current
    DESCRIPTION
        "Set the priority of the alarm from 1 to 10 (where 10 is highest priority)"
::= { enc1A8audioEmbeddedChannelIsNotPresentEntry 2 }

enc1A8audioEmbeddedChannelIsNotPresentAcknowledged  OBJECT-TYPE
    SYNTAX     AlarmAcknowledged
    MAX-ACCESS read-write
    STATUS     current
    DESCRIPTION
        "Acknowledge the alarm such that other clients can see that the alarm has been acknowledged"
::= { enc1A8audioEmbeddedChannelIsNotPresentEntry 3 }

enc1A8audioEmbeddedChannelIsNotPresentTriggerTime  OBJECT-TYPE
    SYNTAX     INTEGER
    MAX-ACCESS read-write
    STATUS     current
    DESCRIPTION
        "Time in 1/10 of a second that an alarm needs to stay triggered until alarm is asserted"
::= { enc1A8audioEmbeddedChannelIsNotPresentEntry 4 }

enc1A8audioEmbeddedChannelIsNotPresentClearTime  OBJECT-TYPE
    SYNTAX     INTEGER
    MAX-ACCESS read-write
    STATUS     current
    DESCRIPTION
        "Time in 1/10 of a second that an alarm needs to stay clear until alarm is unasserted"
::= { enc1A8audioEmbeddedChannelIsNotPresentEntry 5 }

enc1A9extCompressedAudioFormatNotSupportedTable OBJECT-TYPE
    SYNTAX SEQUENCE OF Enc1A9extCompressedAudioFormatNotSupportedEntry
    MAX-ACCESS not-accessible
    STATUS     current
    DESCRIPTION
    "Ext Compressed Audio Format Not Supported"
::= { enc1Alarms 9 }

enc1A9extCompressedAudioFormatNotSupportedEntry OBJECT-TYPE
    SYNTAX Enc1A9extCompressedAudioFormatNotSupportedEntry
    MAX-ACCESS not-accessible
    STATUS     current
    DESCRIPTION
    "Table Entry for Ext Compressed Audio Format Not Supported"
    INDEX { slotId }
::= { enc1A9extCompressedAudioFormatNotSupportedTable 1 }

Enc1A9extCompressedAudioFormatNotSupportedEntry ::= SEQUENCE {
    enc1A9extCompressedAudioFormatNotSupportedEnabled    AlarmEnabled,
    enc1A9extCompressedAudioFormatNotSupportedPriority    INTEGER,
    enc1A9extCompressedAudioFormatNotSupportedAcknowledged    AlarmAcknowledged,
    enc1A9extCompressedAudioFormatNotSupportedTriggerTime    INTEGER,
    enc1A9extCompressedAudioFormatNotSupportedClearTime    INTEGER
}

enc1A9extCompressedAudioFormatNotSupportedEnabled  OBJECT-TYPE
    SYNTAX     AlarmEnabled
    MAX-ACCESS read-write
    STATUS     current
    DESCRIPTION
        "Property to enable or disable the alarm"
::= { enc1A9extCompressedAudioFormatNotSupportedEntry 1 }

enc1A9extCompressedAudioFormatNotSupportedPriority  OBJECT-TYPE
    SYNTAX     INTEGER
    MAX-ACCESS read-write
    STATUS     current
    DESCRIPTION
        "Set the priority of the alarm from 1 to 10 (where 10 is highest priority)"
::= { enc1A9extCompressedAudioFormatNotSupportedEntry 2 }

enc1A9extCompressedAudioFormatNotSupportedAcknowledged  OBJECT-TYPE
    SYNTAX     AlarmAcknowledged
    MAX-ACCESS read-write
    STATUS     current
    DESCRIPTION
        "Acknowledge the alarm such that other clients can see that the alarm has been acknowledged"
::= { enc1A9extCompressedAudioFormatNotSupportedEntry 3 }

enc1A9extCompressedAudioFormatNotSupportedTriggerTime  OBJECT-TYPE
    SYNTAX     INTEGER
    MAX-ACCESS read-write
    STATUS     current
    DESCRIPTION
        "Time in 1/10 of a second that an alarm needs to stay triggered until alarm is asserted"
::= { enc1A9extCompressedAudioFormatNotSupportedEntry 4 }

enc1A9extCompressedAudioFormatNotSupportedClearTime  OBJECT-TYPE
    SYNTAX     INTEGER
    MAX-ACCESS read-write
    STATUS     current
    DESCRIPTION
        "Time in 1/10 of a second that an alarm needs to stay clear until alarm is unasserted"
::= { enc1A9extCompressedAudioFormatNotSupportedEntry 5 }

enc1A10audioConfigurationErrorTable OBJECT-TYPE
    SYNTAX SEQUENCE OF Enc1A10audioConfigurationErrorEntry
    MAX-ACCESS not-accessible
    STATUS     current
    DESCRIPTION
    "Audio Configuration Error"
::= { enc1Alarms 10 }

enc1A10audioConfigurationErrorEntry OBJECT-TYPE
    SYNTAX Enc1A10audioConfigurationErrorEntry
    MAX-ACCESS not-accessible
    STATUS     current
    DESCRIPTION
    "Table Entry for Audio Configuration Error"
    INDEX { slotId }
::= { enc1A10audioConfigurationErrorTable 1 }

Enc1A10audioConfigurationErrorEntry ::= SEQUENCE {
    enc1A10audioConfigurationErrorEnabled    AlarmEnabled,
    enc1A10audioConfigurationErrorPriority    INTEGER,
    enc1A10audioConfigurationErrorAcknowledged    AlarmAcknowledged,
    enc1A10audioConfigurationErrorTriggerTime    INTEGER,
    enc1A10audioConfigurationErrorClearTime    INTEGER
}

enc1A10audioConfigurationErrorEnabled  OBJECT-TYPE
    SYNTAX     AlarmEnabled
    MAX-ACCESS read-write
    STATUS     current
    DESCRIPTION
        "Property to enable or disable the alarm"
::= { enc1A10audioConfigurationErrorEntry 1 }

enc1A10audioConfigurationErrorPriority  OBJECT-TYPE
    SYNTAX     INTEGER
    MAX-ACCESS read-write
    STATUS     current
    DESCRIPTION
        "Set the priority of the alarm from 1 to 10 (where 10 is highest priority)"
::= { enc1A10audioConfigurationErrorEntry 2 }

enc1A10audioConfigurationErrorAcknowledged  OBJECT-TYPE
    SYNTAX     AlarmAcknowledged
    MAX-ACCESS read-write
    STATUS     current
    DESCRIPTION
        "Acknowledge the alarm such that other clients can see that the alarm has been acknowledged"
::= { enc1A10audioConfigurationErrorEntry 3 }

enc1A10audioConfigurationErrorTriggerTime  OBJECT-TYPE
    SYNTAX     INTEGER
    MAX-ACCESS read-write
    STATUS     current
    DESCRIPTION
        "Time in 1/10 of a second that an alarm needs to stay triggered until alarm is asserted"
::= { enc1A10audioConfigurationErrorEntry 4 }

enc1A10audioConfigurationErrorClearTime  OBJECT-TYPE
    SYNTAX     INTEGER
    MAX-ACCESS read-write
    STATUS     current
    DESCRIPTION
        "Time in 1/10 of a second that an alarm needs to stay clear until alarm is unasserted"
::= { enc1A10audioConfigurationErrorEntry 5 }

enc1A11audioVideoSyncAdjustTable OBJECT-TYPE
    SYNTAX SEQUENCE OF Enc1A11audioVideoSyncAdjustEntry
    MAX-ACCESS not-accessible
    STATUS     current
    DESCRIPTION
    "Audio/Video Sync Adjust"
::= { enc1Alarms 11 }

enc1A11audioVideoSyncAdjustEntry OBJECT-TYPE
    SYNTAX Enc1A11audioVideoSyncAdjustEntry
    MAX-ACCESS not-accessible
    STATUS     current
    DESCRIPTION
    "Table Entry for Audio/Video Sync Adjust"
    INDEX { slotId }
::= { enc1A11audioVideoSyncAdjustTable 1 }

Enc1A11audioVideoSyncAdjustEntry ::= SEQUENCE {
    enc1A11audioVideoSyncAdjustEnabled    AlarmEnabled,
    enc1A11audioVideoSyncAdjustPriority    INTEGER,
    enc1A11audioVideoSyncAdjustAcknowledged    AlarmAcknowledged,
    enc1A11audioVideoSyncAdjustTriggerTime    INTEGER,
    enc1A11audioVideoSyncAdjustClearTime    INTEGER
}

enc1A11audioVideoSyncAdjustEnabled  OBJECT-TYPE
    SYNTAX     AlarmEnabled
    MAX-ACCESS read-write
    STATUS     current
    DESCRIPTION
        "Property to enable or disable the alarm"
::= { enc1A11audioVideoSyncAdjustEntry 1 }

enc1A11audioVideoSyncAdjustPriority  OBJECT-TYPE
    SYNTAX     INTEGER
    MAX-ACCESS read-write
    STATUS     current
    DESCRIPTION
        "Set the priority of the alarm from 1 to 10 (where 10 is highest priority)"
::= { enc1A11audioVideoSyncAdjustEntry 2 }

enc1A11audioVideoSyncAdjustAcknowledged  OBJECT-TYPE
    SYNTAX     AlarmAcknowledged
    MAX-ACCESS read-write
    STATUS     current
    DESCRIPTION
        "Acknowledge the alarm such that other clients can see that the alarm has been acknowledged"
::= { enc1A11audioVideoSyncAdjustEntry 3 }

enc1A11audioVideoSyncAdjustTriggerTime  OBJECT-TYPE
    SYNTAX     INTEGER
    MAX-ACCESS read-write
    STATUS     current
    DESCRIPTION
        "Time in 1/10 of a second that an alarm needs to stay triggered until alarm is asserted"
::= { enc1A11audioVideoSyncAdjustEntry 4 }

enc1A11audioVideoSyncAdjustClearTime  OBJECT-TYPE
    SYNTAX     INTEGER
    MAX-ACCESS read-write
    STATUS     current
    DESCRIPTION
        "Time in 1/10 of a second that an alarm needs to stay clear until alarm is unasserted"
::= { enc1A11audioVideoSyncAdjustEntry 5 }

enc1A12audioResourceErrorTable OBJECT-TYPE
    SYNTAX SEQUENCE OF Enc1A12audioResourceErrorEntry
    MAX-ACCESS not-accessible
    STATUS     current
    DESCRIPTION
    "Audio Resource Error"
::= { enc1Alarms 12 }

enc1A12audioResourceErrorEntry OBJECT-TYPE
    SYNTAX Enc1A12audioResourceErrorEntry
    MAX-ACCESS not-accessible
    STATUS     current
    DESCRIPTION
    "Table Entry for Audio Resource Error"
    INDEX { slotId }
::= { enc1A12audioResourceErrorTable 1 }

Enc1A12audioResourceErrorEntry ::= SEQUENCE {
    enc1A12audioResourceErrorEnabled    AlarmEnabled,
    enc1A12audioResourceErrorPriority    INTEGER,
    enc1A12audioResourceErrorAcknowledged    AlarmAcknowledged,
    enc1A12audioResourceErrorTriggerTime    INTEGER,
    enc1A12audioResourceErrorClearTime    INTEGER
}

enc1A12audioResourceErrorEnabled  OBJECT-TYPE
    SYNTAX     AlarmEnabled
    MAX-ACCESS read-write
    STATUS     current
    DESCRIPTION
        "Property to enable or disable the alarm"
::= { enc1A12audioResourceErrorEntry 1 }

enc1A12audioResourceErrorPriority  OBJECT-TYPE
    SYNTAX     INTEGER
    MAX-ACCESS read-write
    STATUS     current
    DESCRIPTION
        "Set the priority of the alarm from 1 to 10 (where 10 is highest priority)"
::= { enc1A12audioResourceErrorEntry 2 }

enc1A12audioResourceErrorAcknowledged  OBJECT-TYPE
    SYNTAX     AlarmAcknowledged
    MAX-ACCESS read-write
    STATUS     current
    DESCRIPTION
        "Acknowledge the alarm such that other clients can see that the alarm has been acknowledged"
::= { enc1A12audioResourceErrorEntry 3 }

enc1A12audioResourceErrorTriggerTime  OBJECT-TYPE
    SYNTAX     INTEGER
    MAX-ACCESS read-write
    STATUS     current
    DESCRIPTION
        "Time in 1/10 of a second that an alarm needs to stay triggered until alarm is asserted"
::= { enc1A12audioResourceErrorEntry 4 }

enc1A12audioResourceErrorClearTime  OBJECT-TYPE
    SYNTAX     INTEGER
    MAX-ACCESS read-write
    STATUS     current
    DESCRIPTION
        "Time in 1/10 of a second that an alarm needs to stay clear until alarm is unasserted"
::= { enc1A12audioResourceErrorEntry 5 }

enc1A13vancdataExceedsBandwidthAllocationTable OBJECT-TYPE
    SYNTAX SEQUENCE OF Enc1A13vancdataExceedsBandwidthAllocationEntry
    MAX-ACCESS not-accessible
    STATUS     current
    DESCRIPTION
    "VANC Data Exceeds Bandwidth Allocation"
::= { enc1Alarms 13 }

enc1A13vancdataExceedsBandwidthAllocationEntry OBJECT-TYPE
    SYNTAX Enc1A13vancdataExceedsBandwidthAllocationEntry
    MAX-ACCESS not-accessible
    STATUS     current
    DESCRIPTION
    "Table Entry for VANC Data Exceeds Bandwidth Allocation"
    INDEX { slotId }
::= { enc1A13vancdataExceedsBandwidthAllocationTable 1 }

Enc1A13vancdataExceedsBandwidthAllocationEntry ::= SEQUENCE {
    enc1A13vancdataExceedsBandwidthAllocationEnabled    AlarmEnabled,
    enc1A13vancdataExceedsBandwidthAllocationPriority    INTEGER,
    enc1A13vancdataExceedsBandwidthAllocationAcknowledged    AlarmAcknowledged,
    enc1A13vancdataExceedsBandwidthAllocationTriggerTime    INTEGER,
    enc1A13vancdataExceedsBandwidthAllocationClearTime    INTEGER
}

enc1A13vancdataExceedsBandwidthAllocationEnabled  OBJECT-TYPE
    SYNTAX     AlarmEnabled
    MAX-ACCESS read-write
    STATUS     current
    DESCRIPTION
        "Property to enable or disable the alarm"
::= { enc1A13vancdataExceedsBandwidthAllocationEntry 1 }

enc1A13vancdataExceedsBandwidthAllocationPriority  OBJECT-TYPE
    SYNTAX     INTEGER
    MAX-ACCESS read-write
    STATUS     current
    DESCRIPTION
        "Set the priority of the alarm from 1 to 10 (where 10 is highest priority)"
::= { enc1A13vancdataExceedsBandwidthAllocationEntry 2 }

enc1A13vancdataExceedsBandwidthAllocationAcknowledged  OBJECT-TYPE
    SYNTAX     AlarmAcknowledged
    MAX-ACCESS read-write
    STATUS     current
    DESCRIPTION
        "Acknowledge the alarm such that other clients can see that the alarm has been acknowledged"
::= { enc1A13vancdataExceedsBandwidthAllocationEntry 3 }

enc1A13vancdataExceedsBandwidthAllocationTriggerTime  OBJECT-TYPE
    SYNTAX     INTEGER
    MAX-ACCESS read-write
    STATUS     current
    DESCRIPTION
        "Time in 1/10 of a second that an alarm needs to stay triggered until alarm is asserted"
::= { enc1A13vancdataExceedsBandwidthAllocationEntry 4 }

enc1A13vancdataExceedsBandwidthAllocationClearTime  OBJECT-TYPE
    SYNTAX     INTEGER
    MAX-ACCESS read-write
    STATUS     current
    DESCRIPTION
        "Time in 1/10 of a second that an alarm needs to stay clear until alarm is unasserted"
::= { enc1A13vancdataExceedsBandwidthAllocationEntry 5 }

enc1A14vancdataDiscardedDueToPacketErrorTable OBJECT-TYPE
    SYNTAX SEQUENCE OF Enc1A14vancdataDiscardedDueToPacketErrorEntry
    MAX-ACCESS not-accessible
    STATUS     current
    DESCRIPTION
    "VANC Data Discarded Due To Packet Error"
::= { enc1Alarms 14 }

enc1A14vancdataDiscardedDueToPacketErrorEntry OBJECT-TYPE
    SYNTAX Enc1A14vancdataDiscardedDueToPacketErrorEntry
    MAX-ACCESS not-accessible
    STATUS     current
    DESCRIPTION
    "Table Entry for VANC Data Discarded Due To Packet Error"
    INDEX { slotId }
::= { enc1A14vancdataDiscardedDueToPacketErrorTable 1 }

Enc1A14vancdataDiscardedDueToPacketErrorEntry ::= SEQUENCE {
    enc1A14vancdataDiscardedDueToPacketErrorEnabled    AlarmEnabled,
    enc1A14vancdataDiscardedDueToPacketErrorPriority    INTEGER,
    enc1A14vancdataDiscardedDueToPacketErrorAcknowledged    AlarmAcknowledged,
    enc1A14vancdataDiscardedDueToPacketErrorTriggerTime    INTEGER,
    enc1A14vancdataDiscardedDueToPacketErrorClearTime    INTEGER
}

enc1A14vancdataDiscardedDueToPacketErrorEnabled  OBJECT-TYPE
    SYNTAX     AlarmEnabled
    MAX-ACCESS read-write
    STATUS     current
    DESCRIPTION
        "Property to enable or disable the alarm"
::= { enc1A14vancdataDiscardedDueToPacketErrorEntry 1 }

enc1A14vancdataDiscardedDueToPacketErrorPriority  OBJECT-TYPE
    SYNTAX     INTEGER
    MAX-ACCESS read-write
    STATUS     current
    DESCRIPTION
        "Set the priority of the alarm from 1 to 10 (where 10 is highest priority)"
::= { enc1A14vancdataDiscardedDueToPacketErrorEntry 2 }

enc1A14vancdataDiscardedDueToPacketErrorAcknowledged  OBJECT-TYPE
    SYNTAX     AlarmAcknowledged
    MAX-ACCESS read-write
    STATUS     current
    DESCRIPTION
        "Acknowledge the alarm such that other clients can see that the alarm has been acknowledged"
::= { enc1A14vancdataDiscardedDueToPacketErrorEntry 3 }

enc1A14vancdataDiscardedDueToPacketErrorTriggerTime  OBJECT-TYPE
    SYNTAX     INTEGER
    MAX-ACCESS read-write
    STATUS     current
    DESCRIPTION
        "Time in 1/10 of a second that an alarm needs to stay triggered until alarm is asserted"
::= { enc1A14vancdataDiscardedDueToPacketErrorEntry 4 }

enc1A14vancdataDiscardedDueToPacketErrorClearTime  OBJECT-TYPE
    SYNTAX     INTEGER
    MAX-ACCESS read-write
    STATUS     current
    DESCRIPTION
        "Time in 1/10 of a second that an alarm needs to stay clear until alarm is unasserted"
::= { enc1A14vancdataDiscardedDueToPacketErrorEntry 5 }

enc1A15vancconfigurationRateBelowMinimumTable OBJECT-TYPE
    SYNTAX SEQUENCE OF Enc1A15vancconfigurationRateBelowMinimumEntry
    MAX-ACCESS not-accessible
    STATUS     current
    DESCRIPTION
    "VANC Configuration: Rate Below Minimum"
::= { enc1Alarms 15 }

enc1A15vancconfigurationRateBelowMinimumEntry OBJECT-TYPE
    SYNTAX Enc1A15vancconfigurationRateBelowMinimumEntry
    MAX-ACCESS not-accessible
    STATUS     current
    DESCRIPTION
    "Table Entry for VANC Configuration: Rate Below Minimum"
    INDEX { slotId }
::= { enc1A15vancconfigurationRateBelowMinimumTable 1 }

Enc1A15vancconfigurationRateBelowMinimumEntry ::= SEQUENCE {
    enc1A15vancconfigurationRateBelowMinimumEnabled    AlarmEnabled,
    enc1A15vancconfigurationRateBelowMinimumPriority    INTEGER,
    enc1A15vancconfigurationRateBelowMinimumAcknowledged    AlarmAcknowledged,
    enc1A15vancconfigurationRateBelowMinimumTriggerTime    INTEGER,
    enc1A15vancconfigurationRateBelowMinimumClearTime    INTEGER
}

enc1A15vancconfigurationRateBelowMinimumEnabled  OBJECT-TYPE
    SYNTAX     AlarmEnabled
    MAX-ACCESS read-write
    STATUS     current
    DESCRIPTION
        "Property to enable or disable the alarm"
::= { enc1A15vancconfigurationRateBelowMinimumEntry 1 }

enc1A15vancconfigurationRateBelowMinimumPriority  OBJECT-TYPE
    SYNTAX     INTEGER
    MAX-ACCESS read-write
    STATUS     current
    DESCRIPTION
        "Set the priority of the alarm from 1 to 10 (where 10 is highest priority)"
::= { enc1A15vancconfigurationRateBelowMinimumEntry 2 }

enc1A15vancconfigurationRateBelowMinimumAcknowledged  OBJECT-TYPE
    SYNTAX     AlarmAcknowledged
    MAX-ACCESS read-write
    STATUS     current
    DESCRIPTION
        "Acknowledge the alarm such that other clients can see that the alarm has been acknowledged"
::= { enc1A15vancconfigurationRateBelowMinimumEntry 3 }

enc1A15vancconfigurationRateBelowMinimumTriggerTime  OBJECT-TYPE
    SYNTAX     INTEGER
    MAX-ACCESS read-write
    STATUS     current
    DESCRIPTION
        "Time in 1/10 of a second that an alarm needs to stay triggered until alarm is asserted"
::= { enc1A15vancconfigurationRateBelowMinimumEntry 4 }

enc1A15vancconfigurationRateBelowMinimumClearTime  OBJECT-TYPE
    SYNTAX     INTEGER
    MAX-ACCESS read-write
    STATUS     current
    DESCRIPTION
        "Time in 1/10 of a second that an alarm needs to stay clear until alarm is unasserted"
::= { enc1A15vancconfigurationRateBelowMinimumEntry 5 }

enc1A16excessiveVBIDataExtractionErrorsTable OBJECT-TYPE
    SYNTAX SEQUENCE OF Enc1A16excessiveVBIDataExtractionErrorsEntry
    MAX-ACCESS not-accessible
    STATUS     current
    DESCRIPTION
    "Excessive VBI Data Extraction Errors"
::= { enc1Alarms 16 }

enc1A16excessiveVBIDataExtractionErrorsEntry OBJECT-TYPE
    SYNTAX Enc1A16excessiveVBIDataExtractionErrorsEntry
    MAX-ACCESS not-accessible
    STATUS     current
    DESCRIPTION
    "Table Entry for Excessive VBI Data Extraction Errors"
    INDEX { slotId }
::= { enc1A16excessiveVBIDataExtractionErrorsTable 1 }

Enc1A16excessiveVBIDataExtractionErrorsEntry ::= SEQUENCE {
    enc1A16excessiveVBIDataExtractionErrorsEnabled    AlarmEnabled,
    enc1A16excessiveVBIDataExtractionErrorsPriority    INTEGER,
    enc1A16excessiveVBIDataExtractionErrorsAcknowledged    AlarmAcknowledged,
    enc1A16excessiveVBIDataExtractionErrorsTriggerTime    INTEGER,
    enc1A16excessiveVBIDataExtractionErrorsClearTime    INTEGER
}

enc1A16excessiveVBIDataExtractionErrorsEnabled  OBJECT-TYPE
    SYNTAX     AlarmEnabled
    MAX-ACCESS read-write
    STATUS     current
    DESCRIPTION
        "Property to enable or disable the alarm"
::= { enc1A16excessiveVBIDataExtractionErrorsEntry 1 }

enc1A16excessiveVBIDataExtractionErrorsPriority  OBJECT-TYPE
    SYNTAX     INTEGER
    MAX-ACCESS read-write
    STATUS     current
    DESCRIPTION
        "Set the priority of the alarm from 1 to 10 (where 10 is highest priority)"
::= { enc1A16excessiveVBIDataExtractionErrorsEntry 2 }

enc1A16excessiveVBIDataExtractionErrorsAcknowledged  OBJECT-TYPE
    SYNTAX     AlarmAcknowledged
    MAX-ACCESS read-write
    STATUS     current
    DESCRIPTION
        "Acknowledge the alarm such that other clients can see that the alarm has been acknowledged"
::= { enc1A16excessiveVBIDataExtractionErrorsEntry 3 }

enc1A16excessiveVBIDataExtractionErrorsTriggerTime  OBJECT-TYPE
    SYNTAX     INTEGER
    MAX-ACCESS read-write
    STATUS     current
    DESCRIPTION
        "Time in 1/10 of a second that an alarm needs to stay triggered until alarm is asserted"
::= { enc1A16excessiveVBIDataExtractionErrorsEntry 4 }

enc1A16excessiveVBIDataExtractionErrorsClearTime  OBJECT-TYPE
    SYNTAX     INTEGER
    MAX-ACCESS read-write
    STATUS     current
    DESCRIPTION
        "Time in 1/10 of a second that an alarm needs to stay clear until alarm is unasserted"
::= { enc1A16excessiveVBIDataExtractionErrorsEntry 5 }

enc1A17klvdataExceedsBandwidthAllocationTable OBJECT-TYPE
    SYNTAX SEQUENCE OF Enc1A17klvdataExceedsBandwidthAllocationEntry
    MAX-ACCESS not-accessible
    STATUS     current
    DESCRIPTION
    "KLV Data Exceeds Bandwidth Allocation"
::= { enc1Alarms 17 }

enc1A17klvdataExceedsBandwidthAllocationEntry OBJECT-TYPE
    SYNTAX Enc1A17klvdataExceedsBandwidthAllocationEntry
    MAX-ACCESS not-accessible
    STATUS     current
    DESCRIPTION
    "Table Entry for KLV Data Exceeds Bandwidth Allocation"
    INDEX { slotId }
::= { enc1A17klvdataExceedsBandwidthAllocationTable 1 }

Enc1A17klvdataExceedsBandwidthAllocationEntry ::= SEQUENCE {
    enc1A17klvdataExceedsBandwidthAllocationEnabled    AlarmEnabled,
    enc1A17klvdataExceedsBandwidthAllocationPriority    INTEGER,
    enc1A17klvdataExceedsBandwidthAllocationAcknowledged    AlarmAcknowledged,
    enc1A17klvdataExceedsBandwidthAllocationTriggerTime    INTEGER,
    enc1A17klvdataExceedsBandwidthAllocationClearTime    INTEGER
}

enc1A17klvdataExceedsBandwidthAllocationEnabled  OBJECT-TYPE
    SYNTAX     AlarmEnabled
    MAX-ACCESS read-write
    STATUS     current
    DESCRIPTION
        "Property to enable or disable the alarm"
::= { enc1A17klvdataExceedsBandwidthAllocationEntry 1 }

enc1A17klvdataExceedsBandwidthAllocationPriority  OBJECT-TYPE
    SYNTAX     INTEGER
    MAX-ACCESS read-write
    STATUS     current
    DESCRIPTION
        "Set the priority of the alarm from 1 to 10 (where 10 is highest priority)"
::= { enc1A17klvdataExceedsBandwidthAllocationEntry 2 }

enc1A17klvdataExceedsBandwidthAllocationAcknowledged  OBJECT-TYPE
    SYNTAX     AlarmAcknowledged
    MAX-ACCESS read-write
    STATUS     current
    DESCRIPTION
        "Acknowledge the alarm such that other clients can see that the alarm has been acknowledged"
::= { enc1A17klvdataExceedsBandwidthAllocationEntry 3 }

enc1A17klvdataExceedsBandwidthAllocationTriggerTime  OBJECT-TYPE
    SYNTAX     INTEGER
    MAX-ACCESS read-write
    STATUS     current
    DESCRIPTION
        "Time in 1/10 of a second that an alarm needs to stay triggered until alarm is asserted"
::= { enc1A17klvdataExceedsBandwidthAllocationEntry 4 }

enc1A17klvdataExceedsBandwidthAllocationClearTime  OBJECT-TYPE
    SYNTAX     INTEGER
    MAX-ACCESS read-write
    STATUS     current
    DESCRIPTION
        "Time in 1/10 of a second that an alarm needs to stay clear until alarm is unasserted"
::= { enc1A17klvdataExceedsBandwidthAllocationEntry 5 }

enc1A18klvdataDiscardedDueToPacketErrorTable OBJECT-TYPE
    SYNTAX SEQUENCE OF Enc1A18klvdataDiscardedDueToPacketErrorEntry
    MAX-ACCESS not-accessible
    STATUS     current
    DESCRIPTION
    "KLV Data Discarded Due To Packet Error"
::= { enc1Alarms 18 }

enc1A18klvdataDiscardedDueToPacketErrorEntry OBJECT-TYPE
    SYNTAX Enc1A18klvdataDiscardedDueToPacketErrorEntry
    MAX-ACCESS not-accessible
    STATUS     current
    DESCRIPTION
    "Table Entry for KLV Data Discarded Due To Packet Error"
    INDEX { slotId }
::= { enc1A18klvdataDiscardedDueToPacketErrorTable 1 }

Enc1A18klvdataDiscardedDueToPacketErrorEntry ::= SEQUENCE {
    enc1A18klvdataDiscardedDueToPacketErrorEnabled    AlarmEnabled,
    enc1A18klvdataDiscardedDueToPacketErrorPriority    INTEGER,
    enc1A18klvdataDiscardedDueToPacketErrorAcknowledged    AlarmAcknowledged,
    enc1A18klvdataDiscardedDueToPacketErrorTriggerTime    INTEGER,
    enc1A18klvdataDiscardedDueToPacketErrorClearTime    INTEGER
}

enc1A18klvdataDiscardedDueToPacketErrorEnabled  OBJECT-TYPE
    SYNTAX     AlarmEnabled
    MAX-ACCESS read-write
    STATUS     current
    DESCRIPTION
        "Property to enable or disable the alarm"
::= { enc1A18klvdataDiscardedDueToPacketErrorEntry 1 }

enc1A18klvdataDiscardedDueToPacketErrorPriority  OBJECT-TYPE
    SYNTAX     INTEGER
    MAX-ACCESS read-write
    STATUS     current
    DESCRIPTION
        "Set the priority of the alarm from 1 to 10 (where 10 is highest priority)"
::= { enc1A18klvdataDiscardedDueToPacketErrorEntry 2 }

enc1A18klvdataDiscardedDueToPacketErrorAcknowledged  OBJECT-TYPE
    SYNTAX     AlarmAcknowledged
    MAX-ACCESS read-write
    STATUS     current
    DESCRIPTION
        "Acknowledge the alarm such that other clients can see that the alarm has been acknowledged"
::= { enc1A18klvdataDiscardedDueToPacketErrorEntry 3 }

enc1A18klvdataDiscardedDueToPacketErrorTriggerTime  OBJECT-TYPE
    SYNTAX     INTEGER
    MAX-ACCESS read-write
    STATUS     current
    DESCRIPTION
        "Time in 1/10 of a second that an alarm needs to stay triggered until alarm is asserted"
::= { enc1A18klvdataDiscardedDueToPacketErrorEntry 4 }

enc1A18klvdataDiscardedDueToPacketErrorClearTime  OBJECT-TYPE
    SYNTAX     INTEGER
    MAX-ACCESS read-write
    STATUS     current
    DESCRIPTION
        "Time in 1/10 of a second that an alarm needs to stay clear until alarm is unasserted"
::= { enc1A18klvdataDiscardedDueToPacketErrorEntry 5 }

enc1A19op-47DataExceedsLinesFrameAllocationTable OBJECT-TYPE
    SYNTAX SEQUENCE OF Enc1A19op-47DataExceedsLinesFrameAllocationEntry
    MAX-ACCESS not-accessible
    STATUS     current
    DESCRIPTION
    "OP-47 Data Exceeds Lines/Frame Allocation"
::= { enc1Alarms 19 }

enc1A19op-47DataExceedsLinesFrameAllocationEntry OBJECT-TYPE
    SYNTAX Enc1A19op-47DataExceedsLinesFrameAllocationEntry
    MAX-ACCESS not-accessible
    STATUS     current
    DESCRIPTION
    "Table Entry for OP-47 Data Exceeds Lines/Frame Allocation"
    INDEX { slotId }
::= { enc1A19op-47DataExceedsLinesFrameAllocationTable 1 }

Enc1A19op-47DataExceedsLinesFrameAllocationEntry ::= SEQUENCE {
    enc1A19op-47DataExceedsLinesFrameAllocationEnabled    AlarmEnabled,
    enc1A19op-47DataExceedsLinesFrameAllocationPriority    INTEGER,
    enc1A19op-47DataExceedsLinesFrameAllocationAcknowledged    AlarmAcknowledged,
    enc1A19op-47DataExceedsLinesFrameAllocationTriggerTime    INTEGER,
    enc1A19op-47DataExceedsLinesFrameAllocationClearTime    INTEGER
}

enc1A19op-47DataExceedsLinesFrameAllocationEnabled  OBJECT-TYPE
    SYNTAX     AlarmEnabled
    MAX-ACCESS read-write
    STATUS     current
    DESCRIPTION
        "Property to enable or disable the alarm"
::= { enc1A19op-47DataExceedsLinesFrameAllocationEntry 1 }

enc1A19op-47DataExceedsLinesFrameAllocationPriority  OBJECT-TYPE
    SYNTAX     INTEGER
    MAX-ACCESS read-write
    STATUS     current
    DESCRIPTION
        "Set the priority of the alarm from 1 to 10 (where 10 is highest priority)"
::= { enc1A19op-47DataExceedsLinesFrameAllocationEntry 2 }

enc1A19op-47DataExceedsLinesFrameAllocationAcknowledged  OBJECT-TYPE
    SYNTAX     AlarmAcknowledged
    MAX-ACCESS read-write
    STATUS     current
    DESCRIPTION
        "Acknowledge the alarm such that other clients can see that the alarm has been acknowledged"
::= { enc1A19op-47DataExceedsLinesFrameAllocationEntry 3 }

enc1A19op-47DataExceedsLinesFrameAllocationTriggerTime  OBJECT-TYPE
    SYNTAX     INTEGER
    MAX-ACCESS read-write
    STATUS     current
    DESCRIPTION
        "Time in 1/10 of a second that an alarm needs to stay triggered until alarm is asserted"
::= { enc1A19op-47DataExceedsLinesFrameAllocationEntry 4 }

enc1A19op-47DataExceedsLinesFrameAllocationClearTime  OBJECT-TYPE
    SYNTAX     INTEGER
    MAX-ACCESS read-write
    STATUS     current
    DESCRIPTION
        "Time in 1/10 of a second that an alarm needs to stay clear until alarm is unasserted"
::= { enc1A19op-47DataExceedsLinesFrameAllocationEntry 5 }

enc1A20op-47DataDiscardedDueToPacketErrorTable OBJECT-TYPE
    SYNTAX SEQUENCE OF Enc1A20op-47DataDiscardedDueToPacketErrorEntry
    MAX-ACCESS not-accessible
    STATUS     current
    DESCRIPTION
    "OP-47 Data Discarded Due To Packet Error"
::= { enc1Alarms 20 }

enc1A20op-47DataDiscardedDueToPacketErrorEntry OBJECT-TYPE
    SYNTAX Enc1A20op-47DataDiscardedDueToPacketErrorEntry
    MAX-ACCESS not-accessible
    STATUS     current
    DESCRIPTION
    "Table Entry for OP-47 Data Discarded Due To Packet Error"
    INDEX { slotId }
::= { enc1A20op-47DataDiscardedDueToPacketErrorTable 1 }

Enc1A20op-47DataDiscardedDueToPacketErrorEntry ::= SEQUENCE {
    enc1A20op-47DataDiscardedDueToPacketErrorEnabled    AlarmEnabled,
    enc1A20op-47DataDiscardedDueToPacketErrorPriority    INTEGER,
    enc1A20op-47DataDiscardedDueToPacketErrorAcknowledged    AlarmAcknowledged,
    enc1A20op-47DataDiscardedDueToPacketErrorTriggerTime    INTEGER,
    enc1A20op-47DataDiscardedDueToPacketErrorClearTime    INTEGER
}

enc1A20op-47DataDiscardedDueToPacketErrorEnabled  OBJECT-TYPE
    SYNTAX     AlarmEnabled
    MAX-ACCESS read-write
    STATUS     current
    DESCRIPTION
        "Property to enable or disable the alarm"
::= { enc1A20op-47DataDiscardedDueToPacketErrorEntry 1 }

enc1A20op-47DataDiscardedDueToPacketErrorPriority  OBJECT-TYPE
    SYNTAX     INTEGER
    MAX-ACCESS read-write
    STATUS     current
    DESCRIPTION
        "Set the priority of the alarm from 1 to 10 (where 10 is highest priority)"
::= { enc1A20op-47DataDiscardedDueToPacketErrorEntry 2 }

enc1A20op-47DataDiscardedDueToPacketErrorAcknowledged  OBJECT-TYPE
    SYNTAX     AlarmAcknowledged
    MAX-ACCESS read-write
    STATUS     current
    DESCRIPTION
        "Acknowledge the alarm such that other clients can see that the alarm has been acknowledged"
::= { enc1A20op-47DataDiscardedDueToPacketErrorEntry 3 }

enc1A20op-47DataDiscardedDueToPacketErrorTriggerTime  OBJECT-TYPE
    SYNTAX     INTEGER
    MAX-ACCESS read-write
    STATUS     current
    DESCRIPTION
        "Time in 1/10 of a second that an alarm needs to stay triggered until alarm is asserted"
::= { enc1A20op-47DataDiscardedDueToPacketErrorEntry 4 }

enc1A20op-47DataDiscardedDueToPacketErrorClearTime  OBJECT-TYPE
    SYNTAX     INTEGER
    MAX-ACCESS read-write
    STATUS     current
    DESCRIPTION
        "Time in 1/10 of a second that an alarm needs to stay clear until alarm is unasserted"
::= { enc1A20op-47DataDiscardedDueToPacketErrorEntry 5 }

enc1A21errorsInSCTE104OrSCTE35DataTable OBJECT-TYPE
    SYNTAX SEQUENCE OF Enc1A21errorsInSCTE104OrSCTE35DataEntry
    MAX-ACCESS not-accessible
    STATUS     current
    DESCRIPTION
    "Errors In SCTE 104 Or SCTE 35 Data"
::= { enc1Alarms 21 }

enc1A21errorsInSCTE104OrSCTE35DataEntry OBJECT-TYPE
    SYNTAX Enc1A21errorsInSCTE104OrSCTE35DataEntry
    MAX-ACCESS not-accessible
    STATUS     current
    DESCRIPTION
    "Table Entry for Errors In SCTE 104 Or SCTE 35 Data"
    INDEX { slotId }
::= { enc1A21errorsInSCTE104OrSCTE35DataTable 1 }

Enc1A21errorsInSCTE104OrSCTE35DataEntry ::= SEQUENCE {
    enc1A21errorsInSCTE104OrSCTE35DataEnabled    AlarmEnabled,
    enc1A21errorsInSCTE104OrSCTE35DataPriority    INTEGER,
    enc1A21errorsInSCTE104OrSCTE35DataAcknowledged    AlarmAcknowledged,
    enc1A21errorsInSCTE104OrSCTE35DataTriggerTime    INTEGER,
    enc1A21errorsInSCTE104OrSCTE35DataClearTime    INTEGER
}

enc1A21errorsInSCTE104OrSCTE35DataEnabled  OBJECT-TYPE
    SYNTAX     AlarmEnabled
    MAX-ACCESS read-write
    STATUS     current
    DESCRIPTION
        "Property to enable or disable the alarm"
::= { enc1A21errorsInSCTE104OrSCTE35DataEntry 1 }

enc1A21errorsInSCTE104OrSCTE35DataPriority  OBJECT-TYPE
    SYNTAX     INTEGER
    MAX-ACCESS read-write
    STATUS     current
    DESCRIPTION
        "Set the priority of the alarm from 1 to 10 (where 10 is highest priority)"
::= { enc1A21errorsInSCTE104OrSCTE35DataEntry 2 }

enc1A21errorsInSCTE104OrSCTE35DataAcknowledged  OBJECT-TYPE
    SYNTAX     AlarmAcknowledged
    MAX-ACCESS read-write
    STATUS     current
    DESCRIPTION
        "Acknowledge the alarm such that other clients can see that the alarm has been acknowledged"
::= { enc1A21errorsInSCTE104OrSCTE35DataEntry 3 }

enc1A21errorsInSCTE104OrSCTE35DataTriggerTime  OBJECT-TYPE
    SYNTAX     INTEGER
    MAX-ACCESS read-write
    STATUS     current
    DESCRIPTION
        "Time in 1/10 of a second that an alarm needs to stay triggered until alarm is asserted"
::= { enc1A21errorsInSCTE104OrSCTE35DataEntry 4 }

enc1A21errorsInSCTE104OrSCTE35DataClearTime  OBJECT-TYPE
    SYNTAX     INTEGER
    MAX-ACCESS read-write
    STATUS     current
    DESCRIPTION
        "Time in 1/10 of a second that an alarm needs to stay clear until alarm is unasserted"
::= { enc1A21errorsInSCTE104OrSCTE35DataEntry 5 }

enc1A22splicePointVideoPTSInvalidTable OBJECT-TYPE
    SYNTAX SEQUENCE OF Enc1A22splicePointVideoPTSInvalidEntry
    MAX-ACCESS not-accessible
    STATUS     current
    DESCRIPTION
    "Splice Point Video PTS Invalid"
::= { enc1Alarms 22 }

enc1A22splicePointVideoPTSInvalidEntry OBJECT-TYPE
    SYNTAX Enc1A22splicePointVideoPTSInvalidEntry
    MAX-ACCESS not-accessible
    STATUS     current
    DESCRIPTION
    "Table Entry for Splice Point Video PTS Invalid"
    INDEX { slotId }
::= { enc1A22splicePointVideoPTSInvalidTable 1 }

Enc1A22splicePointVideoPTSInvalidEntry ::= SEQUENCE {
    enc1A22splicePointVideoPTSInvalidEnabled    AlarmEnabled,
    enc1A22splicePointVideoPTSInvalidPriority    INTEGER,
    enc1A22splicePointVideoPTSInvalidAcknowledged    AlarmAcknowledged,
    enc1A22splicePointVideoPTSInvalidTriggerTime    INTEGER,
    enc1A22splicePointVideoPTSInvalidClearTime    INTEGER
}

enc1A22splicePointVideoPTSInvalidEnabled  OBJECT-TYPE
    SYNTAX     AlarmEnabled
    MAX-ACCESS read-write
    STATUS     current
    DESCRIPTION
        "Property to enable or disable the alarm"
::= { enc1A22splicePointVideoPTSInvalidEntry 1 }

enc1A22splicePointVideoPTSInvalidPriority  OBJECT-TYPE
    SYNTAX     INTEGER
    MAX-ACCESS read-write
    STATUS     current
    DESCRIPTION
        "Set the priority of the alarm from 1 to 10 (where 10 is highest priority)"
::= { enc1A22splicePointVideoPTSInvalidEntry 2 }

enc1A22splicePointVideoPTSInvalidAcknowledged  OBJECT-TYPE
    SYNTAX     AlarmAcknowledged
    MAX-ACCESS read-write
    STATUS     current
    DESCRIPTION
        "Acknowledge the alarm such that other clients can see that the alarm has been acknowledged"
::= { enc1A22splicePointVideoPTSInvalidEntry 3 }

enc1A22splicePointVideoPTSInvalidTriggerTime  OBJECT-TYPE
    SYNTAX     INTEGER
    MAX-ACCESS read-write
    STATUS     current
    DESCRIPTION
        "Time in 1/10 of a second that an alarm needs to stay triggered until alarm is asserted"
::= { enc1A22splicePointVideoPTSInvalidEntry 4 }

enc1A22splicePointVideoPTSInvalidClearTime  OBJECT-TYPE
    SYNTAX     INTEGER
    MAX-ACCESS read-write
    STATUS     current
    DESCRIPTION
        "Time in 1/10 of a second that an alarm needs to stay clear until alarm is unasserted"
::= { enc1A22splicePointVideoPTSInvalidEntry 5 }

enc1A23splicePointNotificationTooLateForInsertionTable OBJECT-TYPE
    SYNTAX SEQUENCE OF Enc1A23splicePointNotificationTooLateForInsertionEntry
    MAX-ACCESS not-accessible
    STATUS     current
    DESCRIPTION
    "Splice Point Notification Too Late For Insertion"
::= { enc1Alarms 23 }

enc1A23splicePointNotificationTooLateForInsertionEntry OBJECT-TYPE
    SYNTAX Enc1A23splicePointNotificationTooLateForInsertionEntry
    MAX-ACCESS not-accessible
    STATUS     current
    DESCRIPTION
    "Table Entry for Splice Point Notification Too Late For Insertion"
    INDEX { slotId }
::= { enc1A23splicePointNotificationTooLateForInsertionTable 1 }

Enc1A23splicePointNotificationTooLateForInsertionEntry ::= SEQUENCE {
    enc1A23splicePointNotificationTooLateForInsertionEnabled    AlarmEnabled,
    enc1A23splicePointNotificationTooLateForInsertionPriority    INTEGER,
    enc1A23splicePointNotificationTooLateForInsertionAcknowledged    AlarmAcknowledged,
    enc1A23splicePointNotificationTooLateForInsertionTriggerTime    INTEGER,
    enc1A23splicePointNotificationTooLateForInsertionClearTime    INTEGER
}

enc1A23splicePointNotificationTooLateForInsertionEnabled  OBJECT-TYPE
    SYNTAX     AlarmEnabled
    MAX-ACCESS read-write
    STATUS     current
    DESCRIPTION
        "Property to enable or disable the alarm"
::= { enc1A23splicePointNotificationTooLateForInsertionEntry 1 }

enc1A23splicePointNotificationTooLateForInsertionPriority  OBJECT-TYPE
    SYNTAX     INTEGER
    MAX-ACCESS read-write
    STATUS     current
    DESCRIPTION
        "Set the priority of the alarm from 1 to 10 (where 10 is highest priority)"
::= { enc1A23splicePointNotificationTooLateForInsertionEntry 2 }

enc1A23splicePointNotificationTooLateForInsertionAcknowledged  OBJECT-TYPE
    SYNTAX     AlarmAcknowledged
    MAX-ACCESS read-write
    STATUS     current
    DESCRIPTION
        "Acknowledge the alarm such that other clients can see that the alarm has been acknowledged"
::= { enc1A23splicePointNotificationTooLateForInsertionEntry 3 }

enc1A23splicePointNotificationTooLateForInsertionTriggerTime  OBJECT-TYPE
    SYNTAX     INTEGER
    MAX-ACCESS read-write
    STATUS     current
    DESCRIPTION
        "Time in 1/10 of a second that an alarm needs to stay triggered until alarm is asserted"
::= { enc1A23splicePointNotificationTooLateForInsertionEntry 4 }

enc1A23splicePointNotificationTooLateForInsertionClearTime  OBJECT-TYPE
    SYNTAX     INTEGER
    MAX-ACCESS read-write
    STATUS     current
    DESCRIPTION
        "Time in 1/10 of a second that an alarm needs to stay clear until alarm is unasserted"
::= { enc1A23splicePointNotificationTooLateForInsertionEntry 5 }

enc1A24iptransmitConfigurationErrorTable OBJECT-TYPE
    SYNTAX SEQUENCE OF Enc1A24iptransmitConfigurationErrorEntry
    MAX-ACCESS not-accessible
    STATUS     current
    DESCRIPTION
    "IP Transmit Configuration Error"
::= { enc1Alarms 24 }

enc1A24iptransmitConfigurationErrorEntry OBJECT-TYPE
    SYNTAX Enc1A24iptransmitConfigurationErrorEntry
    MAX-ACCESS not-accessible
    STATUS     current
    DESCRIPTION
    "Table Entry for IP Transmit Configuration Error"
    INDEX { slotId }
::= { enc1A24iptransmitConfigurationErrorTable 1 }

Enc1A24iptransmitConfigurationErrorEntry ::= SEQUENCE {
    enc1A24iptransmitConfigurationErrorEnabled    AlarmEnabled,
    enc1A24iptransmitConfigurationErrorPriority    INTEGER,
    enc1A24iptransmitConfigurationErrorAcknowledged    AlarmAcknowledged,
    enc1A24iptransmitConfigurationErrorTriggerTime    INTEGER,
    enc1A24iptransmitConfigurationErrorClearTime    INTEGER
}

enc1A24iptransmitConfigurationErrorEnabled  OBJECT-TYPE
    SYNTAX     AlarmEnabled
    MAX-ACCESS read-write
    STATUS     current
    DESCRIPTION
        "Property to enable or disable the alarm"
::= { enc1A24iptransmitConfigurationErrorEntry 1 }

enc1A24iptransmitConfigurationErrorPriority  OBJECT-TYPE
    SYNTAX     INTEGER
    MAX-ACCESS read-write
    STATUS     current
    DESCRIPTION
        "Set the priority of the alarm from 1 to 10 (where 10 is highest priority)"
::= { enc1A24iptransmitConfigurationErrorEntry 2 }

enc1A24iptransmitConfigurationErrorAcknowledged  OBJECT-TYPE
    SYNTAX     AlarmAcknowledged
    MAX-ACCESS read-write
    STATUS     current
    DESCRIPTION
        "Acknowledge the alarm such that other clients can see that the alarm has been acknowledged"
::= { enc1A24iptransmitConfigurationErrorEntry 3 }

enc1A24iptransmitConfigurationErrorTriggerTime  OBJECT-TYPE
    SYNTAX     INTEGER
    MAX-ACCESS read-write
    STATUS     current
    DESCRIPTION
        "Time in 1/10 of a second that an alarm needs to stay triggered until alarm is asserted"
::= { enc1A24iptransmitConfigurationErrorEntry 4 }

enc1A24iptransmitConfigurationErrorClearTime  OBJECT-TYPE
    SYNTAX     INTEGER
    MAX-ACCESS read-write
    STATUS     current
    DESCRIPTION
        "Time in 1/10 of a second that an alarm needs to stay clear until alarm is unasserted"
::= { enc1A24iptransmitConfigurationErrorEntry 5 }

enc1A25ipreceiveOverflowErrorTable OBJECT-TYPE
    SYNTAX SEQUENCE OF Enc1A25ipreceiveOverflowErrorEntry
    MAX-ACCESS not-accessible
    STATUS     current
    DESCRIPTION
    "IP Receive Overflow Error"
::= { enc1Alarms 25 }

enc1A25ipreceiveOverflowErrorEntry OBJECT-TYPE
    SYNTAX Enc1A25ipreceiveOverflowErrorEntry
    MAX-ACCESS not-accessible
    STATUS     current
    DESCRIPTION
    "Table Entry for IP Receive Overflow Error"
    INDEX { slotId }
::= { enc1A25ipreceiveOverflowErrorTable 1 }

Enc1A25ipreceiveOverflowErrorEntry ::= SEQUENCE {
    enc1A25ipreceiveOverflowErrorEnabled    AlarmEnabled,
    enc1A25ipreceiveOverflowErrorPriority    INTEGER,
    enc1A25ipreceiveOverflowErrorAcknowledged    AlarmAcknowledged,
    enc1A25ipreceiveOverflowErrorTriggerTime    INTEGER,
    enc1A25ipreceiveOverflowErrorClearTime    INTEGER
}

enc1A25ipreceiveOverflowErrorEnabled  OBJECT-TYPE
    SYNTAX     AlarmEnabled
    MAX-ACCESS read-write
    STATUS     current
    DESCRIPTION
        "Property to enable or disable the alarm"
::= { enc1A25ipreceiveOverflowErrorEntry 1 }

enc1A25ipreceiveOverflowErrorPriority  OBJECT-TYPE
    SYNTAX     INTEGER
    MAX-ACCESS read-write
    STATUS     current
    DESCRIPTION
        "Set the priority of the alarm from 1 to 10 (where 10 is highest priority)"
::= { enc1A25ipreceiveOverflowErrorEntry 2 }

enc1A25ipreceiveOverflowErrorAcknowledged  OBJECT-TYPE
    SYNTAX     AlarmAcknowledged
    MAX-ACCESS read-write
    STATUS     current
    DESCRIPTION
        "Acknowledge the alarm such that other clients can see that the alarm has been acknowledged"
::= { enc1A25ipreceiveOverflowErrorEntry 3 }

enc1A25ipreceiveOverflowErrorTriggerTime  OBJECT-TYPE
    SYNTAX     INTEGER
    MAX-ACCESS read-write
    STATUS     current
    DESCRIPTION
        "Time in 1/10 of a second that an alarm needs to stay triggered until alarm is asserted"
::= { enc1A25ipreceiveOverflowErrorEntry 4 }

enc1A25ipreceiveOverflowErrorClearTime  OBJECT-TYPE
    SYNTAX     INTEGER
    MAX-ACCESS read-write
    STATUS     current
    DESCRIPTION
        "Time in 1/10 of a second that an alarm needs to stay clear until alarm is unasserted"
::= { enc1A25ipreceiveOverflowErrorEntry 5 }

enc1A26iptransmitOverflowErrorTable OBJECT-TYPE
    SYNTAX SEQUENCE OF Enc1A26iptransmitOverflowErrorEntry
    MAX-ACCESS not-accessible
    STATUS     current
    DESCRIPTION
    "IP Transmit Overflow Error"
::= { enc1Alarms 26 }

enc1A26iptransmitOverflowErrorEntry OBJECT-TYPE
    SYNTAX Enc1A26iptransmitOverflowErrorEntry
    MAX-ACCESS not-accessible
    STATUS     current
    DESCRIPTION
    "Table Entry for IP Transmit Overflow Error"
    INDEX { slotId }
::= { enc1A26iptransmitOverflowErrorTable 1 }

Enc1A26iptransmitOverflowErrorEntry ::= SEQUENCE {
    enc1A26iptransmitOverflowErrorEnabled    AlarmEnabled,
    enc1A26iptransmitOverflowErrorPriority    INTEGER,
    enc1A26iptransmitOverflowErrorAcknowledged    AlarmAcknowledged,
    enc1A26iptransmitOverflowErrorTriggerTime    INTEGER,
    enc1A26iptransmitOverflowErrorClearTime    INTEGER
}

enc1A26iptransmitOverflowErrorEnabled  OBJECT-TYPE
    SYNTAX     AlarmEnabled
    MAX-ACCESS read-write
    STATUS     current
    DESCRIPTION
        "Property to enable or disable the alarm"
::= { enc1A26iptransmitOverflowErrorEntry 1 }

enc1A26iptransmitOverflowErrorPriority  OBJECT-TYPE
    SYNTAX     INTEGER
    MAX-ACCESS read-write
    STATUS     current
    DESCRIPTION
        "Set the priority of the alarm from 1 to 10 (where 10 is highest priority)"
::= { enc1A26iptransmitOverflowErrorEntry 2 }

enc1A26iptransmitOverflowErrorAcknowledged  OBJECT-TYPE
    SYNTAX     AlarmAcknowledged
    MAX-ACCESS read-write
    STATUS     current
    DESCRIPTION
        "Acknowledge the alarm such that other clients can see that the alarm has been acknowledged"
::= { enc1A26iptransmitOverflowErrorEntry 3 }

enc1A26iptransmitOverflowErrorTriggerTime  OBJECT-TYPE
    SYNTAX     INTEGER
    MAX-ACCESS read-write
    STATUS     current
    DESCRIPTION
        "Time in 1/10 of a second that an alarm needs to stay triggered until alarm is asserted"
::= { enc1A26iptransmitOverflowErrorEntry 4 }

enc1A26iptransmitOverflowErrorClearTime  OBJECT-TYPE
    SYNTAX     INTEGER
    MAX-ACCESS read-write
    STATUS     current
    DESCRIPTION
        "Time in 1/10 of a second that an alarm needs to stay clear until alarm is unasserted"
::= { enc1A26iptransmitOverflowErrorEntry 5 }

enc1A27ipreceiveErrorTable OBJECT-TYPE
    SYNTAX SEQUENCE OF Enc1A27ipreceiveErrorEntry
    MAX-ACCESS not-accessible
    STATUS     current
    DESCRIPTION
    "IP Receive Error"
::= { enc1Alarms 27 }

enc1A27ipreceiveErrorEntry OBJECT-TYPE
    SYNTAX Enc1A27ipreceiveErrorEntry
    MAX-ACCESS not-accessible
    STATUS     current
    DESCRIPTION
    "Table Entry for IP Receive Error"
    INDEX { slotId }
::= { enc1A27ipreceiveErrorTable 1 }

Enc1A27ipreceiveErrorEntry ::= SEQUENCE {
    enc1A27ipreceiveErrorEnabled    AlarmEnabled,
    enc1A27ipreceiveErrorPriority    INTEGER,
    enc1A27ipreceiveErrorAcknowledged    AlarmAcknowledged,
    enc1A27ipreceiveErrorTriggerTime    INTEGER,
    enc1A27ipreceiveErrorClearTime    INTEGER
}

enc1A27ipreceiveErrorEnabled  OBJECT-TYPE
    SYNTAX     AlarmEnabled
    MAX-ACCESS read-write
    STATUS     current
    DESCRIPTION
        "Property to enable or disable the alarm"
::= { enc1A27ipreceiveErrorEntry 1 }

enc1A27ipreceiveErrorPriority  OBJECT-TYPE
    SYNTAX     INTEGER
    MAX-ACCESS read-write
    STATUS     current
    DESCRIPTION
        "Set the priority of the alarm from 1 to 10 (where 10 is highest priority)"
::= { enc1A27ipreceiveErrorEntry 2 }

enc1A27ipreceiveErrorAcknowledged  OBJECT-TYPE
    SYNTAX     AlarmAcknowledged
    MAX-ACCESS read-write
    STATUS     current
    DESCRIPTION
        "Acknowledge the alarm such that other clients can see that the alarm has been acknowledged"
::= { enc1A27ipreceiveErrorEntry 3 }

enc1A27ipreceiveErrorTriggerTime  OBJECT-TYPE
    SYNTAX     INTEGER
    MAX-ACCESS read-write
    STATUS     current
    DESCRIPTION
        "Time in 1/10 of a second that an alarm needs to stay triggered until alarm is asserted"
::= { enc1A27ipreceiveErrorEntry 4 }

enc1A27ipreceiveErrorClearTime  OBJECT-TYPE
    SYNTAX     INTEGER
    MAX-ACCESS read-write
    STATUS     current
    DESCRIPTION
        "Time in 1/10 of a second that an alarm needs to stay clear until alarm is unasserted"
::= { enc1A27ipreceiveErrorEntry 5 }

enc1A28mhinputErrorTable OBJECT-TYPE
    SYNTAX SEQUENCE OF Enc1A28mhinputErrorEntry
    MAX-ACCESS not-accessible
    STATUS     current
    DESCRIPTION
    "MH Input Error"
::= { enc1Alarms 28 }

enc1A28mhinputErrorEntry OBJECT-TYPE
    SYNTAX Enc1A28mhinputErrorEntry
    MAX-ACCESS not-accessible
    STATUS     current
    DESCRIPTION
    "Table Entry for MH Input Error"
    INDEX { slotId }
::= { enc1A28mhinputErrorTable 1 }

Enc1A28mhinputErrorEntry ::= SEQUENCE {
    enc1A28mhinputErrorEnabled    AlarmEnabled,
    enc1A28mhinputErrorPriority    INTEGER,
    enc1A28mhinputErrorAcknowledged    AlarmAcknowledged,
    enc1A28mhinputErrorTriggerTime    INTEGER,
    enc1A28mhinputErrorClearTime    INTEGER
}

enc1A28mhinputErrorEnabled  OBJECT-TYPE
    SYNTAX     AlarmEnabled
    MAX-ACCESS read-write
    STATUS     current
    DESCRIPTION
        "Property to enable or disable the alarm"
::= { enc1A28mhinputErrorEntry 1 }

enc1A28mhinputErrorPriority  OBJECT-TYPE
    SYNTAX     INTEGER
    MAX-ACCESS read-write
    STATUS     current
    DESCRIPTION
        "Set the priority of the alarm from 1 to 10 (where 10 is highest priority)"
::= { enc1A28mhinputErrorEntry 2 }

enc1A28mhinputErrorAcknowledged  OBJECT-TYPE
    SYNTAX     AlarmAcknowledged
    MAX-ACCESS read-write
    STATUS     current
    DESCRIPTION
        "Acknowledge the alarm such that other clients can see that the alarm has been acknowledged"
::= { enc1A28mhinputErrorEntry 3 }

enc1A28mhinputErrorTriggerTime  OBJECT-TYPE
    SYNTAX     INTEGER
    MAX-ACCESS read-write
    STATUS     current
    DESCRIPTION
        "Time in 1/10 of a second that an alarm needs to stay triggered until alarm is asserted"
::= { enc1A28mhinputErrorEntry 4 }

enc1A28mhinputErrorClearTime  OBJECT-TYPE
    SYNTAX     INTEGER
    MAX-ACCESS read-write
    STATUS     current
    DESCRIPTION
        "Time in 1/10 of a second that an alarm needs to stay clear until alarm is unasserted"
::= { enc1A28mhinputErrorEntry 5 }

enc1A29mhoutputErrorTable OBJECT-TYPE
    SYNTAX SEQUENCE OF Enc1A29mhoutputErrorEntry
    MAX-ACCESS not-accessible
    STATUS     current
    DESCRIPTION
    "MH Output Error"
::= { enc1Alarms 29 }

enc1A29mhoutputErrorEntry OBJECT-TYPE
    SYNTAX Enc1A29mhoutputErrorEntry
    MAX-ACCESS not-accessible
    STATUS     current
    DESCRIPTION
    "Table Entry for MH Output Error"
    INDEX { slotId }
::= { enc1A29mhoutputErrorTable 1 }

Enc1A29mhoutputErrorEntry ::= SEQUENCE {
    enc1A29mhoutputErrorEnabled    AlarmEnabled,
    enc1A29mhoutputErrorPriority    INTEGER,
    enc1A29mhoutputErrorAcknowledged    AlarmAcknowledged,
    enc1A29mhoutputErrorTriggerTime    INTEGER,
    enc1A29mhoutputErrorClearTime    INTEGER
}

enc1A29mhoutputErrorEnabled  OBJECT-TYPE
    SYNTAX     AlarmEnabled
    MAX-ACCESS read-write
    STATUS     current
    DESCRIPTION
        "Property to enable or disable the alarm"
::= { enc1A29mhoutputErrorEntry 1 }

enc1A29mhoutputErrorPriority  OBJECT-TYPE
    SYNTAX     INTEGER
    MAX-ACCESS read-write
    STATUS     current
    DESCRIPTION
        "Set the priority of the alarm from 1 to 10 (where 10 is highest priority)"
::= { enc1A29mhoutputErrorEntry 2 }

enc1A29mhoutputErrorAcknowledged  OBJECT-TYPE
    SYNTAX     AlarmAcknowledged
    MAX-ACCESS read-write
    STATUS     current
    DESCRIPTION
        "Acknowledge the alarm such that other clients can see that the alarm has been acknowledged"
::= { enc1A29mhoutputErrorEntry 3 }

enc1A29mhoutputErrorTriggerTime  OBJECT-TYPE
    SYNTAX     INTEGER
    MAX-ACCESS read-write
    STATUS     current
    DESCRIPTION
        "Time in 1/10 of a second that an alarm needs to stay triggered until alarm is asserted"
::= { enc1A29mhoutputErrorEntry 4 }

enc1A29mhoutputErrorClearTime  OBJECT-TYPE
    SYNTAX     INTEGER
    MAX-ACCESS read-write
    STATUS     current
    DESCRIPTION
        "Time in 1/10 of a second that an alarm needs to stay clear until alarm is unasserted"
::= { enc1A29mhoutputErrorEntry 5 }

enc1A30mhecmcommunicationErrorTable OBJECT-TYPE
    SYNTAX SEQUENCE OF Enc1A30mhecmcommunicationErrorEntry
    MAX-ACCESS not-accessible
    STATUS     current
    DESCRIPTION
    "MH ECM Communication Error"
::= { enc1Alarms 30 }

enc1A30mhecmcommunicationErrorEntry OBJECT-TYPE
    SYNTAX Enc1A30mhecmcommunicationErrorEntry
    MAX-ACCESS not-accessible
    STATUS     current
    DESCRIPTION
    "Table Entry for MH ECM Communication Error"
    INDEX { slotId }
::= { enc1A30mhecmcommunicationErrorTable 1 }

Enc1A30mhecmcommunicationErrorEntry ::= SEQUENCE {
    enc1A30mhecmcommunicationErrorEnabled    AlarmEnabled,
    enc1A30mhecmcommunicationErrorPriority    INTEGER,
    enc1A30mhecmcommunicationErrorAcknowledged    AlarmAcknowledged,
    enc1A30mhecmcommunicationErrorTriggerTime    INTEGER,
    enc1A30mhecmcommunicationErrorClearTime    INTEGER
}

enc1A30mhecmcommunicationErrorEnabled  OBJECT-TYPE
    SYNTAX     AlarmEnabled
    MAX-ACCESS read-write
    STATUS     current
    DESCRIPTION
        "Property to enable or disable the alarm"
::= { enc1A30mhecmcommunicationErrorEntry 1 }

enc1A30mhecmcommunicationErrorPriority  OBJECT-TYPE
    SYNTAX     INTEGER
    MAX-ACCESS read-write
    STATUS     current
    DESCRIPTION
        "Set the priority of the alarm from 1 to 10 (where 10 is highest priority)"
::= { enc1A30mhecmcommunicationErrorEntry 2 }

enc1A30mhecmcommunicationErrorAcknowledged  OBJECT-TYPE
    SYNTAX     AlarmAcknowledged
    MAX-ACCESS read-write
    STATUS     current
    DESCRIPTION
        "Acknowledge the alarm such that other clients can see that the alarm has been acknowledged"
::= { enc1A30mhecmcommunicationErrorEntry 3 }

enc1A30mhecmcommunicationErrorTriggerTime  OBJECT-TYPE
    SYNTAX     INTEGER
    MAX-ACCESS read-write
    STATUS     current
    DESCRIPTION
        "Time in 1/10 of a second that an alarm needs to stay triggered until alarm is asserted"
::= { enc1A30mhecmcommunicationErrorEntry 4 }

enc1A30mhecmcommunicationErrorClearTime  OBJECT-TYPE
    SYNTAX     INTEGER
    MAX-ACCESS read-write
    STATUS     current
    DESCRIPTION
        "Time in 1/10 of a second that an alarm needs to stay clear until alarm is unasserted"
::= { enc1A30mhecmcommunicationErrorEntry 5 }

enc1A31rateConfigurationErrorTable OBJECT-TYPE
    SYNTAX SEQUENCE OF Enc1A31rateConfigurationErrorEntry
    MAX-ACCESS not-accessible
    STATUS     current
    DESCRIPTION
    "Rate Configuration Error"
::= { enc1Alarms 31 }

enc1A31rateConfigurationErrorEntry OBJECT-TYPE
    SYNTAX Enc1A31rateConfigurationErrorEntry
    MAX-ACCESS not-accessible
    STATUS     current
    DESCRIPTION
    "Table Entry for Rate Configuration Error"
    INDEX { slotId }
::= { enc1A31rateConfigurationErrorTable 1 }

Enc1A31rateConfigurationErrorEntry ::= SEQUENCE {
    enc1A31rateConfigurationErrorEnabled    AlarmEnabled,
    enc1A31rateConfigurationErrorPriority    INTEGER,
    enc1A31rateConfigurationErrorAcknowledged    AlarmAcknowledged,
    enc1A31rateConfigurationErrorTriggerTime    INTEGER,
    enc1A31rateConfigurationErrorClearTime    INTEGER
}

enc1A31rateConfigurationErrorEnabled  OBJECT-TYPE
    SYNTAX     AlarmEnabled
    MAX-ACCESS read-write
    STATUS     current
    DESCRIPTION
        "Property to enable or disable the alarm"
::= { enc1A31rateConfigurationErrorEntry 1 }

enc1A31rateConfigurationErrorPriority  OBJECT-TYPE
    SYNTAX     INTEGER
    MAX-ACCESS read-write
    STATUS     current
    DESCRIPTION
        "Set the priority of the alarm from 1 to 10 (where 10 is highest priority)"
::= { enc1A31rateConfigurationErrorEntry 2 }

enc1A31rateConfigurationErrorAcknowledged  OBJECT-TYPE
    SYNTAX     AlarmAcknowledged
    MAX-ACCESS read-write
    STATUS     current
    DESCRIPTION
        "Acknowledge the alarm such that other clients can see that the alarm has been acknowledged"
::= { enc1A31rateConfigurationErrorEntry 3 }

enc1A31rateConfigurationErrorTriggerTime  OBJECT-TYPE
    SYNTAX     INTEGER
    MAX-ACCESS read-write
    STATUS     current
    DESCRIPTION
        "Time in 1/10 of a second that an alarm needs to stay triggered until alarm is asserted"
::= { enc1A31rateConfigurationErrorEntry 4 }

enc1A31rateConfigurationErrorClearTime  OBJECT-TYPE
    SYNTAX     INTEGER
    MAX-ACCESS read-write
    STATUS     current
    DESCRIPTION
        "Time in 1/10 of a second that an alarm needs to stay clear until alarm is unasserted"
::= { enc1A31rateConfigurationErrorEntry 5 }

enc1A32amolrateConfigurationErrorTable OBJECT-TYPE
    SYNTAX SEQUENCE OF Enc1A32amolrateConfigurationErrorEntry
    MAX-ACCESS not-accessible
    STATUS     current
    DESCRIPTION
    "AMOL Rate Configuration Error"
::= { enc1Alarms 32 }

enc1A32amolrateConfigurationErrorEntry OBJECT-TYPE
    SYNTAX Enc1A32amolrateConfigurationErrorEntry
    MAX-ACCESS not-accessible
    STATUS     current
    DESCRIPTION
    "Table Entry for AMOL Rate Configuration Error"
    INDEX { slotId }
::= { enc1A32amolrateConfigurationErrorTable 1 }

Enc1A32amolrateConfigurationErrorEntry ::= SEQUENCE {
    enc1A32amolrateConfigurationErrorEnabled    AlarmEnabled,
    enc1A32amolrateConfigurationErrorPriority    INTEGER,
    enc1A32amolrateConfigurationErrorAcknowledged    AlarmAcknowledged,
    enc1A32amolrateConfigurationErrorTriggerTime    INTEGER,
    enc1A32amolrateConfigurationErrorClearTime    INTEGER
}

enc1A32amolrateConfigurationErrorEnabled  OBJECT-TYPE
    SYNTAX     AlarmEnabled
    MAX-ACCESS read-write
    STATUS     current
    DESCRIPTION
        "Property to enable or disable the alarm"
::= { enc1A32amolrateConfigurationErrorEntry 1 }

enc1A32amolrateConfigurationErrorPriority  OBJECT-TYPE
    SYNTAX     INTEGER
    MAX-ACCESS read-write
    STATUS     current
    DESCRIPTION
        "Set the priority of the alarm from 1 to 10 (where 10 is highest priority)"
::= { enc1A32amolrateConfigurationErrorEntry 2 }

enc1A32amolrateConfigurationErrorAcknowledged  OBJECT-TYPE
    SYNTAX     AlarmAcknowledged
    MAX-ACCESS read-write
    STATUS     current
    DESCRIPTION
        "Acknowledge the alarm such that other clients can see that the alarm has been acknowledged"
::= { enc1A32amolrateConfigurationErrorEntry 3 }

enc1A32amolrateConfigurationErrorTriggerTime  OBJECT-TYPE
    SYNTAX     INTEGER
    MAX-ACCESS read-write
    STATUS     current
    DESCRIPTION
        "Time in 1/10 of a second that an alarm needs to stay triggered until alarm is asserted"
::= { enc1A32amolrateConfigurationErrorEntry 4 }

enc1A32amolrateConfigurationErrorClearTime  OBJECT-TYPE
    SYNTAX     INTEGER
    MAX-ACCESS read-write
    STATUS     current
    DESCRIPTION
        "Time in 1/10 of a second that an alarm needs to stay clear until alarm is unasserted"
::= { enc1A32amolrateConfigurationErrorEntry 5 }

enc1A33mhconfigurationErrorTable OBJECT-TYPE
    SYNTAX SEQUENCE OF Enc1A33mhconfigurationErrorEntry
    MAX-ACCESS not-accessible
    STATUS     current
    DESCRIPTION
    "MH Configuration Error"
::= { enc1Alarms 33 }

enc1A33mhconfigurationErrorEntry OBJECT-TYPE
    SYNTAX Enc1A33mhconfigurationErrorEntry
    MAX-ACCESS not-accessible
    STATUS     current
    DESCRIPTION
    "Table Entry for MH Configuration Error"
    INDEX { slotId }
::= { enc1A33mhconfigurationErrorTable 1 }

Enc1A33mhconfigurationErrorEntry ::= SEQUENCE {
    enc1A33mhconfigurationErrorEnabled    AlarmEnabled,
    enc1A33mhconfigurationErrorPriority    INTEGER,
    enc1A33mhconfigurationErrorAcknowledged    AlarmAcknowledged,
    enc1A33mhconfigurationErrorTriggerTime    INTEGER,
    enc1A33mhconfigurationErrorClearTime    INTEGER
}

enc1A33mhconfigurationErrorEnabled  OBJECT-TYPE
    SYNTAX     AlarmEnabled
    MAX-ACCESS read-write
    STATUS     current
    DESCRIPTION
        "Property to enable or disable the alarm"
::= { enc1A33mhconfigurationErrorEntry 1 }

enc1A33mhconfigurationErrorPriority  OBJECT-TYPE
    SYNTAX     INTEGER
    MAX-ACCESS read-write
    STATUS     current
    DESCRIPTION
        "Set the priority of the alarm from 1 to 10 (where 10 is highest priority)"
::= { enc1A33mhconfigurationErrorEntry 2 }

enc1A33mhconfigurationErrorAcknowledged  OBJECT-TYPE
    SYNTAX     AlarmAcknowledged
    MAX-ACCESS read-write
    STATUS     current
    DESCRIPTION
        "Acknowledge the alarm such that other clients can see that the alarm has been acknowledged"
::= { enc1A33mhconfigurationErrorEntry 3 }

enc1A33mhconfigurationErrorTriggerTime  OBJECT-TYPE
    SYNTAX     INTEGER
    MAX-ACCESS read-write
    STATUS     current
    DESCRIPTION
        "Time in 1/10 of a second that an alarm needs to stay triggered until alarm is asserted"
::= { enc1A33mhconfigurationErrorEntry 4 }

enc1A33mhconfigurationErrorClearTime  OBJECT-TYPE
    SYNTAX     INTEGER
    MAX-ACCESS read-write
    STATUS     current
    DESCRIPTION
        "Time in 1/10 of a second that an alarm needs to stay clear until alarm is unasserted"
::= { enc1A33mhconfigurationErrorEntry 5 }

enc1A34extCompressedAudioErrorTable OBJECT-TYPE
    SYNTAX SEQUENCE OF Enc1A34extCompressedAudioErrorEntry
    MAX-ACCESS not-accessible
    STATUS     current
    DESCRIPTION
    "Ext Compressed Audio Error"
::= { enc1Alarms 34 }

enc1A34extCompressedAudioErrorEntry OBJECT-TYPE
    SYNTAX Enc1A34extCompressedAudioErrorEntry
    MAX-ACCESS not-accessible
    STATUS     current
    DESCRIPTION
    "Table Entry for Ext Compressed Audio Error"
    INDEX { slotId }
::= { enc1A34extCompressedAudioErrorTable 1 }

Enc1A34extCompressedAudioErrorEntry ::= SEQUENCE {
    enc1A34extCompressedAudioErrorEnabled    AlarmEnabled,
    enc1A34extCompressedAudioErrorPriority    INTEGER,
    enc1A34extCompressedAudioErrorAcknowledged    AlarmAcknowledged,
    enc1A34extCompressedAudioErrorTriggerTime    INTEGER,
    enc1A34extCompressedAudioErrorClearTime    INTEGER
}

enc1A34extCompressedAudioErrorEnabled  OBJECT-TYPE
    SYNTAX     AlarmEnabled
    MAX-ACCESS read-write
    STATUS     current
    DESCRIPTION
        "Property to enable or disable the alarm"
::= { enc1A34extCompressedAudioErrorEntry 1 }

enc1A34extCompressedAudioErrorPriority  OBJECT-TYPE
    SYNTAX     INTEGER
    MAX-ACCESS read-write
    STATUS     current
    DESCRIPTION
        "Set the priority of the alarm from 1 to 10 (where 10 is highest priority)"
::= { enc1A34extCompressedAudioErrorEntry 2 }

enc1A34extCompressedAudioErrorAcknowledged  OBJECT-TYPE
    SYNTAX     AlarmAcknowledged
    MAX-ACCESS read-write
    STATUS     current
    DESCRIPTION
        "Acknowledge the alarm such that other clients can see that the alarm has been acknowledged"
::= { enc1A34extCompressedAudioErrorEntry 3 }

enc1A34extCompressedAudioErrorTriggerTime  OBJECT-TYPE
    SYNTAX     INTEGER
    MAX-ACCESS read-write
    STATUS     current
    DESCRIPTION
        "Time in 1/10 of a second that an alarm needs to stay triggered until alarm is asserted"
::= { enc1A34extCompressedAudioErrorEntry 4 }

enc1A34extCompressedAudioErrorClearTime  OBJECT-TYPE
    SYNTAX     INTEGER
    MAX-ACCESS read-write
    STATUS     current
    DESCRIPTION
        "Time in 1/10 of a second that an alarm needs to stay clear until alarm is unasserted"
::= { enc1A34extCompressedAudioErrorEntry 5 }

enc1A35audioExtCompressedAVNotLockedTable OBJECT-TYPE
    SYNTAX SEQUENCE OF Enc1A35audioExtCompressedAVNotLockedEntry
    MAX-ACCESS not-accessible
    STATUS     current
    DESCRIPTION
    "Audio Ext Compressed A/V Not Locked"
::= { enc1Alarms 35 }

enc1A35audioExtCompressedAVNotLockedEntry OBJECT-TYPE
    SYNTAX Enc1A35audioExtCompressedAVNotLockedEntry
    MAX-ACCESS not-accessible
    STATUS     current
    DESCRIPTION
    "Table Entry for Audio Ext Compressed A/V Not Locked"
    INDEX { slotId }
::= { enc1A35audioExtCompressedAVNotLockedTable 1 }

Enc1A35audioExtCompressedAVNotLockedEntry ::= SEQUENCE {
    enc1A35audioExtCompressedAVNotLockedEnabled    AlarmEnabled,
    enc1A35audioExtCompressedAVNotLockedPriority    INTEGER,
    enc1A35audioExtCompressedAVNotLockedAcknowledged    AlarmAcknowledged,
    enc1A35audioExtCompressedAVNotLockedTriggerTime    INTEGER,
    enc1A35audioExtCompressedAVNotLockedClearTime    INTEGER
}

enc1A35audioExtCompressedAVNotLockedEnabled  OBJECT-TYPE
    SYNTAX     AlarmEnabled
    MAX-ACCESS read-write
    STATUS     current
    DESCRIPTION
        "Property to enable or disable the alarm"
::= { enc1A35audioExtCompressedAVNotLockedEntry 1 }

enc1A35audioExtCompressedAVNotLockedPriority  OBJECT-TYPE
    SYNTAX     INTEGER
    MAX-ACCESS read-write
    STATUS     current
    DESCRIPTION
        "Set the priority of the alarm from 1 to 10 (where 10 is highest priority)"
::= { enc1A35audioExtCompressedAVNotLockedEntry 2 }

enc1A35audioExtCompressedAVNotLockedAcknowledged  OBJECT-TYPE
    SYNTAX     AlarmAcknowledged
    MAX-ACCESS read-write
    STATUS     current
    DESCRIPTION
        "Acknowledge the alarm such that other clients can see that the alarm has been acknowledged"
::= { enc1A35audioExtCompressedAVNotLockedEntry 3 }

enc1A35audioExtCompressedAVNotLockedTriggerTime  OBJECT-TYPE
    SYNTAX     INTEGER
    MAX-ACCESS read-write
    STATUS     current
    DESCRIPTION
        "Time in 1/10 of a second that an alarm needs to stay triggered until alarm is asserted"
::= { enc1A35audioExtCompressedAVNotLockedEntry 4 }

enc1A35audioExtCompressedAVNotLockedClearTime  OBJECT-TYPE
    SYNTAX     INTEGER
    MAX-ACCESS read-write
    STATUS     current
    DESCRIPTION
        "Time in 1/10 of a second that an alarm needs to stay clear until alarm is unasserted"
::= { enc1A35audioExtCompressedAVNotLockedEntry 5 }

enc1A36highTemperatureWarningTable OBJECT-TYPE
    SYNTAX SEQUENCE OF Enc1A36highTemperatureWarningEntry
    MAX-ACCESS not-accessible
    STATUS     current
    DESCRIPTION
    "High Temperature Warning"
::= { enc1Alarms 36 }

enc1A36highTemperatureWarningEntry OBJECT-TYPE
    SYNTAX Enc1A36highTemperatureWarningEntry
    MAX-ACCESS not-accessible
    STATUS     current
    DESCRIPTION
    "Table Entry for High Temperature Warning"
    INDEX { slotId }
::= { enc1A36highTemperatureWarningTable 1 }

Enc1A36highTemperatureWarningEntry ::= SEQUENCE {
    enc1A36highTemperatureWarningEnabled    AlarmEnabled,
    enc1A36highTemperatureWarningPriority    INTEGER,
    enc1A36highTemperatureWarningAcknowledged    AlarmAcknowledged,
    enc1A36highTemperatureWarningTriggerTime    INTEGER,
    enc1A36highTemperatureWarningClearTime    INTEGER
}

enc1A36highTemperatureWarningEnabled  OBJECT-TYPE
    SYNTAX     AlarmEnabled
    MAX-ACCESS read-write
    STATUS     current
    DESCRIPTION
        "Property to enable or disable the alarm"
::= { enc1A36highTemperatureWarningEntry 1 }

enc1A36highTemperatureWarningPriority  OBJECT-TYPE
    SYNTAX     INTEGER
    MAX-ACCESS read-write
    STATUS     current
    DESCRIPTION
        "Set the priority of the alarm from 1 to 10 (where 10 is highest priority)"
::= { enc1A36highTemperatureWarningEntry 2 }

enc1A36highTemperatureWarningAcknowledged  OBJECT-TYPE
    SYNTAX     AlarmAcknowledged
    MAX-ACCESS read-write
    STATUS     current
    DESCRIPTION
        "Acknowledge the alarm such that other clients can see that the alarm has been acknowledged"
::= { enc1A36highTemperatureWarningEntry 3 }

enc1A36highTemperatureWarningTriggerTime  OBJECT-TYPE
    SYNTAX     INTEGER
    MAX-ACCESS read-write
    STATUS     current
    DESCRIPTION
        "Time in 1/10 of a second that an alarm needs to stay triggered until alarm is asserted"
::= { enc1A36highTemperatureWarningEntry 4 }

enc1A36highTemperatureWarningClearTime  OBJECT-TYPE
    SYNTAX     INTEGER
    MAX-ACCESS read-write
    STATUS     current
    DESCRIPTION
        "Time in 1/10 of a second that an alarm needs to stay clear until alarm is unasserted"
::= { enc1A36highTemperatureWarningEntry 5 }

enc1A37audioOutputDegradedTable OBJECT-TYPE
    SYNTAX SEQUENCE OF Enc1A37audioOutputDegradedEntry
    MAX-ACCESS not-accessible
    STATUS     current
    DESCRIPTION
    "Audio Output Degraded"
::= { enc1Alarms 37 }

enc1A37audioOutputDegradedEntry OBJECT-TYPE
    SYNTAX Enc1A37audioOutputDegradedEntry
    MAX-ACCESS not-accessible
    STATUS     current
    DESCRIPTION
    "Table Entry for Audio Output Degraded"
    INDEX { slotId }
::= { enc1A37audioOutputDegradedTable 1 }

Enc1A37audioOutputDegradedEntry ::= SEQUENCE {
    enc1A37audioOutputDegradedEnabled    AlarmEnabled,
    enc1A37audioOutputDegradedPriority    INTEGER,
    enc1A37audioOutputDegradedAcknowledged    AlarmAcknowledged,
    enc1A37audioOutputDegradedTriggerTime    INTEGER,
    enc1A37audioOutputDegradedClearTime    INTEGER
}

enc1A37audioOutputDegradedEnabled  OBJECT-TYPE
    SYNTAX     AlarmEnabled
    MAX-ACCESS read-write
    STATUS     current
    DESCRIPTION
        "Property to enable or disable the alarm"
::= { enc1A37audioOutputDegradedEntry 1 }

enc1A37audioOutputDegradedPriority  OBJECT-TYPE
    SYNTAX     INTEGER
    MAX-ACCESS read-write
    STATUS     current
    DESCRIPTION
        "Set the priority of the alarm from 1 to 10 (where 10 is highest priority)"
::= { enc1A37audioOutputDegradedEntry 2 }

enc1A37audioOutputDegradedAcknowledged  OBJECT-TYPE
    SYNTAX     AlarmAcknowledged
    MAX-ACCESS read-write
    STATUS     current
    DESCRIPTION
        "Acknowledge the alarm such that other clients can see that the alarm has been acknowledged"
::= { enc1A37audioOutputDegradedEntry 3 }

enc1A37audioOutputDegradedTriggerTime  OBJECT-TYPE
    SYNTAX     INTEGER
    MAX-ACCESS read-write
    STATUS     current
    DESCRIPTION
        "Time in 1/10 of a second that an alarm needs to stay triggered until alarm is asserted"
::= { enc1A37audioOutputDegradedEntry 4 }

enc1A37audioOutputDegradedClearTime  OBJECT-TYPE
    SYNTAX     INTEGER
    MAX-ACCESS read-write
    STATUS     current
    DESCRIPTION
        "Time in 1/10 of a second that an alarm needs to stay clear until alarm is unasserted"
::= { enc1A37audioOutputDegradedEntry 5 }

enc1A38moduleInFailsafeTable OBJECT-TYPE
    SYNTAX SEQUENCE OF Enc1A38moduleInFailsafeEntry
    MAX-ACCESS not-accessible
    STATUS     current
    DESCRIPTION
    "Module In Failsafe"
::= { enc1Alarms 38 }

enc1A38moduleInFailsafeEntry OBJECT-TYPE
    SYNTAX Enc1A38moduleInFailsafeEntry
    MAX-ACCESS not-accessible
    STATUS     current
    DESCRIPTION
    "Table Entry for Module In Failsafe"
    INDEX { slotId }
::= { enc1A38moduleInFailsafeTable 1 }

Enc1A38moduleInFailsafeEntry ::= SEQUENCE {
    enc1A38moduleInFailsafeEnabled    AlarmEnabled,
    enc1A38moduleInFailsafePriority    INTEGER,
    enc1A38moduleInFailsafeAcknowledged    AlarmAcknowledged,
    enc1A38moduleInFailsafeTriggerTime    INTEGER,
    enc1A38moduleInFailsafeClearTime    INTEGER
}

enc1A38moduleInFailsafeEnabled  OBJECT-TYPE
    SYNTAX     AlarmEnabled
    MAX-ACCESS read-write
    STATUS     current
    DESCRIPTION
        "Property to enable or disable the alarm"
::= { enc1A38moduleInFailsafeEntry 1 }

enc1A38moduleInFailsafePriority  OBJECT-TYPE
    SYNTAX     INTEGER
    MAX-ACCESS read-write
    STATUS     current
    DESCRIPTION
        "Set the priority of the alarm from 1 to 10 (where 10 is highest priority)"
::= { enc1A38moduleInFailsafeEntry 2 }

enc1A38moduleInFailsafeAcknowledged  OBJECT-TYPE
    SYNTAX     AlarmAcknowledged
    MAX-ACCESS read-write
    STATUS     current
    DESCRIPTION
        "Acknowledge the alarm such that other clients can see that the alarm has been acknowledged"
::= { enc1A38moduleInFailsafeEntry 3 }

enc1A38moduleInFailsafeTriggerTime  OBJECT-TYPE
    SYNTAX     INTEGER
    MAX-ACCESS read-write
    STATUS     current
    DESCRIPTION
        "Time in 1/10 of a second that an alarm needs to stay triggered until alarm is asserted"
::= { enc1A38moduleInFailsafeEntry 4 }

enc1A38moduleInFailsafeClearTime  OBJECT-TYPE
    SYNTAX     INTEGER
    MAX-ACCESS read-write
    STATUS     current
    DESCRIPTION
        "Time in 1/10 of a second that an alarm needs to stay clear until alarm is unasserted"
::= { enc1A38moduleInFailsafeEntry 5 }

enc1A39audioLateInputDiscardedTable OBJECT-TYPE
    SYNTAX SEQUENCE OF Enc1A39audioLateInputDiscardedEntry
    MAX-ACCESS not-accessible
    STATUS     current
    DESCRIPTION
    "Audio Late Input Discarded"
::= { enc1Alarms 39 }

enc1A39audioLateInputDiscardedEntry OBJECT-TYPE
    SYNTAX Enc1A39audioLateInputDiscardedEntry
    MAX-ACCESS not-accessible
    STATUS     current
    DESCRIPTION
    "Table Entry for Audio Late Input Discarded"
    INDEX { slotId }
::= { enc1A39audioLateInputDiscardedTable 1 }

Enc1A39audioLateInputDiscardedEntry ::= SEQUENCE {
    enc1A39audioLateInputDiscardedEnabled    AlarmEnabled,
    enc1A39audioLateInputDiscardedPriority    INTEGER,
    enc1A39audioLateInputDiscardedAcknowledged    AlarmAcknowledged,
    enc1A39audioLateInputDiscardedTriggerTime    INTEGER,
    enc1A39audioLateInputDiscardedClearTime    INTEGER
}

enc1A39audioLateInputDiscardedEnabled  OBJECT-TYPE
    SYNTAX     AlarmEnabled
    MAX-ACCESS read-write
    STATUS     current
    DESCRIPTION
        "Property to enable or disable the alarm"
::= { enc1A39audioLateInputDiscardedEntry 1 }

enc1A39audioLateInputDiscardedPriority  OBJECT-TYPE
    SYNTAX     INTEGER
    MAX-ACCESS read-write
    STATUS     current
    DESCRIPTION
        "Set the priority of the alarm from 1 to 10 (where 10 is highest priority)"
::= { enc1A39audioLateInputDiscardedEntry 2 }

enc1A39audioLateInputDiscardedAcknowledged  OBJECT-TYPE
    SYNTAX     AlarmAcknowledged
    MAX-ACCESS read-write
    STATUS     current
    DESCRIPTION
        "Acknowledge the alarm such that other clients can see that the alarm has been acknowledged"
::= { enc1A39audioLateInputDiscardedEntry 3 }

enc1A39audioLateInputDiscardedTriggerTime  OBJECT-TYPE
    SYNTAX     INTEGER
    MAX-ACCESS read-write
    STATUS     current
    DESCRIPTION
        "Time in 1/10 of a second that an alarm needs to stay triggered until alarm is asserted"
::= { enc1A39audioLateInputDiscardedEntry 4 }

enc1A39audioLateInputDiscardedClearTime  OBJECT-TYPE
    SYNTAX     INTEGER
    MAX-ACCESS read-write
    STATUS     current
    DESCRIPTION
        "Time in 1/10 of a second that an alarm needs to stay clear until alarm is unasserted"
::= { enc1A39audioLateInputDiscardedEntry 5 }

enc1A40internalIPDataErrorTable OBJECT-TYPE
    SYNTAX SEQUENCE OF Enc1A40internalIPDataErrorEntry
    MAX-ACCESS not-accessible
    STATUS     current
    DESCRIPTION
    "Internal IP Data Error"
::= { enc1Alarms 40 }

enc1A40internalIPDataErrorEntry OBJECT-TYPE
    SYNTAX Enc1A40internalIPDataErrorEntry
    MAX-ACCESS not-accessible
    STATUS     current
    DESCRIPTION
    "Table Entry for Internal IP Data Error"
    INDEX { slotId }
::= { enc1A40internalIPDataErrorTable 1 }

Enc1A40internalIPDataErrorEntry ::= SEQUENCE {
    enc1A40internalIPDataErrorEnabled    AlarmEnabled,
    enc1A40internalIPDataErrorPriority    INTEGER,
    enc1A40internalIPDataErrorAcknowledged    AlarmAcknowledged,
    enc1A40internalIPDataErrorTriggerTime    INTEGER,
    enc1A40internalIPDataErrorClearTime    INTEGER
}

enc1A40internalIPDataErrorEnabled  OBJECT-TYPE
    SYNTAX     AlarmEnabled
    MAX-ACCESS read-write
    STATUS     current
    DESCRIPTION
        "Property to enable or disable the alarm"
::= { enc1A40internalIPDataErrorEntry 1 }

enc1A40internalIPDataErrorPriority  OBJECT-TYPE
    SYNTAX     INTEGER
    MAX-ACCESS read-write
    STATUS     current
    DESCRIPTION
        "Set the priority of the alarm from 1 to 10 (where 10 is highest priority)"
::= { enc1A40internalIPDataErrorEntry 2 }

enc1A40internalIPDataErrorAcknowledged  OBJECT-TYPE
    SYNTAX     AlarmAcknowledged
    MAX-ACCESS read-write
    STATUS     current
    DESCRIPTION
        "Acknowledge the alarm such that other clients can see that the alarm has been acknowledged"
::= { enc1A40internalIPDataErrorEntry 3 }

enc1A40internalIPDataErrorTriggerTime  OBJECT-TYPE
    SYNTAX     INTEGER
    MAX-ACCESS read-write
    STATUS     current
    DESCRIPTION
        "Time in 1/10 of a second that an alarm needs to stay triggered until alarm is asserted"
::= { enc1A40internalIPDataErrorEntry 4 }

enc1A40internalIPDataErrorClearTime  OBJECT-TYPE
    SYNTAX     INTEGER
    MAX-ACCESS read-write
    STATUS     current
    DESCRIPTION
        "Time in 1/10 of a second that an alarm needs to stay clear until alarm is unasserted"
::= { enc1A40internalIPDataErrorEntry 5 }

enc1A41videoEncoderFaultTable OBJECT-TYPE
    SYNTAX SEQUENCE OF Enc1A41videoEncoderFaultEntry
    MAX-ACCESS not-accessible
    STATUS     current
    DESCRIPTION
    "Video Encoder Fault"
::= { enc1Alarms 41 }

enc1A41videoEncoderFaultEntry OBJECT-TYPE
    SYNTAX Enc1A41videoEncoderFaultEntry
    MAX-ACCESS not-accessible
    STATUS     current
    DESCRIPTION
    "Table Entry for Video Encoder Fault"
    INDEX { slotId }
::= { enc1A41videoEncoderFaultTable 1 }

Enc1A41videoEncoderFaultEntry ::= SEQUENCE {
    enc1A41videoEncoderFaultEnabled    AlarmEnabled,
    enc1A41videoEncoderFaultPriority    INTEGER,
    enc1A41videoEncoderFaultAcknowledged    AlarmAcknowledged,
    enc1A41videoEncoderFaultTriggerTime    INTEGER,
    enc1A41videoEncoderFaultClearTime    INTEGER
}

enc1A41videoEncoderFaultEnabled  OBJECT-TYPE
    SYNTAX     AlarmEnabled
    MAX-ACCESS read-write
    STATUS     current
    DESCRIPTION
        "Property to enable or disable the alarm"
::= { enc1A41videoEncoderFaultEntry 1 }

enc1A41videoEncoderFaultPriority  OBJECT-TYPE
    SYNTAX     INTEGER
    MAX-ACCESS read-write
    STATUS     current
    DESCRIPTION
        "Set the priority of the alarm from 1 to 10 (where 10 is highest priority)"
::= { enc1A41videoEncoderFaultEntry 2 }

enc1A41videoEncoderFaultAcknowledged  OBJECT-TYPE
    SYNTAX     AlarmAcknowledged
    MAX-ACCESS read-write
    STATUS     current
    DESCRIPTION
        "Acknowledge the alarm such that other clients can see that the alarm has been acknowledged"
::= { enc1A41videoEncoderFaultEntry 3 }

enc1A41videoEncoderFaultTriggerTime  OBJECT-TYPE
    SYNTAX     INTEGER
    MAX-ACCESS read-write
    STATUS     current
    DESCRIPTION
        "Time in 1/10 of a second that an alarm needs to stay triggered until alarm is asserted"
::= { enc1A41videoEncoderFaultEntry 4 }

enc1A41videoEncoderFaultClearTime  OBJECT-TYPE
    SYNTAX     INTEGER
    MAX-ACCESS read-write
    STATUS     current
    DESCRIPTION
        "Time in 1/10 of a second that an alarm needs to stay clear until alarm is unasserted"
::= { enc1A41videoEncoderFaultEntry 5 }

enc1A42videoAlternateInputRunningTable OBJECT-TYPE
    SYNTAX SEQUENCE OF Enc1A42videoAlternateInputRunningEntry
    MAX-ACCESS not-accessible
    STATUS     current
    DESCRIPTION
    "Video Alternate Input Running"
::= { enc1Alarms 42 }

enc1A42videoAlternateInputRunningEntry OBJECT-TYPE
    SYNTAX Enc1A42videoAlternateInputRunningEntry
    MAX-ACCESS not-accessible
    STATUS     current
    DESCRIPTION
    "Table Entry for Video Alternate Input Running"
    INDEX { slotId }
::= { enc1A42videoAlternateInputRunningTable 1 }

Enc1A42videoAlternateInputRunningEntry ::= SEQUENCE {
    enc1A42videoAlternateInputRunningEnabled    AlarmEnabled,
    enc1A42videoAlternateInputRunningPriority    INTEGER,
    enc1A42videoAlternateInputRunningAcknowledged    AlarmAcknowledged,
    enc1A42videoAlternateInputRunningTriggerTime    INTEGER,
    enc1A42videoAlternateInputRunningClearTime    INTEGER
}

enc1A42videoAlternateInputRunningEnabled  OBJECT-TYPE
    SYNTAX     AlarmEnabled
    MAX-ACCESS read-write
    STATUS     current
    DESCRIPTION
        "Property to enable or disable the alarm"
::= { enc1A42videoAlternateInputRunningEntry 1 }

enc1A42videoAlternateInputRunningPriority  OBJECT-TYPE
    SYNTAX     INTEGER
    MAX-ACCESS read-write
    STATUS     current
    DESCRIPTION
        "Set the priority of the alarm from 1 to 10 (where 10 is highest priority)"
::= { enc1A42videoAlternateInputRunningEntry 2 }

enc1A42videoAlternateInputRunningAcknowledged  OBJECT-TYPE
    SYNTAX     AlarmAcknowledged
    MAX-ACCESS read-write
    STATUS     current
    DESCRIPTION
        "Acknowledge the alarm such that other clients can see that the alarm has been acknowledged"
::= { enc1A42videoAlternateInputRunningEntry 3 }

enc1A42videoAlternateInputRunningTriggerTime  OBJECT-TYPE
    SYNTAX     INTEGER
    MAX-ACCESS read-write
    STATUS     current
    DESCRIPTION
        "Time in 1/10 of a second that an alarm needs to stay triggered until alarm is asserted"
::= { enc1A42videoAlternateInputRunningEntry 4 }

enc1A42videoAlternateInputRunningClearTime  OBJECT-TYPE
    SYNTAX     INTEGER
    MAX-ACCESS read-write
    STATUS     current
    DESCRIPTION
        "Time in 1/10 of a second that an alarm needs to stay clear until alarm is unasserted"
::= { enc1A42videoAlternateInputRunningEntry 5 }

enc1A43globalSTCSynchronizationHasBeenLostTable OBJECT-TYPE
    SYNTAX SEQUENCE OF Enc1A43globalSTCSynchronizationHasBeenLostEntry
    MAX-ACCESS not-accessible
    STATUS     current
    DESCRIPTION
    "Global STC Synchronization Has Been Lost"
::= { enc1Alarms 43 }

enc1A43globalSTCSynchronizationHasBeenLostEntry OBJECT-TYPE
    SYNTAX Enc1A43globalSTCSynchronizationHasBeenLostEntry
    MAX-ACCESS not-accessible
    STATUS     current
    DESCRIPTION
    "Table Entry for Global STC Synchronization Has Been Lost"
    INDEX { slotId }
::= { enc1A43globalSTCSynchronizationHasBeenLostTable 1 }

Enc1A43globalSTCSynchronizationHasBeenLostEntry ::= SEQUENCE {
    enc1A43globalSTCSynchronizationHasBeenLostEnabled    AlarmEnabled,
    enc1A43globalSTCSynchronizationHasBeenLostPriority    INTEGER,
    enc1A43globalSTCSynchronizationHasBeenLostAcknowledged    AlarmAcknowledged,
    enc1A43globalSTCSynchronizationHasBeenLostTriggerTime    INTEGER,
    enc1A43globalSTCSynchronizationHasBeenLostClearTime    INTEGER
}

enc1A43globalSTCSynchronizationHasBeenLostEnabled  OBJECT-TYPE
    SYNTAX     AlarmEnabled
    MAX-ACCESS read-write
    STATUS     current
    DESCRIPTION
        "Property to enable or disable the alarm"
::= { enc1A43globalSTCSynchronizationHasBeenLostEntry 1 }

enc1A43globalSTCSynchronizationHasBeenLostPriority  OBJECT-TYPE
    SYNTAX     INTEGER
    MAX-ACCESS read-write
    STATUS     current
    DESCRIPTION
        "Set the priority of the alarm from 1 to 10 (where 10 is highest priority)"
::= { enc1A43globalSTCSynchronizationHasBeenLostEntry 2 }

enc1A43globalSTCSynchronizationHasBeenLostAcknowledged  OBJECT-TYPE
    SYNTAX     AlarmAcknowledged
    MAX-ACCESS read-write
    STATUS     current
    DESCRIPTION
        "Acknowledge the alarm such that other clients can see that the alarm has been acknowledged"
::= { enc1A43globalSTCSynchronizationHasBeenLostEntry 3 }

enc1A43globalSTCSynchronizationHasBeenLostTriggerTime  OBJECT-TYPE
    SYNTAX     INTEGER
    MAX-ACCESS read-write
    STATUS     current
    DESCRIPTION
        "Time in 1/10 of a second that an alarm needs to stay triggered until alarm is asserted"
::= { enc1A43globalSTCSynchronizationHasBeenLostEntry 4 }

enc1A43globalSTCSynchronizationHasBeenLostClearTime  OBJECT-TYPE
    SYNTAX     INTEGER
    MAX-ACCESS read-write
    STATUS     current
    DESCRIPTION
        "Time in 1/10 of a second that an alarm needs to stay clear until alarm is unasserted"
::= { enc1A43globalSTCSynchronizationHasBeenLostEntry 5 }

enc1A44videoInputLOSImageFaultTable OBJECT-TYPE
    SYNTAX SEQUENCE OF Enc1A44videoInputLOSImageFaultEntry
    MAX-ACCESS not-accessible
    STATUS     current
    DESCRIPTION
    "Video Input LOS Image Fault"
::= { enc1Alarms 44 }

enc1A44videoInputLOSImageFaultEntry OBJECT-TYPE
    SYNTAX Enc1A44videoInputLOSImageFaultEntry
    MAX-ACCESS not-accessible
    STATUS     current
    DESCRIPTION
    "Table Entry for Video Input LOS Image Fault"
    INDEX { slotId }
::= { enc1A44videoInputLOSImageFaultTable 1 }

Enc1A44videoInputLOSImageFaultEntry ::= SEQUENCE {
    enc1A44videoInputLOSImageFaultEnabled    AlarmEnabled,
    enc1A44videoInputLOSImageFaultPriority    INTEGER,
    enc1A44videoInputLOSImageFaultAcknowledged    AlarmAcknowledged,
    enc1A44videoInputLOSImageFaultTriggerTime    INTEGER,
    enc1A44videoInputLOSImageFaultClearTime    INTEGER
}

enc1A44videoInputLOSImageFaultEnabled  OBJECT-TYPE
    SYNTAX     AlarmEnabled
    MAX-ACCESS read-write
    STATUS     current
    DESCRIPTION
        "Property to enable or disable the alarm"
::= { enc1A44videoInputLOSImageFaultEntry 1 }

enc1A44videoInputLOSImageFaultPriority  OBJECT-TYPE
    SYNTAX     INTEGER
    MAX-ACCESS read-write
    STATUS     current
    DESCRIPTION
        "Set the priority of the alarm from 1 to 10 (where 10 is highest priority)"
::= { enc1A44videoInputLOSImageFaultEntry 2 }

enc1A44videoInputLOSImageFaultAcknowledged  OBJECT-TYPE
    SYNTAX     AlarmAcknowledged
    MAX-ACCESS read-write
    STATUS     current
    DESCRIPTION
        "Acknowledge the alarm such that other clients can see that the alarm has been acknowledged"
::= { enc1A44videoInputLOSImageFaultEntry 3 }

enc1A44videoInputLOSImageFaultTriggerTime  OBJECT-TYPE
    SYNTAX     INTEGER
    MAX-ACCESS read-write
    STATUS     current
    DESCRIPTION
        "Time in 1/10 of a second that an alarm needs to stay triggered until alarm is asserted"
::= { enc1A44videoInputLOSImageFaultEntry 4 }

enc1A44videoInputLOSImageFaultClearTime  OBJECT-TYPE
    SYNTAX     INTEGER
    MAX-ACCESS read-write
    STATUS     current
    DESCRIPTION
        "Time in 1/10 of a second that an alarm needs to stay clear until alarm is unasserted"
::= { enc1A44videoInputLOSImageFaultEntry 5 }

enc1A45smpte2031DataExceedsBandwidthAllocationTable OBJECT-TYPE
    SYNTAX SEQUENCE OF Enc1A45smpte2031DataExceedsBandwidthAllocationEntry
    MAX-ACCESS not-accessible
    STATUS     current
    DESCRIPTION
    "SMPTE 2031 Data Exceeds Bandwidth Allocation"
::= { enc1Alarms 45 }

enc1A45smpte2031DataExceedsBandwidthAllocationEntry OBJECT-TYPE
    SYNTAX Enc1A45smpte2031DataExceedsBandwidthAllocationEntry
    MAX-ACCESS not-accessible
    STATUS     current
    DESCRIPTION
    "Table Entry for SMPTE 2031 Data Exceeds Bandwidth Allocation"
    INDEX { slotId }
::= { enc1A45smpte2031DataExceedsBandwidthAllocationTable 1 }

Enc1A45smpte2031DataExceedsBandwidthAllocationEntry ::= SEQUENCE {
    enc1A45smpte2031DataExceedsBandwidthAllocationEnabled    AlarmEnabled,
    enc1A45smpte2031DataExceedsBandwidthAllocationPriority    INTEGER,
    enc1A45smpte2031DataExceedsBandwidthAllocationAcknowledged    AlarmAcknowledged,
    enc1A45smpte2031DataExceedsBandwidthAllocationTriggerTime    INTEGER,
    enc1A45smpte2031DataExceedsBandwidthAllocationClearTime    INTEGER
}

enc1A45smpte2031DataExceedsBandwidthAllocationEnabled  OBJECT-TYPE
    SYNTAX     AlarmEnabled
    MAX-ACCESS read-write
    STATUS     current
    DESCRIPTION
        "Property to enable or disable the alarm"
::= { enc1A45smpte2031DataExceedsBandwidthAllocationEntry 1 }

enc1A45smpte2031DataExceedsBandwidthAllocationPriority  OBJECT-TYPE
    SYNTAX     INTEGER
    MAX-ACCESS read-write
    STATUS     current
    DESCRIPTION
        "Set the priority of the alarm from 1 to 10 (where 10 is highest priority)"
::= { enc1A45smpte2031DataExceedsBandwidthAllocationEntry 2 }

enc1A45smpte2031DataExceedsBandwidthAllocationAcknowledged  OBJECT-TYPE
    SYNTAX     AlarmAcknowledged
    MAX-ACCESS read-write
    STATUS     current
    DESCRIPTION
        "Acknowledge the alarm such that other clients can see that the alarm has been acknowledged"
::= { enc1A45smpte2031DataExceedsBandwidthAllocationEntry 3 }

enc1A45smpte2031DataExceedsBandwidthAllocationTriggerTime  OBJECT-TYPE
    SYNTAX     INTEGER
    MAX-ACCESS read-write
    STATUS     current
    DESCRIPTION
        "Time in 1/10 of a second that an alarm needs to stay triggered until alarm is asserted"
::= { enc1A45smpte2031DataExceedsBandwidthAllocationEntry 4 }

enc1A45smpte2031DataExceedsBandwidthAllocationClearTime  OBJECT-TYPE
    SYNTAX     INTEGER
    MAX-ACCESS read-write
    STATUS     current
    DESCRIPTION
        "Time in 1/10 of a second that an alarm needs to stay clear until alarm is unasserted"
::= { enc1A45smpte2031DataExceedsBandwidthAllocationEntry 5 }

enc1A46smpte2031DataDiscardedDueToPacketErrorTable OBJECT-TYPE
    SYNTAX SEQUENCE OF Enc1A46smpte2031DataDiscardedDueToPacketErrorEntry
    MAX-ACCESS not-accessible
    STATUS     current
    DESCRIPTION
    "SMPTE 2031 Data Discarded Due To Packet Error"
::= { enc1Alarms 46 }

enc1A46smpte2031DataDiscardedDueToPacketErrorEntry OBJECT-TYPE
    SYNTAX Enc1A46smpte2031DataDiscardedDueToPacketErrorEntry
    MAX-ACCESS not-accessible
    STATUS     current
    DESCRIPTION
    "Table Entry for SMPTE 2031 Data Discarded Due To Packet Error"
    INDEX { slotId }
::= { enc1A46smpte2031DataDiscardedDueToPacketErrorTable 1 }

Enc1A46smpte2031DataDiscardedDueToPacketErrorEntry ::= SEQUENCE {
    enc1A46smpte2031DataDiscardedDueToPacketErrorEnabled    AlarmEnabled,
    enc1A46smpte2031DataDiscardedDueToPacketErrorPriority    INTEGER,
    enc1A46smpte2031DataDiscardedDueToPacketErrorAcknowledged    AlarmAcknowledged,
    enc1A46smpte2031DataDiscardedDueToPacketErrorTriggerTime    INTEGER,
    enc1A46smpte2031DataDiscardedDueToPacketErrorClearTime    INTEGER
}

enc1A46smpte2031DataDiscardedDueToPacketErrorEnabled  OBJECT-TYPE
    SYNTAX     AlarmEnabled
    MAX-ACCESS read-write
    STATUS     current
    DESCRIPTION
        "Property to enable or disable the alarm"
::= { enc1A46smpte2031DataDiscardedDueToPacketErrorEntry 1 }

enc1A46smpte2031DataDiscardedDueToPacketErrorPriority  OBJECT-TYPE
    SYNTAX     INTEGER
    MAX-ACCESS read-write
    STATUS     current
    DESCRIPTION
        "Set the priority of the alarm from 1 to 10 (where 10 is highest priority)"
::= { enc1A46smpte2031DataDiscardedDueToPacketErrorEntry 2 }

enc1A46smpte2031DataDiscardedDueToPacketErrorAcknowledged  OBJECT-TYPE
    SYNTAX     AlarmAcknowledged
    MAX-ACCESS read-write
    STATUS     current
    DESCRIPTION
        "Acknowledge the alarm such that other clients can see that the alarm has been acknowledged"
::= { enc1A46smpte2031DataDiscardedDueToPacketErrorEntry 3 }

enc1A46smpte2031DataDiscardedDueToPacketErrorTriggerTime  OBJECT-TYPE
    SYNTAX     INTEGER
    MAX-ACCESS read-write
    STATUS     current
    DESCRIPTION
        "Time in 1/10 of a second that an alarm needs to stay triggered until alarm is asserted"
::= { enc1A46smpte2031DataDiscardedDueToPacketErrorEntry 4 }

enc1A46smpte2031DataDiscardedDueToPacketErrorClearTime  OBJECT-TYPE
    SYNTAX     INTEGER
    MAX-ACCESS read-write
    STATUS     current
    DESCRIPTION
        "Time in 1/10 of a second that an alarm needs to stay clear until alarm is unasserted"
::= { enc1A46smpte2031DataDiscardedDueToPacketErrorEntry 5 }

enc1A47smpte2031VBIConfigurationAndDataMismatchTable OBJECT-TYPE
    SYNTAX SEQUENCE OF Enc1A47smpte2031VBIConfigurationAndDataMismatchEntry
    MAX-ACCESS not-accessible
    STATUS     current
    DESCRIPTION
    "SMPTE 2031 VBI Configuration And Data Mismatch"
::= { enc1Alarms 47 }

enc1A47smpte2031VBIConfigurationAndDataMismatchEntry OBJECT-TYPE
    SYNTAX Enc1A47smpte2031VBIConfigurationAndDataMismatchEntry
    MAX-ACCESS not-accessible
    STATUS     current
    DESCRIPTION
    "Table Entry for SMPTE 2031 VBI Configuration And Data Mismatch"
    INDEX { slotId }
::= { enc1A47smpte2031VBIConfigurationAndDataMismatchTable 1 }

Enc1A47smpte2031VBIConfigurationAndDataMismatchEntry ::= SEQUENCE {
    enc1A47smpte2031VBIConfigurationAndDataMismatchEnabled    AlarmEnabled,
    enc1A47smpte2031VBIConfigurationAndDataMismatchPriority    INTEGER,
    enc1A47smpte2031VBIConfigurationAndDataMismatchAcknowledged    AlarmAcknowledged,
    enc1A47smpte2031VBIConfigurationAndDataMismatchTriggerTime    INTEGER,
    enc1A47smpte2031VBIConfigurationAndDataMismatchClearTime    INTEGER
}

enc1A47smpte2031VBIConfigurationAndDataMismatchEnabled  OBJECT-TYPE
    SYNTAX     AlarmEnabled
    MAX-ACCESS read-write
    STATUS     current
    DESCRIPTION
        "Property to enable or disable the alarm"
::= { enc1A47smpte2031VBIConfigurationAndDataMismatchEntry 1 }

enc1A47smpte2031VBIConfigurationAndDataMismatchPriority  OBJECT-TYPE
    SYNTAX     INTEGER
    MAX-ACCESS read-write
    STATUS     current
    DESCRIPTION
        "Set the priority of the alarm from 1 to 10 (where 10 is highest priority)"
::= { enc1A47smpte2031VBIConfigurationAndDataMismatchEntry 2 }

enc1A47smpte2031VBIConfigurationAndDataMismatchAcknowledged  OBJECT-TYPE
    SYNTAX     AlarmAcknowledged
    MAX-ACCESS read-write
    STATUS     current
    DESCRIPTION
        "Acknowledge the alarm such that other clients can see that the alarm has been acknowledged"
::= { enc1A47smpte2031VBIConfigurationAndDataMismatchEntry 3 }

enc1A47smpte2031VBIConfigurationAndDataMismatchTriggerTime  OBJECT-TYPE
    SYNTAX     INTEGER
    MAX-ACCESS read-write
    STATUS     current
    DESCRIPTION
        "Time in 1/10 of a second that an alarm needs to stay triggered until alarm is asserted"
::= { enc1A47smpte2031VBIConfigurationAndDataMismatchEntry 4 }

enc1A47smpte2031VBIConfigurationAndDataMismatchClearTime  OBJECT-TYPE
    SYNTAX     INTEGER
    MAX-ACCESS read-write
    STATUS     current
    DESCRIPTION
        "Time in 1/10 of a second that an alarm needs to stay clear until alarm is unasserted"
::= { enc1A47smpte2031VBIConfigurationAndDataMismatchEntry 5 }

enc1A48externalDataBandwidthExceededTable OBJECT-TYPE
    SYNTAX SEQUENCE OF Enc1A48externalDataBandwidthExceededEntry
    MAX-ACCESS not-accessible
    STATUS     current
    DESCRIPTION
    "External Data Bandwidth Exceeded"
::= { enc1Alarms 48 }

enc1A48externalDataBandwidthExceededEntry OBJECT-TYPE
    SYNTAX Enc1A48externalDataBandwidthExceededEntry
    MAX-ACCESS not-accessible
    STATUS     current
    DESCRIPTION
    "Table Entry for External Data Bandwidth Exceeded"
    INDEX { slotId }
::= { enc1A48externalDataBandwidthExceededTable 1 }

Enc1A48externalDataBandwidthExceededEntry ::= SEQUENCE {
    enc1A48externalDataBandwidthExceededEnabled    AlarmEnabled,
    enc1A48externalDataBandwidthExceededPriority    INTEGER,
    enc1A48externalDataBandwidthExceededAcknowledged    AlarmAcknowledged,
    enc1A48externalDataBandwidthExceededTriggerTime    INTEGER,
    enc1A48externalDataBandwidthExceededClearTime    INTEGER
}

enc1A48externalDataBandwidthExceededEnabled  OBJECT-TYPE
    SYNTAX     AlarmEnabled
    MAX-ACCESS read-write
    STATUS     current
    DESCRIPTION
        "Property to enable or disable the alarm"
::= { enc1A48externalDataBandwidthExceededEntry 1 }

enc1A48externalDataBandwidthExceededPriority  OBJECT-TYPE
    SYNTAX     INTEGER
    MAX-ACCESS read-write
    STATUS     current
    DESCRIPTION
        "Set the priority of the alarm from 1 to 10 (where 10 is highest priority)"
::= { enc1A48externalDataBandwidthExceededEntry 2 }

enc1A48externalDataBandwidthExceededAcknowledged  OBJECT-TYPE
    SYNTAX     AlarmAcknowledged
    MAX-ACCESS read-write
    STATUS     current
    DESCRIPTION
        "Acknowledge the alarm such that other clients can see that the alarm has been acknowledged"
::= { enc1A48externalDataBandwidthExceededEntry 3 }

enc1A48externalDataBandwidthExceededTriggerTime  OBJECT-TYPE
    SYNTAX     INTEGER
    MAX-ACCESS read-write
    STATUS     current
    DESCRIPTION
        "Time in 1/10 of a second that an alarm needs to stay triggered until alarm is asserted"
::= { enc1A48externalDataBandwidthExceededEntry 4 }

enc1A48externalDataBandwidthExceededClearTime  OBJECT-TYPE
    SYNTAX     INTEGER
    MAX-ACCESS read-write
    STATUS     current
    DESCRIPTION
        "Time in 1/10 of a second that an alarm needs to stay clear until alarm is unasserted"
::= { enc1A48externalDataBandwidthExceededEntry 5 }

enc1A49externalAudioMetadataErrorTable OBJECT-TYPE
    SYNTAX SEQUENCE OF Enc1A49externalAudioMetadataErrorEntry
    MAX-ACCESS not-accessible
    STATUS     current
    DESCRIPTION
    "External Audio Metadata Error"
::= { enc1Alarms 49 }

enc1A49externalAudioMetadataErrorEntry OBJECT-TYPE
    SYNTAX Enc1A49externalAudioMetadataErrorEntry
    MAX-ACCESS not-accessible
    STATUS     current
    DESCRIPTION
    "Table Entry for External Audio Metadata Error"
    INDEX { slotId }
::= { enc1A49externalAudioMetadataErrorTable 1 }

Enc1A49externalAudioMetadataErrorEntry ::= SEQUENCE {
    enc1A49externalAudioMetadataErrorEnabled    AlarmEnabled,
    enc1A49externalAudioMetadataErrorPriority    INTEGER,
    enc1A49externalAudioMetadataErrorAcknowledged    AlarmAcknowledged,
    enc1A49externalAudioMetadataErrorTriggerTime    INTEGER,
    enc1A49externalAudioMetadataErrorClearTime    INTEGER
}

enc1A49externalAudioMetadataErrorEnabled  OBJECT-TYPE
    SYNTAX     AlarmEnabled
    MAX-ACCESS read-write
    STATUS     current
    DESCRIPTION
        "Property to enable or disable the alarm"
::= { enc1A49externalAudioMetadataErrorEntry 1 }

enc1A49externalAudioMetadataErrorPriority  OBJECT-TYPE
    SYNTAX     INTEGER
    MAX-ACCESS read-write
    STATUS     current
    DESCRIPTION
        "Set the priority of the alarm from 1 to 10 (where 10 is highest priority)"
::= { enc1A49externalAudioMetadataErrorEntry 2 }

enc1A49externalAudioMetadataErrorAcknowledged  OBJECT-TYPE
    SYNTAX     AlarmAcknowledged
    MAX-ACCESS read-write
    STATUS     current
    DESCRIPTION
        "Acknowledge the alarm such that other clients can see that the alarm has been acknowledged"
::= { enc1A49externalAudioMetadataErrorEntry 3 }

enc1A49externalAudioMetadataErrorTriggerTime  OBJECT-TYPE
    SYNTAX     INTEGER
    MAX-ACCESS read-write
    STATUS     current
    DESCRIPTION
        "Time in 1/10 of a second that an alarm needs to stay triggered until alarm is asserted"
::= { enc1A49externalAudioMetadataErrorEntry 4 }

enc1A49externalAudioMetadataErrorClearTime  OBJECT-TYPE
    SYNTAX     INTEGER
    MAX-ACCESS read-write
    STATUS     current
    DESCRIPTION
        "Time in 1/10 of a second that an alarm needs to stay clear until alarm is unasserted"
::= { enc1A49externalAudioMetadataErrorEntry 5 }

enc1AlternateNameTable OBJECT-TYPE
    SYNTAX SEQUENCE OF Enc1AlternateNameTableEntry
    MAX-ACCESS not-accessible
    STATUS     current
    DESCRIPTION
    "Device specific information table"
::= { enc1DeviceInfo 1 }

enc1AlternateNameTableEntry OBJECT-TYPE
    SYNTAX Enc1AlternateNameTableEntry
    MAX-ACCESS not-accessible
    STATUS     current
    DESCRIPTION
    "Device specific information table entry"
    INDEX { slotId }
::= { enc1AlternateNameTable 1 }

Enc1AlternateNameTableEntry ::= SEQUENCE {
    enc1AlternateNameValue DisplayString
}

enc1AlternateNameValue  OBJECT-TYPE
    SYNTAX DisplayString
    MAX-ACCESS read-only
    STATUS     current
    DESCRIPTION
    "Alternate Name of the device"
::= { enc1AlternateNameTableEntry 1  }

enc1CustomNameTable OBJECT-TYPE
    SYNTAX SEQUENCE OF Enc1CustomNameTableEntry
    MAX-ACCESS not-accessible
    STATUS     current
    DESCRIPTION
    "Device specific information table"
::= { enc1DeviceInfo 2 }

enc1CustomNameTableEntry OBJECT-TYPE
    SYNTAX Enc1CustomNameTableEntry
    MAX-ACCESS not-accessible
    STATUS     current
    DESCRIPTION
    "Device specific information table entry"
    INDEX { slotId }
::= { enc1CustomNameTable 1 }

Enc1CustomNameTableEntry ::= SEQUENCE {
    enc1CustomNameValue DisplayString
}

enc1CustomNameValue  OBJECT-TYPE
    SYNTAX DisplayString
    MAX-ACCESS read-write
    STATUS     current
    DESCRIPTION
    "User Custom Name for the device"
::= { enc1CustomNameTableEntry 1  }

enc1InterfaceVersionTable OBJECT-TYPE
    SYNTAX SEQUENCE OF Enc1InterfaceVersionTableEntry
    MAX-ACCESS not-accessible
    STATUS     current
    DESCRIPTION
    "Device specific information table"
::= { enc1DeviceInfo 3 }

enc1InterfaceVersionTableEntry OBJECT-TYPE
    SYNTAX Enc1InterfaceVersionTableEntry
    MAX-ACCESS not-accessible
    STATUS     current
    DESCRIPTION
    "Device specific information table entry"
    INDEX { slotId }
::= { enc1InterfaceVersionTable 1 }

Enc1InterfaceVersionTableEntry ::= SEQUENCE {
    enc1InterfaceVersionValue DisplayString
}

enc1InterfaceVersionValue  OBJECT-TYPE
    SYNTAX DisplayString
    MAX-ACCESS read-only
    STATUS     current
    DESCRIPTION
    "Interface Version of the device"
::= { enc1InterfaceVersionTableEntry 1  }

enc1VersionValueTable OBJECT-TYPE
    SYNTAX SEQUENCE OF Enc1VersionValueTableEntry
    MAX-ACCESS not-accessible
    STATUS     current
    DESCRIPTION
    "Device specific information table"
::= { enc1DeviceInfo 4 }

enc1VersionValueTableEntry OBJECT-TYPE
    SYNTAX Enc1VersionValueTableEntry
    MAX-ACCESS not-accessible
    STATUS     current
    DESCRIPTION
    "Device specific information table entry"
    INDEX { slotId }
::= { enc1VersionValueTable 1 }

Enc1VersionValueTableEntry ::= SEQUENCE {
    enc1VersionValueValue DisplayString
}

enc1VersionValueValue  OBJECT-TYPE
    SYNTAX DisplayString
    MAX-ACCESS read-only
    STATUS     current
    DESCRIPTION
    "Other version information of the device"
::= { enc1VersionValueTableEntry 1  }

enc1SerialNumberTable OBJECT-TYPE
    SYNTAX SEQUENCE OF Enc1SerialNumberTableEntry
    MAX-ACCESS not-accessible
    STATUS     current
    DESCRIPTION
    "Device specific information table"
::= { enc1DeviceInfo 5 }

enc1SerialNumberTableEntry OBJECT-TYPE
    SYNTAX Enc1SerialNumberTableEntry
    MAX-ACCESS not-accessible
    STATUS     current
    DESCRIPTION
    "Device specific information table entry"
    INDEX { slotId }
::= { enc1SerialNumberTable 1 }

Enc1SerialNumberTableEntry ::= SEQUENCE {
    enc1SerialNumberValue DisplayString
}

enc1SerialNumberValue  OBJECT-TYPE
    SYNTAX DisplayString
    MAX-ACCESS read-only
    STATUS     current
    DESCRIPTION
    "Serial number of the device"
::= { enc1SerialNumberTableEntry 1  }

enc1LicenseKeyTable OBJECT-TYPE
    SYNTAX SEQUENCE OF Enc1LicenseKeyTableEntry
    MAX-ACCESS not-accessible
    STATUS     current
    DESCRIPTION
    "Device specific information table"
::= { enc1DeviceInfo 6 }

enc1LicenseKeyTableEntry OBJECT-TYPE
    SYNTAX Enc1LicenseKeyTableEntry
    MAX-ACCESS not-accessible
    STATUS     current
    DESCRIPTION
    "Device specific information table entry"
    INDEX { slotId }
::= { enc1LicenseKeyTable 1 }

Enc1LicenseKeyTableEntry ::= SEQUENCE {
    enc1LicenseKeyValue DisplayString
}

enc1LicenseKeyValue  OBJECT-TYPE
    SYNTAX DisplayString
    MAX-ACCESS read-write
    STATUS     current
    DESCRIPTION
    "License key of the device"
::= { enc1LicenseKeyTableEntry 1  }

enc1OptionsKeyTable OBJECT-TYPE
    SYNTAX SEQUENCE OF Enc1OptionsKeyTableEntry
    MAX-ACCESS not-accessible
    STATUS     current
    DESCRIPTION
    "Device specific information table"
::= { enc1DeviceInfo 7 }

enc1OptionsKeyTableEntry OBJECT-TYPE
    SYNTAX Enc1OptionsKeyTableEntry
    MAX-ACCESS not-accessible
    STATUS     current
    DESCRIPTION
    "Device specific information table entry"
    INDEX { slotId }
::= { enc1OptionsKeyTable 1 }

Enc1OptionsKeyTableEntry ::= SEQUENCE {
    enc1OptionsKeyValue DisplayString
}

enc1OptionsKeyValue  OBJECT-TYPE
    SYNTAX DisplayString
    MAX-ACCESS read-only
    STATUS     current
    DESCRIPTION
    "Options enabled by the License key of the device"
::= { enc1OptionsKeyTableEntry 1  }

enc1AlarmThresholdTable OBJECT-TYPE
    SYNTAX SEQUENCE OF Enc1AlarmThresholdTableEntry
    MAX-ACCESS not-accessible
    STATUS     current
    DESCRIPTION
    "Device specific information table"
::= { enc1DeviceInfo 8 }

enc1AlarmThresholdTableEntry OBJECT-TYPE
    SYNTAX Enc1AlarmThresholdTableEntry
    MAX-ACCESS not-accessible
    STATUS     current
    DESCRIPTION
    "Device specific information table entry"
    INDEX { slotId }
::= { enc1AlarmThresholdTable 1 }

Enc1AlarmThresholdTableEntry ::= SEQUENCE {
    enc1AlarmThresholdValue Integer32
}

enc1AlarmThresholdValue  OBJECT-TYPE
    SYNTAX Integer32
    MAX-ACCESS read-write
    STATUS     current
    DESCRIPTION
    "Global alarm filter for the device"
::= { enc1AlarmThresholdTableEntry 1  }

enc1AlarmStateSetTable OBJECT-TYPE
    SYNTAX SEQUENCE OF Enc1AlarmStateSetTableEntry
    MAX-ACCESS not-accessible
    STATUS     current
    DESCRIPTION
    "Device specific information table"
::= { enc1DeviceInfo 9 }

enc1AlarmStateSetTableEntry OBJECT-TYPE
    SYNTAX Enc1AlarmStateSetTableEntry
    MAX-ACCESS not-accessible
    STATUS     current
    DESCRIPTION
    "Device specific information table entry"
    INDEX { slotId }
::= { enc1AlarmStateSetTable 1 }

Enc1AlarmStateSetTableEntry ::= SEQUENCE {
    enc1AlarmStateSetValue Integer32
}

enc1AlarmStateSetValue  OBJECT-TYPE
    SYNTAX Integer32
    MAX-ACCESS read-write
    STATUS     current
    DESCRIPTION
    "Function to enable/disable all alarms on the device"
::= { enc1AlarmStateSetTableEntry 1  }

enc1NextDirtyTable OBJECT-TYPE
    SYNTAX SEQUENCE OF Enc1NextDirtyTableEntry
    MAX-ACCESS not-accessible
    STATUS     current
    DESCRIPTION
    "Device specific information table"
::= { enc1DeviceInfo 10 }

enc1NextDirtyTableEntry OBJECT-TYPE
    SYNTAX Enc1NextDirtyTableEntry
    MAX-ACCESS not-accessible
    STATUS     current
    DESCRIPTION
    "Device specific information table entry"
    INDEX { slotId }
::= { enc1NextDirtyTable 1 }

Enc1NextDirtyTableEntry ::= SEQUENCE {
    enc1NextDirtyValue OBJECT IDENTIFIER
}

enc1NextDirtyValue  OBJECT-TYPE
    SYNTAX OBJECT IDENTIFIER
    MAX-ACCESS read-only
    STATUS     current
    DESCRIPTION
    "The next dirty OID of the dirty list (returns empty list if there are no dirties, or -1 if the dirties exceed a certain amount)"
::= { enc1NextDirtyTableEntry 1  }

enc1DirtyCountTable OBJECT-TYPE
    SYNTAX SEQUENCE OF Enc1DirtyCountTableEntry
    MAX-ACCESS not-accessible
    STATUS     current
    DESCRIPTION
    "Device specific information table"
::= { enc1DeviceInfo 11 }

enc1DirtyCountTableEntry OBJECT-TYPE
    SYNTAX Enc1DirtyCountTableEntry
    MAX-ACCESS not-accessible
    STATUS     current
    DESCRIPTION
    "Device specific information table entry"
    INDEX { slotId }
::= { enc1DirtyCountTable 1 }

Enc1DirtyCountTableEntry ::= SEQUENCE {
    enc1DirtyCountValue Integer32
}

enc1DirtyCountValue  OBJECT-TYPE
    SYNTAX Integer32
    MAX-ACCESS read-only
    STATUS     current
    DESCRIPTION
    "The number of dirties since discovery of read/write parameters"
::= { enc1DirtyCountTableEntry 1  }

END
